;;Utility for Curvilinear perspective
;;v02 adds ability for curves (lines only in v01)
;;v03 adds vert perspective
;;Jarvis Fosdick, 10-15-05 (C) 2005
(defun set_station (/ ss)
  (princ "\nPick View Station")
  (setq view_station (getpoint))
)
(defun Cen-p (/)
  (princ "\nPick Perspective VP (in the big circle)")
  (setq big_circle (getpoint))
)
(defun c:setbase (/)
  (set_station)
  (cen-p)
)
(defun c:dcp (/ ss spnts scrvpnts scircpnts pp)
  (defun *error* (str)
    (princ str)(princ)
    )
  (defun d0 (n1 n2 /)
    (cond
      ((= 0 n2)
       (* 0 0)
      )
      ((= 0 0)
       (/ n1 n2)
      )
    )
  )
  (defun hypt (opp adj /)
    (sqrt (+ (expt opp 2) (expt adj 2)))
  )
  (defun cdx (li /)
    (car (reverse li))
  )
  (defun cdrx (li /)
    (reverse (cdr (reverse li)))
  )
  (defun midpnt	(p1 p2 /)
    (mapcar '+
	    (mapcar '(lambda (x) (/ x 2.0)) (mapcar 'dis p1 p2))
	    p1
    )
  )
  (defun dis (p1 p2 /)
    (- p2 p1)
  )
  (defun ang (opp adj /)
    (setq opp (* 1.00 opp)
	  adj (* 1.00 adj)
    )
    (atan (d0 opp adj))
  )
  (defun d->r (rads /)
    (* (/ 180 pi) rads)
  )
  (defun foreachss (fun ss / cnt)
    (setq cnt 0)
    (while (> (sslength ss) cnt)
      (eval '(fun (entget (ssname ss cnt))))
      (setq cnt (1+ cnt))
    )
  )
  (defun rlpnts	(line /)
    (list (cdr (assoc 10 line)) (cdr (assoc 11 line)))

  )
  (defun rspl (line /)
    (setq spnts '())
    (setq spnts (reverse (append spnts (rlpnts line))))
    (setq spnts	(append	spnts
			(list (midpnt (cdx spnts)
				      (midpnt (cdx spnts) (car spnts))
			      )
			)
		)
    )
    (setq spnts (append spnts (list (midpnt (car spnts) (cadr spnts)))))
    (setq spnts (append spnts (list (midpnt (cdx spnts) (car spnts)))))
    (setq spnts (append (cdr spnts) (list (car spnts))))
    (setq spnts spnts)

  )
  (defun rcpnts (curv / )
    (list (cdr (assoc 10 curv))
	  (cdr (assoc 40 curv))
	  ;(min (cdr (assoc 50 curv)) (cdr (assoc 51 curv)))
	  ;(max (cdr (assoc 50 curv)) (cdr (assoc 51 curv)))
	  (cdr (assoc 50 curv))
	  (cdr (assoc 51 curv))
    )
    )
 (defun rcircpnts (curv / )
   (list (cdr (assoc 10 curv)) (cdr (assoc 40 curv)))
   )
  (defun rcpp (base ang dist / )
    (polar base ang dist)
    )
(defun get-circ-data (curv / )
  (setq scircpnts '())
    (setq scircpnts (append scircpnts (list (polar (car (rcircpnts curv))
					   0
					   (cadr (rcircpnts curv))
					   ))
			   )
	  )
   (setq cnt (/ (* 2 pi) 30.0))
  (setq int cnt)
          (while (< cnt (* 2 pi))
(setq scircpnts (append scircpnts (list (polar (car (rcircpnts curv))
					     cnt
					     (cadr (rcircpnts curv))
					     ))
		       )
      )
	  (setq cnt (+ cnt int))
	  );while
      (setq scircpnts (append scircpnts (list (polar (car (rcircpnts curv))
					   0
					   (cadr (rcircpnts curv))
					   ))
			   )
	  )
   )
  
  
  (defun get-c-data (curv /)
    ;(setq cen_ang (- (cadddr (rcpnts curv)) (caddr (rcpnts curv))))
    ;(setq len (* (cadr (rcpnts curv)) cen_ang))    
(setq scrvpnts '())
    ;(setq scrvpnts (append scrvpnts (list (car (rcpnts curv)))))
    ;(setq scrvpnts (append scrvpnts (list (caddr (rcpnts curv)))))
    (setq scrvpnts (append scrvpnts (list (polar (car (rcpnts curv))
					   (cadddr (rcpnts curv))
					   (cadr (rcpnts curv))
					   ))
			   )
	  )
    (setq scrvpnts (append scrvpnts (list (polar (car (rcpnts curv))
					   (caddr (rcpnts curv))
					   (cadr (rcpnts curv))
					   ))
			   )
	  )
    
  (setq int 24)  
  (setq cnt (abs (/ (- (cadddr (rcpnts curv)) (caddr (rcpnts curv))) int)))
  (setq int cnt)
  
        (repeat 22
(setq scrvpnts (append scrvpnts (list (polar (car (rcpnts curv))
					     (+ cnt (caddr (rcpnts curv)))
					     (cadr (rcpnts curv))
					     ))
		       )
      )
	  (setq cnt (+ cnt int))
	  
)	  ;repeat
  (setq scrvpnts (append (cdr scrvpnts) (list (car scrvpnts))))

  );defun get-c-data

	  
;;;    (setq scrvpnts (append scrvpnts (list (inters
;;;				     (cadr scrvpnts)
;;;				     (polar (cadr scrvpnts) (+ (/ pi 2.0) (angle (cadr scrvpnts) (car scrvpnts))) (cadr (rcpnts curv)))
;;;				     (cdx scrvpnts)
;;;				     (polar (cdx scrvpnts) (+ (/ pi 2.0) (angle (cdx scrvpnts) (car scrvpnts))) (cadr (rcpnts curv)))
;;;				     nil
;;;				     ))
;;;			  )
;;;	  )
;;;    (setq bulge (/ (distance (car scrvpnts) (inters (caddr scrvpnts) (cadr scrvpnts) (car scrvpnts) (cadddr scrvpnts)))
;;;		   (/ (distance (car scrvpnts) (cadr scrvpnts)) 2.0)
;;;		   )
;;;	  )
;;;    (setq b2 (/ (- (cadddr (rcpnts curv)) (caddr (rcpnts curv))) 4.0))
;;;		   
;;;    
    
  (defun xy_zh (bas pnt /)
    (mapcar 'd->r
	    (mapcar 'ang
		    (list (car (mapcar 'dis bas pnt))
			  	
			  (cdx (mapcar 'dis bas pnt))
		    )
		    (list (hypt (cadr (mapcar 'dis bas pnt))
				(cdx (mapcar 'dis bas pnt))
				)
			  (hypt	(car (mapcar 'dis bas pnt))
				(cadr (mapcar 'dis bas pnt))
			  
		    )
	    )
    )
  )
    )
  (defun p-pnts	(obj bas /)
    
    (setq pp '())
    (cond ((= (cdr (assoc 0 obj)) "LINE")
    (foreach x (rspl obj)
      (setq
	pp (append pp
		   (list (mapcar '+ (cdrx big_circle) (xy_zh bas x)))
	   )
      )
    ))
	  ((= (cdr (assoc 0 obj)) "ARC")
	       (foreach x (get-c-data obj)
      (setq
	pp (append pp
		   (list (mapcar '+ (cdrx big_circle) (xy_zh bas x)))
	   )
      )
    ))
	  ((= (cdr (assoc 0 obj)) "CIRCLE")
	       (foreach x (get-circ-data obj)
      (setq
	pp (append pp
		   (list (mapcar '+ (cdrx big_circle) (xy_zh bas x)))
	   )
      )
    ))
	  )
(cond
  ((and (car pp))
      (command ".spline")
 (mapcar 'command pp)
	(command 	"")
	(command 	"")
	(command 	"")
       

))
      )
    					;cond
  
  (defun getlines (/)
    (princ "\nSelect Lines, Arcs or Circles: ")
    (ssget)
  )

  (setq user_os_mode (getvar "osmode"))
  (setvar "osmode" 0)
  (command "undo" "mark")
  (cond
    ((or (not view_station) (not big_circle))
     (set_station)
     (cen-p)
    )
  )
  (setq ss (getlines))

  (foreachss (lambda (x) (setvar "clayer" (cdr (assoc 8 x))) (p-pnts x view_station)) ss)(princ)

  (setvar "osmode" user_os_mode)
  (princ)


)					;dcp  end of main command
(princ "\ntype  DCP to begin")
