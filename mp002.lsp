(command "layer" "m" edge "" )
(command "layer" "m" edge "" )
(command "layer" "m" edge "" )
(command "layer" "m" edge "" )
(command "layer" "m" edge "" )
(command "insert" edge '(0 -6) 5 5 0 )
(command "layer" "m" edge "" )
(command "insert" edge '(0 -10) 5 5 0 )
(command "layer" "m" edge "" )
(command "insert" edge '(0 -12) 5 5 0 )
(command "insert" edge '(0 -12) 5 5 0 )
(command "insert" edge '(0 -12) 5 5 0 )
