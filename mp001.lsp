(command "layer" "m" "ped" "" )
(command "insert" "ped" '(211 -105) 1 1 0 )
(command "insert" "ped" '(270 -97) 1 1 0 )
(command "insert" "ped" '(187 -94) 1 1 0 )
(command "insert" "ped" '(185 -101) 1 1 0 )
(command "insert" "ped" '(186 -93) 1 1 0 )
(command "insert" "ped" '(243 -100) 1 1 0 )
(command "insert" "ped" '(212 -107) 1 1 0 )
(command "insert" "ped" '(213 -99) 1 1 0 )
(command "insert" "ped" '(257 -106) 1 1 0 )
(command "insert" "ped" '(224 -101) 1 1 0 )
(command "insert" "ped" '(188 -91) 1 1 0 )
(command "insert" "ped" '(194 -98) 1 1 0 )
(command "insert" "ped" '(264 -102) 1 1 0 )
(command "insert" "ped" '(214 -97) 1 1 0 )
(command "insert" "ped" '(249 -99) 1 1 0 )
(command "insert" "ped" '(228 -107) 1 1 0 )
(command "insert" "ped" '(191 -97) 1 1 0 )
(command "insert" "ped" '(226 -103) 1 1 0 )
(command "insert" "ped" '(198 -100) 1 1 0 )
(command "insert" "ped" '(262 -105) 1 1 0 )
(command "insert" "ped" '(246 -98) 1 1 0 )
(command "insert" "ped" '(202 -107) 1 1 0 )
(command "insert" "ped" '(203 -107) 1 1 0 )
(command "insert" "ped" '(250 -97) 1 1 0 )
(command "insert" "ped" '(223 -100) 1 1 0 )
(command "insert" "ped" '(233 -102) 1 1 0 )
(command "insert" "ped" '(263 -103) 1 1 0 )
(command "insert" "ped" '(221 -101) 1 1 0 )
(command "insert" "ped" '(254 -107) 1 1 0 )
(command "insert" "ped" '(274 -93) 1 1 0 )
(command "insert" "ped" '(236 -106) 1 1 0 )
(command "insert" "ped" '(195 -106) 1 1 0 )
(command "insert" "ped" '(280 -94) 1 1 0 )
(command "insert" "ped" '(243 -96) 1 1 0 )
(command "insert" "ped" '(282 -92) 1 1 0 )
(command "insert" "ped" '(192 -107) 1 1 0 )
(command "insert" "ped" '(216 -99) 1 1 0 )
(command "insert" "ped" '(187 -99) 1 1 0 )
(command "insert" "ped" '(186 -100) 1 1 0 )
(command "insert" "ped" '(193 -103) 1 1 0 )
(command "insert" "ped" '(269 -94) 1 1 0 )
(command "insert" "ped" '(284 -90) 1 1 0 )
(command "insert" "ped" '(261 -107) 1 1 0 )
(command "insert" "ped" '(276 -96) 1 1 0 )
(command "insert" "ped" '(217 -105) 1 1 0 )
(command "insert" "ped" '(190 -102) 1 1 0 )
(command "insert" "ped" '(187 -96) 1 1 0 )
(command "insert" "ped" '(197 -105) 1 1 0 )
(command "insert" "ped" '(258 -102) 1 1 0 )
(command "insert" "ped" '(215 -106) 1 1 0 )
(command "insert" "ped" '(275 -93) 1 1 0 )
(command "insert" "ped" '(222 -99) 1 1 0 )
(command "insert" "ped" '(282 -96) 1 1 0 )
(command "insert" "ped" '(263 -97) 1 1 0 )
(command "insert" "ped" '(189 -106) 1 1 0 )
(command "insert" "ped" '(199 -103) 1 1 0 )
(command "insert" "ped" '(246 -101) 1 1 0 )
(command "insert" "ped" '(235 -104) 1 1 0 )
(command "insert" "ped" '(277 -95) 1 1 0 )
(command "insert" "ped" '(227 -102) 1 1 0 )
(command "insert" "ped" '(225 -106) 1 1 0 )
(command "insert" "ped" '(289 -93) 1 1 0 )
(command "insert" "ped" '(205 -106) 1 1 0 )
(command "insert" "ped" '(252 -102) 1 1 0 )
(command "insert" "ped" '(279 -89) 1 1 0 )
(command "insert" "ped" '(229 -100) 1 1 0 )
(command "insert" "ped" '(197 -96) 1 1 0 )
(command "insert" "ped" '(240 -100) 1 1 0 )
(command "insert" "ped" '(257 -103) 1 1 0 )
(command "insert" "ped" '(281 -89) 1 1 0 )
(command "insert" "ped" '(271 -93) 1 1 0 )
(command "insert" "ped" '(268 -93) 1 1 0 )
(command "insert" "ped" '(283 -95) 1 1 0 )
(command "insert" "ped" '(216 -106) 1 1 0 )
(command "insert" "ped" '(206 -106) 1 1 0 )
(command "insert" "ped" '(285 -93) 1 1 0 )
(command "insert" "ped" '(196 -97) 1 1 0 )
(command "insert" "ped" '(190 -105) 1 1 0 )
(command "insert" "ped" '(208 -102) 1 1 0 )
(command "insert" "ped" '(271 -97) 1 1 0 )
(command "insert" "ped" '(287 -91) 1 1 0 )
(command "insert" "ped" '(275 -98) 1 1 0 )
(command "insert" "ped" '(222 -106) 1 1 0 )
(command "insert" "ped" '(219 -100) 1 1 0 )
(command "insert" "ped" '(203 -102) 1 1 0 )
(command "insert" "ped" '(189 -99) 1 1 0 )
(command "insert" "ped" '(224 -105) 1 1 0 )
(command "insert" "ped" '(187 -95) 1 1 0 )
(command "insert" "ped" '(244 -100) 1 1 0 )
(command "insert" "ped" '(200 -101) 1 1 0 )
(command "insert" "ped" '(251 -99) 1 1 0 )
(command "insert" "ped" '(223 -106) 1 1 0 )
(command "insert" "ped" '(278 -94) 1 1 0 )
(command "insert" "ped" '(221 -102) 1 1 0 )
(command "insert" "ped" '(228 -103) 1 1 0 )
(command "insert" "ped" '(225 -99) 1 1 0 )
(command "insert" "ped" '(235 -100) 1 1 0 )
(command "insert" "ped" '(189 -93) 1 1 0 )
(command "insert" "ped" '(255 -105) 1 1 0 )
(command "insert" "ped" '(202 -103) 1 1 0 )
(command "insert" "ped" '(206 -103) 1 1 0 )
(command "insert" "ped" '(279 -86) 1 1 0 )
(command "insert" "ped" '(241 -99) 1 1 0 )
(command "insert" "ped" '(231 -107) 1 1 0 )
(command "insert" "ped" '(255 -99) 1 1 0 )
(command "insert" "ped" '(242 -97) 1 1 0 )
(command "insert" "ped" '(266 -100) 1 1 0 )
(command "insert" "ped" '(195 -104) 1 1 0 )
(command "insert" "ped" '(183 -95) 1 1 0 )
(command "insert" "ped" '(287 -95) 1 1 0 )
(command "insert" "ped" '(184 -90) 1 1 0 )
(command "insert" "ped" '(241 -95) 1 1 0 )
(command "insert" "ped" '(189 -94) 1 1 0 )
(command "insert" "ped" '(218 -107) 1 1 0 )
(command "insert" "ped" '(188 -96) 1 1 0 )
(command "insert" "ped" '(185 -98) 1 1 0 )
(command "insert" "ped" '(195 -103) 1 1 0 )
(command "insert" "ped" '(192 -99) 1 1 0 )
(command "insert" "ped" '(193 -107) 1 1 0 )
(command "insert" "ped" '(274 -98) 1 1 0 )
(command "insert" "ped" '(220 -101) 1 1 0 )
(command "insert" "ped" '(265 -99) 1 1 0 )
(command "insert" "ped" '(196 -105) 1 1 0 )
(command "insert" "ped" '(188 -94) 1 1 0 )
(command "insert" "ped" '(194 -105) 1 1 0 )
(command "insert" "ped" '(277 -97) 1 1 0 )
(command "insert" "ped" '(208 -99) 1 1 0 )
(command "insert" "ped" '(225 -100) 1 1 0 )
(command "insert" "ped" '(226 -106) 1 1 0 )
(command "insert" "ped" '(198 -99) 1 1 0 )
(command "insert" "ped" '(242 -95) 1 1 0 )
(command "insert" "ped" '(265 -107) 1 1 0 )
(command "insert" "ped" '(250 -100) 1 1 0 )
(command "insert" "ped" '(210 -105) 1 1 0 )
(command "insert" "ped" '(262 -98) 1 1 0 )
(command "insert" "ped" '(234 -99) 1 1 0 )
(command "insert" "ped" '(215 -102) 1 1 0 )
(command "insert" "ped" '(241 -100) 1 1 0 )
(command "insert" "ped" '(204 -104) 1 1 0 )
(command "insert" "ped" '(274 -96) 1 1 0 )
(command "insert" "ped" '(212 -100) 1 1 0 )
(command "insert" "ped" '(290 -95) 1 1 0 )
(command "insert" "ped" '(280 -89) 1 1 0 )
(command "insert" "ped" '(184 -97) 1 1 0 )
(command "insert" "ped" '(264 -100) 1 1 0 )
(command "insert" "ped" '(211 -107) 1 1 0 )
(command "insert" "ped" '(261 -94) 1 1 0 )
(command "insert" "ped" '(186 -91) 1 1 0 )
(command "insert" "ped" '(199 -99) 1 1 0 )
(command "insert" "ped" '(284 -93) 1 1 0 )
(command "insert" "ped" '(213 -97) 1 1 0 )
(command "insert" "ped" '(217 -102) 1 1 0 )
(command "insert" "ped" '(196 -103) 1 1 0 )
(command "insert" "ped" '(224 -103) 1 1 0 )
(command "insert" "ped" '(194 -96) 1 1 0 )
(command "insert" "ped" '(245 -100) 1 1 0 )
(command "insert" "ped" '(201 -107) 1 1 0 )
(command "insert" "ped" '(214 -103) 1 1 0 )
(command "insert" "ped" '(249 -97) 1 1 0 )
(command "insert" "ped" '(219 -104) 1 1 0 )
(command "insert" "ped" '(191 -99) 1 1 0 )
(command "insert" "ped" '(226 -101) 1 1 0 )
(command "insert" "ped" '(239 -101) 1 1 0 )
(command "insert" "ped" '(199 -104) 1 1 0 )
(command "insert" "ped" '(246 -96) 1 1 0 )
(command "insert" "ped" '(202 -105) 1 1 0 )
(command "insert" "ped" '(223 -102) 1 1 0 )
(command "insert" "ped" '(230 -103) 1 1 0 )
(command "insert" "ped" '(227 -99) 1 1 0 )
(command "insert" "ped" '(234 -106) 1 1 0 )
(command "insert" "ped" '(289 -90) 1 1 0 )
(command "insert" "ped" '(204 -103) 1 1 0 )
(command "insert" "ped" '(255 -101) 1 1 0 )
(command "insert" "ped" '(252 -105) 1 1 0 )
(command "insert" "ped" '(236 -100) 1 1 0 )
(command "insert" "ped" '(257 -107) 1 1 0 )
(command "insert" "ped" '(256 -104) 1 1 0 )
(command "insert" "ped" '(278 -95) 1 1 0 )
(command "insert" "ped" '(281 -86) 1 1 0 )
(command "insert" "ped" '(266 -102) 1 1 0 )
(command "insert" "ped" '(267 -94) 1 1 0 )
(command "insert" "ped" '(282 -90) 1 1 0 )
(command "insert" "ped" '(272 -93) 1 1 0 )
(command "insert" "ped" '(216 -101) 1 1 0 )
(command "insert" "ped" '(186 -98) 1 1 0 )
(command "insert" "ped" '(193 -106) 1 1 0 )
(command "insert" "ped" '(213 -106) 1 1 0 )
(command "insert" "ped" '(183 -97) 1 1 0 )
(command "insert" "ped" '(218 -103) 1 1 0 )
(command "insert" "ped" '(190 -100) 1 1 0 )
(command "insert" "ped" '(187 -98) 1 1 0 )
(command "insert" "ped" '(238 -98) 1 1 0 )
(command "insert" "ped" '(196 -95) 1 1 0 )
(command "insert" "ped" '(215 -100) 1 1 0 )
(command "insert" "ped" '(275 -95) 1 1 0 )
(command "insert" "ped" '(191 -104) 1 1 0 )
(command "insert" "ped" '(189 -104) 1 1 0 )
(command "insert" "ped" '(262 -102) 1 1 0 )
(command "insert" "ped" '(196 -101) 1 1 0 )
(command "insert" "ped" '(273 -94) 1 1 0 )
(command "insert" "ped" '(277 -93) 1 1 0 )
(command "insert" "ped" '(221 -107) 1 1 0 )
(command "insert" "ped" '(227 -104) 1 1 0 )
(command "insert" "ped" '(225 -104) 1 1 0 )
(command "insert" "ped" '(272 -96) 1 1 0 )
(command "insert" "ped" '(205 -104) 1 1 0 )
(command "insert" "ped" '(279 -91) 1 1 0 )
(command "insert" "ped" '(214 -99) 1 1 0 )
(command "insert" "ped" '(236 -99) 1 1 0 )
(command "insert" "ped" '(287 -92) 1 1 0 )
(command "insert" "ped" '(204 -107) 1 1 0 )
(command "insert" "ped" '(261 -95) 1 1 0 )
(command "insert" "ped" '(281 -95) 1 1 0 )
(command "insert" "ped" '(242 -100) 1 1 0 )
(command "insert" "ped" '(268 -95) 1 1 0 )
(command "insert" "ped" '(257 -99) 1 1 0 )
(command "insert" "ped" '(254 -102) 1 1 0 )
(command "insert" "ped" '(206 -104) 1 1 0 )
(command "insert" "ped" '(285 -91) 1 1 0 )
(command "insert" "ped" '(239 -98) 1 1 0 )
(command "insert" "ped" '(238 -101) 1 1 0 )
(command "insert" "ped" '(185 -95) 1 1 0 )
(command "insert" "ped" '(195 -96) 1 1 0 )
(command "insert" "ped" '(222 -104) 1 1 0 )
(command "insert" "ped" '(219 -102) 1 1 0 )
(command "insert" "ped" '(220 -104) 1 1 0 )
(command "insert" "ped" '(189 -97) 1 1 0 )
(command "insert" "ped" '(224 -107) 1 1 0 )
(command "insert" "ped" '(259 -105) 1 1 0 )
(command "insert" "ped" '(247 -96) 1 1 0 )
(command "insert" "ped" '(257 -105) 1 1 0 )
(command "insert" "ped" '(200 -103) 1 1 0 )
(command "insert" "ped" '(251 -101) 1 1 0 )
(command "insert" "ped" '(214 -107) 1 1 0 )
(command "insert" "ped" '(221 -100) 1 1 0 )
(command "insert" "ped" '(236 -104) 1 1 0 )
(command "insert" "ped" '(288 -91) 1 1 0 )
(command "insert" "ped" '(235 -102) 1 1 0 )
(command "insert" "ped" '(232 -100) 1 1 0 )
(command "insert" "ped" '(255 -107) 1 1 0 )
(command "insert" "ped" '(253 -103) 1 1 0 )
(command "insert" "ped" '(209 -102) 1 1 0 )
(command "insert" "ped" '(229 -107) 1 1 0 )
(command "insert" "ped" '(230 -107) 1 1 0 )
(command "insert" "ped" '(237 -100) 1 1 0 )
(command "insert" "ped" '(234 -102) 1 1 0 )
(command "insert" "ped" '(241 -97) 1 1 0 )
(command "insert" "ped" '(232 -106) 1 1 0 )
(command "insert" "ped" '(231 -101) 1 1 0 )
(command "insert" "ped" '(260 -99) 1 1 0 )
(command "insert" "ped" '(280 -84) 1 1 0 )
(command "insert" "ped" '(184 -92) 1 1 0 )
(command "insert" "ped" '(207 -99) 1 1 0 )
(command "insert" "ped" '(211 -100) 1 1 0 )
(command "insert" "ped" '(263 -94) 1 1 0 )
(command "insert" "ped" '(218 -105) 1 1 0 )
(command "insert" "ped" '(188 -98) 1 1 0 )
(command "insert" "ped" '(185 -96) 1 1 0 )
(command "insert" "ped" '(195 -105) 1 1 0 )
(command "insert" "ped" '(192 -101) 1 1 0 )
(command "insert" "ped" '(193 -105) 1 1 0 )
(command "insert" "ped" '(212 -104) 1 1 0 )
(command "insert" "ped" '(213 -102) 1 1 0 )
(command "insert" "ped" '(283 -98) 1 1 0 )
(command "insert" "ped" '(217 -99) 1 1 0 )
(command "insert" "ped" '(196 -107) 1 1 0 )
(command "insert" "ped" '(197 -99) 1 1 0 )
(command "insert" "ped" '(194 -103) 1 1 0 )
(command "insert" "ped" '(196 -93) 1 1 0 )
(command "insert" "ped" '(264 -99) 1 1 0 )
(command "insert" "ped" '(214 -98) 1 1 0 )
(command "insert" "ped" '(208 -101) 1 1 0 )
(command "insert" "ped" '(228 -104) 1 1 0 )
(command "insert" "ped" '(191 -100) 1 1 0 )
(command "insert" "ped" '(226 -104) 1 1 0 )
(command "insert" "ped" '(232 -107) 1 1 0 )
(command "insert" "ped" '(233 -99) 1 1 0 )
(command "insert" "ped" '(265 -105) 1 1 0 )
(command "insert" "ped" '(250 -98) 1 1 0 )
(command "insert" "ped" '(210 -103) 1 1 0 )
(command "insert" "ped" '(256 -102) 1 1 0 )
(command "insert" "ped" '(283 -97) 1 1 0 )
(command "insert" "ped" '(288 -95) 1 1 0 )
(command "insert" "ped" '(288 -94) 1 1 0 )
(command "insert" "ped" '(204 -106) 1 1 0 )
(command "insert" "ped" '(274 -94) 1 1 0 )
(command "insert" "ped" '(203 -103) 1 1 0 )
(command "insert" "ped" '(290 -93) 1 1 0 )
(command "insert" "ped" '(249 -100) 1 1 0 )
(command "insert" "ped" '(204 -105) 1 1 0 )
(command "insert" "ped" '(280 -91) 1 1 0 )
(command "insert" "ped" '(244 -97) 1 1 0 )
(command "insert" "ped" '(260 -101) 1 1 0 )
(command "insert" "ped" '(184 -99) 1 1 0 )
(command "insert" "ped" '(282 -94) 1 1 0 )
(command "insert" "ped" '(207 -104) 1 1 0 )
(command "insert" "ped" '(194 -104) 1 1 0 )
(command "insert" "ped" '(214 -105) 1 1 0 )
(command "insert" "ped" '(193 -98) 1 1 0 )
(command "insert" "ped" '(284 -95) 1 1 0 )
(command "insert" "ped" '(217 -100) 1 1 0 )
(command "insert" "ped" '(190 -99) 1 1 0 )
(command "insert" "ped" '(239 -96) 1 1 0 )
(command "insert" "ped" '(245 -98) 1 1 0 )
(command "insert" "ped" '(201 -105) 1 1 0 )
(command "insert" "ped" '(214 -101) 1 1 0 )
(command "insert" "ped" '(215 -105) 1 1 0 )
(command "insert" "ped" '(285 -97) 1 1 0 )
(command "insert" "ped" '(219 -106) 1 1 0 )
(command "insert" "ped" '(226 -99) 1 1 0 )
(command "insert" "ped" '(233 -100) 1 1 0 )
(command "insert" "ped" '(230 -101) 1 1 0 )
(command "insert" "ped" '(227 -101) 1 1 0 )
(command "insert" "ped" '(234 -104) 1 1 0 )
(command "insert" "ped" '(235 -106) 1 1 0 )
(command "insert" "ped" '(255 -103) 1 1 0 )
(command "insert" "ped" '(252 -107) 1 1 0 )
(command "insert" "ped" '(209 -106) 1 1 0 )
(command "insert" "ped" '(229 -103) 1 1 0 )
(command "insert" "ped" '(236 -102) 1 1 0 )
(command "insert" "ped" '(240 -97) 1 1 0 )
(command "insert" "ped" '(265 -94) 1 1 0 )
(command "insert" "ped" '(281 -84) 1 1 0 )
(command "insert" "ped" '(272 -95) 1 1 0 )
(command "insert" "ped" '(197 -94) 1 1 0 )
(command "insert" "ped" '(283 -90) 1 1 0 )
(command "insert" "ped" '(273 -97) 1 1 0 )
(command "insert" "ped" '(216 -103) 1 1 0 )
(command "insert" "ped" '(186 -96) 1 1 0 )
(command "insert" "ped" '(240 -93) 1 1 0 )
(command "insert" "ped" '(286 -97) 1 1 0 )
(command "insert" "ped" '(213 -104) 1 1 0 )
(command "insert" "ped" '(262 -96) 1 1 0 )
(command "insert" "ped" '(183 -99) 1 1 0 )
(command "insert" "ped" '(218 -101) 1 1 0 )
(command "insert" "ped" '(190 -106) 1 1 0 )
(command "insert" "ped" '(187 -100) 1 1 0 )
(command "insert" "ped" '(238 -96) 1 1 0 )
(command "insert" "ped" '(192 -105) 1 1 0 )
(command "insert" "ped" '(278 -97) 1 1 0 )
(command "insert" "ped" '(275 -97) 1 1 0 )
(command "insert" "ped" '(222 -103) 1 1 0 )
(command "insert" "ped" '(219 -99) 1 1 0 )
(command "insert" "ped" '(191 -106) 1 1 0 )
(command "insert" "ped" '(189 -102) 1 1 0 )
(command "insert" "ped" '(262 -100) 1 1 0 )
(command "insert" "ped" '(187 -90) 1 1 0 )
(command "insert" "ped" '(247 -101) 1 1 0 )
(command "insert" "ped" '(266 -107) 1 1 0 )
(command "insert" "ped" '(223 -105) 1 1 0 )
(command "insert" "ped" '(208 -105) 1 1 0 )
(command "insert" "ped" '(221 -105) 1 1 0 )
(command "insert" "ped" '(227 -106) 1 1 0 )
(command "insert" "ped" '(228 -100) 1 1 0 )
(command "insert" "ped" '(235 -99) 1 1 0 )
(command "insert" "ped" '(205 -102) 1 1 0 )
(command "insert" "ped" '(209 -99) 1 1 0 )
(command "insert" "ped" '(264 -93) 1 1 0 )
(command "insert" "ped" '(245 -97) 1 1 0 )
(command "insert" "ped" '(191 -94) 1 1 0 )
(command "insert" "ped" '(288 -92) 1 1 0 )
(command "insert" "ped" '(264 -107) 1 1 0 )
(command "insert" "ped" '(266 -95) 1 1 0 )
(command "insert" "ped" '(281 -93) 1 1 0 )
(command "insert" "ped" '(240 -98) 1 1 0 )
(command "insert" "ped" '(242 -98) 1 1 0 )
(command "insert" "ped" '(233 -105) 1 1 0 )
(command "insert" "ped" '(258 -100) 1 1 0 )
(command "insert" "ped" '(207 -100) 1 1 0 )
(command "insert" "ped" '(252 -100) 1 1 0 )
(command "insert" "ped" '(244 -96) 1 1 0 )
(command "insert" "ped" '(205 -105) 1 1 0 )
(command "insert" "ped" '(188 -101) 1 1 0 )
(command "insert" "ped" '(185 -93) 1 1 0 )
(command "insert" "ped" '(195 -98) 1 1 0 )
(command "insert" "ped" '(192 -96) 1 1 0 )
(command "insert" "ped" '(263 -106) 1 1 0 )
(command "insert" "ped" '(212 -99) 1 1 0 )
(command "insert" "ped" '(220 -106) 1 1 0 )
(command "insert" "ped" '(262 -95) 1 1 0 )
(command "insert" "ped" '(259 -107) 1 1 0 )
(command "insert" "ped" '(247 -98) 1 1 0 )
(command "insert" "ped" '(194 -106) 1 1 0 )
(command "insert" "ped" '(200 -105) 1 1 0 )
(command "insert" "ped" '(248 -99) 1 1 0 )
(command "insert" "ped" '(199 -101) 1 1 0 )
(command "insert" "ped" '(284 -97) 1 1 0 )
(command "insert" "ped" '(228 -99) 1 1 0 )
(command "insert" "ped" '(225 -103) 1 1 0 )
(command "insert" "ped" '(232 -102) 1 1 0 )
(command "insert" "ped" '(265 -102) 1 1 0 )
(command "insert" "ped" '(253 -101) 1 1 0 )
(command "insert" "ped" '(209 -100) 1 1 0 )
(command "insert" "ped" '(210 -106) 1 1 0 )
(command "insert" "ped" '(229 -105) 1 1 0 )
(command "insert" "ped" '(230 -105) 1 1 0 )
(command "insert" "ped" '(237 -98) 1 1 0 )
(command "insert" "ped" '(288 -90) 1 1 0 )
(command "insert" "ped" '(270 -94) 1 1 0 )
(command "insert" "ped" '(254 -99) 1 1 0 )
(command "insert" "ped" '(189 -95) 1 1 0 )
(command "insert" "ped" '(231 -103) 1 1 0 )
(command "insert" "ped" '(188 -92) 1 1 0 )
(command "insert" "ped" '(193 -99) 1 1 0 )
(command "insert" "ped" '(261 -97) 1 1 0 )
(command "insert" "ped" '(280 -86) 1 1 0 )
(command "insert" "ped" '(184 -94) 1 1 0 )
(command "insert" "ped" '(211 -102) 1 1 0 )
(command "insert" "ped" '(186 -92) 1 1 0 )
(command "insert" "ped" '(192 -103) 1 1 0 )
(command "insert" "ped" '(243 -101) 1 1 0 )
(command "insert" "ped" '(212 -106) 1 1 0 )
(command "insert" "ped" '(213 -100) 1 1 0 )
(command "insert" "ped" '(280 -98) 1 1 0 )
(command "insert" "ped" '(224 -100) 1 1 0 )
(command "insert" "ped" '(187 -104) 1 1 0 )
(command "insert" "ped" '(188 -90) 1 1 0 )
(command "insert" "ped" '(194 -101) 1 1 0 )
(command "insert" "ped" '(201 -102) 1 1 0 )
(command "insert" "ped" '(214 -96) 1 1 0 )
(command "insert" "ped" '(208 -103) 1 1 0 )
(command "insert" "ped" '(228 -106) 1 1 0 )
(command "insert" "ped" '(191 -102) 1 1 0 )
(command "insert" "ped" '(226 -102) 1 1 0 )
(command "insert" "ped" '(261 -106) 1 1 0 )
(command "insert" "ped" '(262 -104) 1 1 0 )
(command "insert" "ped" '(202 -106) 1 1 0 )
(command "insert" "ped" '(203 -104) 1 1 0 )
(command "insert" "ped" '(250 -96) 1 1 0 )
(command "insert" "ped" '(210 -101) 1 1 0 )
(command "insert" "ped" '(223 -101) 1 1 0 )
(command "insert" "ped" '(276 -94) 1 1 0 )
(command "insert" "ped" '(263 -100) 1 1 0 )
(command "insert" "ped" '(254 -106) 1 1 0 )
(command "insert" "ped" '(257 -100) 1 1 0 )
(command "insert" "ped" '(256 -103) 1 1 0 )
(command "insert" "ped" '(236 -105) 1 1 0 )
(command "insert" "ped" '(234 -100) 1 1 0 )
(command "insert" "ped" '(264 -105) 1 1 0 )
(command "insert" "ped" '(280 -93) 1 1 0 )
(command "insert" "ped" '(214 -100) 1 1 0 )
(command "insert" "ped" '(265 -95) 1 1 0 )
(command "insert" "ped" '(209 -103) 1 1 0 )
(command "insert" "ped" '(184 -101) 1 1 0 )
(command "insert" "ped" '(207 -106) 1 1 0 )
(command "insert" "ped" '(267 -93) 1 1 0 )
(command "insert" "ped" '(282 -95) 1 1 0 )
(command "insert" "ped" '(186 -103) 1 1 0 )
(command "insert" "ped" '(256 -99) 1 1 0 )
(command "insert" "ped" '(269 -95) 1 1 0 )
(command "insert" "ped" '(259 -102) 1 1 0 )
(command "insert" "ped" '(183 -100) 1 1 0 )
(command "insert" "ped" '(190 -97) 1 1 0 )
(command "insert" "ped" '(187 -97) 1 1 0 )
(command "insert" "ped" '(197 -106) 1 1 0 )
(command "insert" "ped" '(245 -96) 1 1 0 )
(command "insert" "ped" '(215 -107) 1 1 0 )
(command "insert" "ped" '(278 -93) 1 1 0 )
(command "insert" "ped" '(189 -107) 1 1 0 )
(command "insert" "ped" '(199 -100) 1 1 0 )
(command "insert" "ped" '(248 -97) 1 1 0 )
(command "insert" "ped" '(279 -96) 1 1 0 )
(command "insert" "ped" '(209 -105) 1 1 0 )
(command "insert" "ped" '(199 -107) 1 1 0 )
(command "insert" "ped" '(227 -103) 1 1 0 )
(command "insert" "ped" '(199 -102) 1 1 0 )
(command "insert" "ped" '(225 -107) 1 1 0 )
(command "insert" "ped" '(289 -94) 1 1 0 )
(command "insert" "ped" '(205 -107) 1 1 0 )
(command "insert" "ped" '(252 -101) 1 1 0 )
(command "insert" "ped" '(209 -104) 1 1 0 )
(command "insert" "ped" '(196 -96) 1 1 0 )
(command "insert" "ped" '(214 -104) 1 1 0 )
(command "insert" "ped" '(229 -101) 1 1 0 )
(command "insert" "ped" '(246 -100) 1 1 0 )
(command "insert" "ped" '(240 -99) 1 1 0 )
(command "insert" "ped" '(218 -100) 1 1 0 )
(command "insert" "ped" '(281 -90) 1 1 0 )
(command "insert" "ped" '(207 -103) 1 1 0 )
(command "insert" "ped" '(261 -99) 1 1 0 )
(command "insert" "ped" '(283 -92) 1 1 0 )
(command "insert" "ped" '(217 -107) 1 1 0 )
(command "insert" "ped" '(198 -107) 1 1 0 )
(command "insert" "ped" '(216 -105) 1 1 0 )
(command "insert" "ped" '(240 -95) 1 1 0 )
(command "insert" "ped" '(230 -100) 1 1 0 )
(command "insert" "ped" '(285 -94) 1 1 0 )
(command "insert" "ped" '(276 -97) 1 1 0 )
(command "insert" "ped" '(218 -99) 1 1 0 )
(command "insert" "ped" '(190 -104) 1 1 0 )
(command "insert" "ped" '(187 -102) 1 1 0 )
(command "insert" "ped" '(188 -104) 1 1 0 )
(command "insert" "ped" '(185 -90) 1 1 0 )
(command "insert" "ped" '(198 -104) 1 1 0 )
(command "insert" "ped" '(242 -93) 1 1 0 )
(command "insert" "ped" '(215 -96) 1 1 0 )
(command "insert" "ped" '(212 -102) 1 1 0 )
(command "insert" "ped" '(222 -101) 1 1 0 )
(command "insert" "ped" '(219 -101) 1 1 0 )
(command "insert" "ped" '(263 -96) 1 1 0 )
(command "insert" "ped" '(189 -100) 1 1 0 )
(command "insert" "ped" '(224 -104) 1 1 0 )
(command "insert" "ped" '(187 -92) 1 1 0 )
(command "insert" "ped" '(266 -105) 1 1 0 )
(command "insert" "ped" '(200 -100) 1 1 0 )
(command "insert" "ped" '(251 -96) 1 1 0 )
(command "insert" "ped" '(223 -107) 1 1 0 )
(command "insert" "ped" '(208 -107) 1 1 0 )
(command "insert" "ped" '(221 -103) 1 1 0 )
(command "insert" "ped" '(228 -102) 1 1 0 )
(command "insert" "ped" '(235 -101) 1 1 0 )
(command "insert" "ped" '(261 -102) 1 1 0 )
(command "insert" "ped" '(202 -102) 1 1 0 )
(command "insert" "ped" '(253 -106) 1 1 0 )
(command "insert" "ped" '(279 -87) 1 1 0 )
(command "insert" "ped" '(264 -95) 1 1 0 )
(command "insert" "ped" '(194 -99) 1 1 0 )
(command "insert" "ped" '(266 -93) 1 1 0 )
(command "insert" "ped" '(231 -104) 1 1 0 )
(command "insert" "ped" '(242 -96) 1 1 0 )
(command "insert" "ped" '(209 -107) 1 1 0 )
(command "insert" "ped" '(183 -92) 1 1 0 )
(command "insert" "ped" '(214 -102) 1 1 0 )
(command "insert" "ped" '(195 -94) 1 1 0 )
(command "insert" "ped" '(207 -102) 1 1 0 )
(command "insert" "ped" '(211 -99) 1 1 0 )
(command "insert" "ped" '(288 -93) 1 1 0 )
(command "insert" "ped" '(196 -98) 1 1 0 )
(command "insert" "ped" '(259 -99) 1 1 0 )
(command "insert" "ped" '(188 -103) 1 1 0 )
(command "insert" "ped" '(185 -99) 1 1 0 )
(command "insert" "ped" '(195 -100) 1 1 0 )
(command "insert" "ped" '(192 -98) 1 1 0 )
(command "insert" "ped" '(220 -100) 1 1 0 )
(command "insert" "ped" '(262 -93) 1 1 0 )
(command "insert" "ped" '(196 -104) 1 1 0 )
(command "insert" "ped" '(188 -93) 1 1 0 )
(command "insert" "ped" '(244 -98) 1 1 0 )
(command "insert" "ped" '(200 -107) 1 1 0 )
(command "insert" "ped" '(248 -101) 1 1 0 )
(command "insert" "ped" '(225 -101) 1 1 0 )
(command "insert" "ped" '(232 -104) 1 1 0 )
(command "insert" "ped" '(190 -95) 1 1 0 )
(command "insert" "ped" '(261 -104) 1 1 0 )
(command "insert" "ped" '(265 -100) 1 1 0 )
(command "insert" "ped" '(253 -99) 1 1 0 )
(command "insert" "ped" '(210 -104) 1 1 0 )
(command "insert" "ped" '(233 -103) 1 1 0 )
(command "insert" "ped" '(254 -105) 1 1 0 )
(command "insert" "ped" '(237 -96) 1 1 0 )
(command "insert" "ped" '(263 -105) 1 1 0 )
(command "insert" "ped" '(241 -101) 1 1 0 )
(command "insert" "ped" '(233 -106) 1 1 0 )
(command "insert" "ped" '(290 -94) 1 1 0 )
(command "insert" "ped" '(266 -101) 1 1 0 )
(command "insert" "ped" '(195 -107) 1 1 0 )
(command "insert" "ped" '(222 -107) 1 1 0 )
(command "insert" "ped" '(280 -88) 1 1 0 )
(command "insert" "ped" '(248 -96) 1 1 0 )
(command "insert" "ped" '(184 -96) 1 1 0 )
(command "insert" "ped" '(261 -101) 1 1 0 )
(command "insert" "ped" '(211 -104) 1 1 0 )
(command "insert" "ped" '(185 -100) 1 1 0 )
(command "insert" "ped" '(186 -90) 1 1 0 )
(command "insert" "ped" '(284 -92) 1 1 0 )
(command "insert" "ped" '(213 -98) 1 1 0 )
(command "insert" "ped" '(220 -99) 1 1 0 )
(command "insert" "ped" '(217 -103) 1 1 0 )
(command "insert" "ped" '(224 -102) 1 1 0 )
(command "insert" "ped" '(257 -102) 1 1 0 )
(command "insert" "ped" '(245 -101) 1 1 0 )
(command "insert" "ped" '(264 -103) 1 1 0 )
(command "insert" "ped" '(253 -105) 1 1 0 )
(command "insert" "ped" '(249 -98) 1 1 0 )
(command "insert" "ped" '(219 -105) 1 1 0 )
(command "insert" "ped" '(191 -96) 1 1 0 )
(command "insert" "ped" '(226 -100) 1 1 0 )
(command "insert" "ped" '(198 -101) 1 1 0 )
(command "insert" "ped" '(199 -105) 1 1 0 )
(command "insert" "ped" '(246 -99) 1 1 0 )
(command "insert" "ped" '(202 -104) 1 1 0 )
(command "insert" "ped" '(203 -106) 1 1 0 )
(command "insert" "ped" '(235 -105) 1 1 0 )
(command "insert" "ped" '(210 -99) 1 1 0 )
(command "insert" "ped" '(286 -96) 1 1 0 )
(command "insert" "ped" '(230 -102) 1 1 0 )
(command "insert" "ped" '(263 -102) 1 1 0 )
(command "insert" "ped" '(289 -91) 1 1 0 )
(command "insert" "ped" '(204 -102) 1 1 0 )
(command "insert" "ped" '(254 -104) 1 1 0 )
(command "insert" "ped" '(212 -101) 1 1 0 )
(command "insert" "ped" '(262 -97) 1 1 0 )
(command "insert" "ped" '(236 -107) 1 1 0 )
(command "insert" "ped" '(197 -97) 1 1 0 )
(command "insert" "ped" '(252 -104) 1 1 0 )
(command "insert" "ped" '(280 -95) 1 1 0 )
(command "insert" "ped" '(281 -87) 1 1 0 )
(command "insert" "ped" '(287 -94) 1 1 0 )
(command "insert" "ped" '(264 -101) 1 1 0 )
(command "insert" "ped" '(282 -93) 1 1 0 )
(command "insert" "ped" '(216 -100) 1 1 0 )
(command "insert" "ped" '(186 -101) 1 1 0 )
(command "insert" "ped" '(193 -102) 1 1 0 )
(command "insert" "ped" '(269 -93) 1 1 0 )
(command "insert" "ped" '(284 -91) 1 1 0 )
(command "insert" "ped" '(241 -93) 1 1 0 )
(command "insert" "ped" '(217 -104) 1 1 0 )
(command "insert" "ped" '(187 -93) 1 1 0 )
(command "insert" "ped" '(190 -103) 1 1 0 )
(command "insert" "ped" '(196 -94) 1 1 0 )
(command "insert" "ped" '(197 -104) 1 1 0 )
(command "insert" "ped" '(258 -103) 1 1 0 )
(command "insert" "ped" '(215 -101) 1 1 0 )
(command "insert" "ped" '(286 -94) 1 1 0 )
(command "insert" "ped" '(282 -97) 1 1 0 )
(command "insert" "ped" '(191 -105) 1 1 0 )
(command "insert" "ped" '(189 -105) 1 1 0 )
(command "insert" "ped" '(233 -104) 1 1 0 )
(command "insert" "ped" '(196 -100) 1 1 0 )
(command "insert" "ped" '(200 -99) 1 1 0 )
(command "insert" "ped" '(279 -98) 1 1 0 )
(command "insert" "ped" '(273 -95) 1 1 0 )
(command "insert" "ped" '(277 -94) 1 1 0 )
(command "insert" "ped" '(277 -98) 1 1 0 )
(command "insert" "ped" '(227 -105) 1 1 0 )
(command "insert" "ped" '(225 -105) 1 1 0 )
(command "insert" "ped" '(289 -92) 1 1 0 )
(command "insert" "ped" '(279 -85) 1 1 0 )
(command "insert" "ped" '(256 -107) 1 1 0 )
(command "insert" "ped" '(198 -103) 1 1 0 )
(command "insert" "ped" '(252 -103) 1 1 0 )
(command "insert" "ped" '(279 -88) 1 1 0 )
(command "insert" "ped" '(208 -106) 1 1 0 )
(command "insert" "ped" '(191 -93) 1 1 0 )
(command "insert" "ped" '(240 -101) 1 1 0 )
(command "insert" "ped" '(281 -88) 1 1 0 )
(command "insert" "ped" '(266 -103) 1 1 0 )
(command "insert" "ped" '(186 -94) 1 1 0 )
(command "insert" "ped" '(268 -94) 1 1 0 )
(command "insert" "ped" '(283 -94) 1 1 0 )
(command "insert" "ped" '(272 -94) 1 1 0 )
(command "insert" "ped" '(216 -107) 1 1 0 )
(command "insert" "ped" '(273 -96) 1 1 0 )
(command "insert" "ped" '(243 -99) 1 1 0 )
(command "insert" "ped" '(206 -107) 1 1 0 )
(command "insert" "ped" '(285 -92) 1 1 0 )
(command "insert" "ped" '(198 -106) 1 1 0 )
(command "insert" "ped" '(238 -100) 1 1 0 )
(command "insert" "ped" '(195 -97) 1 1 0 )
(command "insert" "ped" '(271 -96) 1 1 0 )
(command "insert" "ped" '(183 -91) 1 1 0 )
(command "insert" "ped" '(276 -93) 1 1 0 )
(command "insert" "ped" '(219 -103) 1 1 0 )
(command "insert" "ped" '(189 -98) 1 1 0 )
(command "insert" "ped" '(224 -106) 1 1 0 )
(command "insert" "ped" '(196 -99) 1 1 0 )
(command "insert" "ped" '(247 -97) 1 1 0 )
(command "insert" "ped" '(244 -101) 1 1 0 )
(command "insert" "ped" '(200 -102) 1 1 0 )
(command "insert" "ped" '(251 -98) 1 1 0 )
(command "insert" "ped" '(214 -106) 1 1 0 )
(command "insert" "ped" '(287 -96) 1 1 0 )
(command "insert" "ped" '(220 -103) 1 1 0 )
(command "insert" "ped" '(235 -103) 1 1 0 )
(command "insert" "ped" '(198 -105) 1 1 0 )
(command "insert" "ped" '(242 -94) 1 1 0 )
(command "insert" "ped" '(255 -104) 1 1 0 )
(command "insert" "ped" '(253 -104) 1 1 0 )
(command "insert" "ped" '(212 -103) 1 1 0 )
(command "insert" "ped" '(187 -101) 1 1 0 )
(command "insert" "ped" '(230 -106) 1 1 0 )
(command "insert" "ped" '(237 -101) 1 1 0 )
(command "insert" "ped" '(215 -103) 1 1 0 )
(command "insert" "ped" '(241 -98) 1 1 0 )
(command "insert" "ped" '(231 -106) 1 1 0 )
(command "insert" "ped" '(267 -95) 1 1 0 )
(command "insert" "ped" '(183 -94) 1 1 0 )
(command "insert" "ped" '(197 -102) 1 1 0 )
(command "insert" "ped" '(184 -91) 1 1 0 )
(command "insert" "ped" '(260 -102) 1 1 0 )
(command "insert" "ped" '(241 -94) 1 1 0 )
(command "insert" "ped" '(211 -101) 1 1 0 )
(command "insert" "ped" '(218 -104) 1 1 0 )
(command "insert" "ped" '(286 -90) 1 1 0 )
(command "insert" "ped" '(188 -97) 1 1 0 )
(command "insert" "ped" '(185 -97) 1 1 0 )
(command "insert" "ped" '(195 -102) 1 1 0 )
(command "insert" "ped" '(192 -100) 1 1 0 )
(command "insert" "ped" '(256 -105) 1 1 0 )
(command "insert" "ped" '(213 -103) 1 1 0 )
(command "insert" "ped" '(220 -102) 1 1 0 )
(command "insert" "ped" '(196 -102) 1 1 0 )
(command "insert" "ped" '(196 -106) 1 1 0 )
(command "insert" "ped" '(197 -100) 1 1 0 )
(command "insert" "ped" '(194 -102) 1 1 0 )
(command "insert" "ped" '(277 -96) 1 1 0 )
(command "insert" "ped" '(208 -100) 1 1 0 )
(command "insert" "ped" '(290 -91) 1 1 0 )
(command "insert" "ped" '(191 -101) 1 1 0 )
(command "insert" "ped" '(226 -107) 1 1 0 )
(command "insert" "ped" '(272 -98) 1 1 0 )
(command "insert" "ped" '(190 -93) 1 1 0 )
(command "insert" "ped" '(265 -106) 1 1 0 )
(command "insert" "ped" '(250 -101) 1 1 0 )
(command "insert" "ped" '(210 -102) 1 1 0 )
(command "insert" "ped" '(263 -107) 1 1 0 )
(command "insert" "ped" '(254 -103) 1 1 0 )
(command "insert" "ped" '(274 -97) 1 1 0 )
(command "insert" "ped" '(231 -99) 1 1 0 )
(command "insert" "ped" '(262 -106) 1 1 0 )
(command "insert" "ped" '(290 -92) 1 1 0 )
(command "insert" "ped" '(213 -107) 1 1 0 )
(command "insert" "ped" '(280 -90) 1 1 0 )
(command "insert" "ped" '(184 -98) 1 1 0 )
(command "insert" "ped" '(207 -105) 1 1 0 )
(command "insert" "ped" '(211 -106) 1 1 0 )
(command "insert" "ped" '(273 -98) 1 1 0 )
(command "insert" "ped" '(243 -97) 1 1 0 )
(command "insert" "ped" '(284 -94) 1 1 0 )
(command "insert" "ped" '(213 -96) 1 1 0 )
(command "insert" "ped" '(217 -101) 1 1 0 )
(command "insert" "ped" '(190 -98) 1 1 0 )
(command "insert" "ped" '(194 -97) 1 1 0 )
(command "insert" "ped" '(245 -99) 1 1 0 )
(command "insert" "ped" '(201 -106) 1 1 0 )
(command "insert" "ped" '(286 -92) 1 1 0 )
(command "insert" "ped" '(249 -96) 1 1 0 )
(command "insert" "ped" '(285 -98) 1 1 0 )
(command "insert" "ped" '(219 -107) 1 1 0 )
(command "insert" "ped" '(191 -98) 1 1 0 )
(command "insert" "ped" '(260 -104) 1 1 0 )
(command "insert" "ped" '(239 -100) 1 1 0 )
(command "insert" "ped" '(233 -101) 1 1 0 )
(command "insert" "ped" '(246 -97) 1 1 0 )
(command "insert" "ped" '(266 -99) 1 1 0 )
(command "insert" "ped" '(283 -96) 1 1 0 )
(command "insert" "ped" '(234 -107) 1 1 0 )
(command "insert" "ped" '(235 -107) 1 1 0 )
(command "insert" "ped" '(255 -100) 1 1 0 )
(command "insert" "ped" '(252 -106) 1 1 0 )
(command "insert" "ped" '(279 -93) 1 1 0 )
(command "insert" "ped" '(236 -101) 1 1 0 )
(command "insert" "ped" '(278 -98) 1 1 0 )
(command "insert" "ped" '(215 -98) 1 1 0 )
(command "insert" "ped" '(254 -100) 1 1 0 )
(command "insert" "ped" '(281 -85) 1 1 0 )
(command "insert" "ped" '(197 -101) 1 1 0 )
(command "insert" "ped" '(282 -91) 1 1 0 )
(command "insert" "ped" '(283 -91) 1 1 0 )
(command "insert" "ped" '(186 -104) 1 1 0 )
(command "insert" "ped" '(216 -102) 1 1 0 )
(command "insert" "ped" '(186 -99) 1 1 0 )
(command "insert" "ped" '(193 -100) 1 1 0 )
(command "insert" "ped" '(206 -102) 1 1 0 )
(command "insert" "ped" '(213 -105) 1 1 0 )
(command "insert" "ped" '(183 -96) 1 1 0 )
(command "insert" "ped" '(281 -97) 1 1 0 )
(command "insert" "ped" '(190 -101) 1 1 0 )
(command "insert" "ped" '(239 -99) 1 1 0 )
(command "insert" "ped" '(238 -99) 1 1 0 )
(command "insert" "ped" '(258 -101) 1 1 0 )
(command "insert" "ped" '(192 -104) 1 1 0 )
(command "insert" "ped" '(278 -96) 1 1 0 )
(command "insert" "ped" '(275 -94) 1 1 0 )
(command "insert" "ped" '(222 -102) 1 1 0 )
(command "insert" "ped" '(191 -107) 1 1 0 )
(command "insert" "ped" '(189 -103) 1 1 0 )
(command "insert" "ped" '(262 -103) 1 1 0 )
(command "insert" "ped" '(187 -91) 1 1 0 )
(command "insert" "ped" '(234 -105) 1 1 0 )
(command "insert" "ped" '(266 -106) 1 1 0 )
(command "insert" "ped" '(273 -93) 1 1 0 )
(command "insert" "ped" '(208 -104) 1 1 0 )
(command "insert" "ped" '(221 -106) 1 1 0 )
(command "insert" "ped" '(227 -107) 1 1 0 )
(command "insert" "ped" '(205 -103) 1 1 0 )
(command "insert" "ped" '(279 -90) 1 1 0 )
(command "insert" "ped" '(193 -96) 1 1 0 )
(command "insert" "ped" '(232 -105) 1 1 0 )
(command "insert" "ped" '(266 -94) 1 1 0 )
(command "insert" "ped" '(281 -94) 1 1 0 )
(command "insert" "ped" '(183 -101) 1 1 0 )
(command "insert" "ped" '(261 -93) 1 1 0 )
(command "insert" "ped" '(242 -101) 1 1 0 )
(command "insert" "ped" '(287 -97) 1 1 0 )
(command "insert" "ped" '(197 -93) 1 1 0 )
(command "insert" "ped" '(260 -107) 1 1 0 )
(command "insert" "ped" '(195 -93) 1 1 0 )
(command "insert" "ped" '(259 -103) 1 1 0 )
(command "insert" "ped" '(206 -105) 1 1 0 )
(command "insert" "ped" '(207 -101) 1 1 0 )
(command "insert" "ped" '(285 -90) 1 1 0 )
(command "insert" "ped" '(271 -94) 1 1 0 )
(command "insert" "ped" '(263 -95) 1 1 0 )
(command "insert" "ped" '(217 -106) 1 1 0 )
(command "insert" "ped" '(188 -100) 1 1 0 )
(command "insert" "ped" '(185 -94) 1 1 0 )
(command "insert" "ped" '(256 -101) 1 1 0 )
(command "insert" "ped" '(271 -98) 1 1 0 )
(command "insert" "ped" '(276 -95) 1 1 0 )
(command "insert" "ped" '(220 -105) 1 1 0 )
(command "insert" "ped" '(256 -106) 1 1 0 )
(command "insert" "ped" '(189 -96) 1 1 0 )
(command "insert" "ped" '(262 -94) 1 1 0 )
(command "insert" "ped" '(259 -104) 1 1 0 )
(command "insert" "ped" '(247 -99) 1 1 0 )
(command "insert" "ped" '(257 -104) 1 1 0 )
(command "insert" "ped" '(200 -104) 1 1 0 )
(command "insert" "ped" '(251 -100) 1 1 0 )
(command "insert" "ped" '(248 -98) 1 1 0 )
(command "insert" "ped" '(287 -98) 1 1 0 )
(command "insert" "ped" '(221 -99) 1 1 0 )
(command "insert" "ped" '(260 -105) 1 1 0 )
(command "insert" "ped" '(232 -101) 1 1 0 )
(command "insert" "ped" '(255 -106) 1 1 0 )
(command "insert" "ped" '(265 -103) 1 1 0 )
(command "insert" "ped" '(253 -102) 1 1 0 )
(command "insert" "ped" '(209 -101) 1 1 0 )
(command "insert" "ped" '(229 -106) 1 1 0 )
(command "insert" "ped" '(258 -105) 1 1 0 )
(command "insert" "ped" '(237 -99) 1 1 0 )
(command "insert" "ped" '(234 -103) 1 1 0 )
(command "insert" "ped" '(263 -104) 1 1 0 )
(command "insert" "ped" '(241 -96) 1 1 0 )
(command "insert" "ped" '(231 -100) 1 1 0 )
(command "insert" "ped" '(270 -93) 1 1 0 )
(command "insert" "ped" '(249 -101) 1 1 0 )
(command "insert" "ped" '(229 -99) 1 1 0 )
(command "insert" "ped" '(280 -85) 1 1 0 )
(command "insert" "ped" '(218 -106) 1 1 0 )
(command "insert" "ped" '(223 -103) 1 1 0 )
(command "insert" "ped" '(197 -103) 1 1 0 )
(command "insert" "ped" '(184 -93) 1 1 0 )
(command "insert" "ped" '(211 -103) 1 1 0 )
(command "insert" "ped" '(188 -99) 1 1 0 )
(command "insert" "ped" '(186 -95) 1 1 0 )
(command "insert" "ped" '(192 -102) 1 1 0 )
(command "insert" "ped" '(243 -98) 1 1 0 )
(command "insert" "ped" '(212 -105) 1 1 0 )
(command "insert" "ped" '(213 -101) 1 1 0 )
(command "insert" "ped" '(218 -102) 1 1 0 )
(command "insert" "ped" '(280 -97) 1 1 0 )
(command "insert" "ped" '(224 -99) 1 1 0 )
(command "insert" "ped" '(239 -97) 1 1 0 )
(command "insert" "ped" '(197 -98) 1 1 0 )
(command "insert" "ped" '(194 -100) 1 1 0 )
(command "insert" "ped" '(201 -103) 1 1 0 )
(command "insert" "ped" '(286 -91) 1 1 0 )
(command "insert" "ped" '(262 -99) 1 1 0 )
(command "insert" "ped" '(270 -98) 1 1 0 )
(command "insert" "ped" '(228 -105) 1 1 0 )
(command "insert" "ped" '(191 -103) 1 1 0 )
(command "insert" "ped" '(226 -105) 1 1 0 )
(command "insert" "ped" '(198 -102) 1 1 0 )
(command "insert" "ped" '(262 -107) 1 1 0 )
(command "insert" "ped" '(265 -104) 1 1 0 )
(command "insert" "ped" '(203 -105) 1 1 0 )
(command "insert" "ped" '(250 -99) 1 1 0 )
(command "insert" "ped" '(210 -100) 1 1 0 )
(command "insert" "ped" '(188 -95) 1 1 0 )
(command "insert" "ped" '(230 -99) 1 1 0 )
(command "insert" "ped" '(263 -101) 1 1 0 )
(command "insert" "ped" '(240 -96) 1 1 0 )
(command "insert" "ped" '(254 -101) 1 1 0 )
(command "insert" "ped" '(274 -95) 1 1 0 )
(command "insert" "ped" '(290 -90) 1 1 0 )
(command "insert" "ped" '(232 -103) 1 1 0 )
(command "insert" "ped" '(280 -92) 1 1 0 )
(command "insert" "ped" '(190 -94) 1 1 0 )
(command "insert" "ped" '(184 -100) 1 1 0 )
(command "insert" "ped" '(207 -107) 1 1 0 )
(command "insert" "ped" '(197 -95) 1 1 0 )
(command "insert" "ped" '(186 -102) 1 1 0 )
(command "insert" "ped" '(193 -97) 1 1 0 )
(command "insert" "ped" '(195 -99) 1 1 0 )
(command "insert" "ped" '(272 -97) 1 1 0 )
(command "insert" "ped" '(263 -93) 1 1 0 )
(command "insert" "ped" '(190 -96) 1 1 0 )
(command "insert" "ped" '(197 -107) 1 1 0 )
(command "insert" "ped" '(258 -104) 1 1 0 )
(command "insert" "ped" '(201 -104) 1 1 0 )
(command "insert" "ped" '(215 -104) 1 1 0 )
(command "insert" "ped" '(285 -96) 1 1 0 )
(command "insert" "ped" '(282 -98) 1 1 0 )
(command "insert" "ped" '(233 -107) 1 1 0 )
(command "insert" "ped" '(279 -97) 1 1 0 )
(command "insert" "ped" '(223 -99) 1 1 0 )
(command "insert" "ped" '(227 -100) 1 1 0 )
(command "insert" "ped" '(222 -105) 1 1 0 )
(command "insert" "ped" '(263 -98) 1 1 0 )
(command "insert" "ped" '(289 -95) 1 1 0 )
(command "insert" "ped" '(287 -93) 1 1 0 )
(command "insert" "ped" '(280 -96) 1 1 0 )
(command "insert" "ped" '(255 -102) 1 1 0 )
(command "insert" "ped" '(281 -98) 1 1 0 )
(command "insert" "ped" '(279 -95) 1 1 0 )
(command "insert" "ped" '(229 -102) 1 1 0 )
(command "insert" "ped" '(258 -107) 1 1 0 )
(command "insert" "ped" '(236 -103) 1 1 0 )
(command "insert" "ped" '(279 -94) 1 1 0 )
(command "insert" "ped" '(264 -106) 1 1 0 )
(command "insert" "ped" '(265 -93) 1 1 0 )
(command "insert" "ped" '(281 -91) 1 1 0 )
(command "insert" "ped" '(286 -93) 1 1 0 )
(command "insert" "ped" '(283 -93) 1 1 0 )
(command "insert" "ped" '(216 -104) 1 1 0 )
(command "insert" "ped" '(186 -97) 1 1 0 )
(command "insert" "ped" '(240 -94) 1 1 0 )
(command "insert" "ped" '(285 -95) 1 1 0 )
(command "insert" "ped" '(183 -98) 1 1 0 )
(command "insert" "ped" '(190 -107) 1 1 0 )
(command "insert" "ped" '(187 -103) 1 1 0 )
(command "insert" "ped" '(238 -97) 1 1 0 )
(command "insert" "ped" '(185 -91) 1 1 0 )
(command "insert" "ped" '(258 -99) 1 1 0 )
(command "insert" "ped" '(192 -106) 1 1 0 )
(command "insert" "ped" '(215 -97) 1 1 0 )
(command "insert" "ped" '(275 -96) 1 1 0 )
(command "insert" "ped" '(222 -100) 1 1 0 )
(command "insert" "ped" '(189 -101) 1 1 0 )
(command "insert" "ped" '(262 -101) 1 1 0 )
(command "insert" "ped" '(259 -101) 1 1 0 )
(command "insert" "ped" '(247 -100) 1 1 0 )
(command "insert" "ped" '(258 -106) 1 1 0 )
(command "insert" "ped" '(244 -99) 1 1 0 )
(command "insert" "ped" '(251 -97) 1 1 0 )
(command "insert" "ped" '(223 -104) 1 1 0 )
(command "insert" "ped" '(199 -106) 1 1 0 )
(command "insert" "ped" '(221 -104) 1 1 0 )
(command "insert" "ped" '(228 -101) 1 1 0 )
(command "insert" "ped" '(215 -99) 1 1 0 )
(command "insert" "ped" '(261 -103) 1 1 0 )
(command "insert" "ped" '(252 -99) 1 1 0 )
(command "insert" "ped" '(253 -107) 1 1 0 )
(command "insert" "ped" '(279 -84) 1 1 0 )
(command "insert" "ped" '(264 -94) 1 1 0 )
(command "insert" "ped" '(193 -101) 1 1 0 )
(command "insert" "ped" '(193 -104) 1 1 0 )
(command "insert" "ped" '(281 -92) 1 1 0 )
(command "insert" "ped" '(231 -105) 1 1 0 )
(command "insert" "ped" '(242 -99) 1 1 0 )
(command "insert" "ped" '(260 -106) 1 1 0 )
(command "insert" "ped" '(261 -98) 1 1 0 )
(command "insert" "ped" '(183 -93) 1 1 0 )
(command "insert" "ped" '(195 -95) 1 1 0 )
(command "insert" "ped" '(270 -96) 1 1 0 )
(command "insert" "ped" '(276 -98) 1 1 0 )
(command "insert" "ped" '(188 -102) 1 1 0 )
(command "insert" "ped" '(185 -92) 1 1 0 )
(command "insert" "ped" '(195 -101) 1 1 0 )
(command "insert" "ped" '(192 -97) 1 1 0 )
(command "insert" "ped" '(280 -87) 1 1 0 )
(command "insert" "ped" '(220 -107) 1 1 0 )
(command "insert" "ped" '(263 -99) 1 1 0 )
(command "insert" "ped" '(259 -106) 1 1 0 )
(command "insert" "ped" '(260 -100) 1 1 0 )
(command "insert" "ped" '(194 -107) 1 1 0 )
(command "insert" "ped" '(200 -106) 1 1 0 )
(command "insert" "ped" '(286 -98) 1 1 0 )
(command "insert" "ped" '(248 -100) 1 1 0 )
(command "insert" "ped" '(284 -98) 1 1 0 )
(command "insert" "ped" '(253 -100) 1 1 0 )
(command "insert" "ped" '(225 -102) 1 1 0 )
(command "insert" "ped" '(287 -90) 1 1 0 )
(command "insert" "ped" '(261 -96) 1 1 0 )
(command "insert" "ped" '(232 -99) 1 1 0 )
(command "insert" "ped" '(265 -101) 1 1 0 )
(command "insert" "ped" '(271 -95) 1 1 0 )
(command "insert" "ped" '(210 -107) 1 1 0 )
(command "insert" "ped" '(229 -104) 1 1 0 )
(command "insert" "ped" '(230 -104) 1 1 0 )
(command "insert" "ped" '(266 -104) 1 1 0 )
(command "insert" "ped" '(237 -97) 1 1 0 )
(command "insert" "ped" '(234 -101) 1 1 0 )
(command "insert" "ped" '(270 -95) 1 1 0 )
(command "insert" "ped" '(261 -105) 1 1 0 )
(command "insert" "ped" '(257 -101) 1 1 0 )
(command "insert" "ped" '(191 -95) 1 1 0 )
(command "insert" "ped" '(231 -102) 1 1 0 )
(command "insert" "ped" '(284 -96) 1 1 0 )
(command "insert" "ped" '(261 -100) 1 1 0 )
(command "insert" "ped" '(259 -100) 1 1 0 )
(command "insert" "ped" '(260 -103) 1 1 0 )
(command "insert" "ped" '(279 -92) 1 1 0 )
(command "insert" "ped" '(264 -104) 1 1 0 )
(command "insert" "ped" '(183 -90) 1 1 0 )
(command "insert" "ped" '(281 -96) 1 1 0 )
(command "insert" "ped" '(286 -95) 1 1 0 )
(command "insert" "ped" '(256 -100) 1 1 0 )
(command "insert" "ped" '(184 -95) 1 1 0 )
(command "layer" "m" "mroads" "" )
(command "insert" "mroads" '(222 -76) 1 1 0 )
(command "insert" "mroads" '(209 -41) 1 1 0 )
(command "insert" "mroads" '(247 -92) 1 1 0 )
(command "insert" "mroads" '(203 -63) 1 1 0 )
(command "insert" "mroads" '(208 -66) 1 1 0 )
(command "insert" "mroads" '(202 -62) 1 1 0 )
(command "insert" "mroads" '(231 -48) 1 1 0 )
(command "insert" "mroads" '(205 -61) 1 1 0 )
(command "insert" "mroads" '(271 -64) 1 1 0 )
(command "insert" "mroads" '(207 -59) 1 1 0 )
(command "insert" "mroads" '(274 -67) 1 1 0 )
(command "insert" "mroads" '(185 -49) 1 1 0 )
(command "insert" "mroads" '(175 -34) 1 1 0 )
(command "insert" "mroads" '(196 -48) 1 1 0 )
(command "insert" "mroads" '(206 -36) 1 1 0 )
(command "insert" "mroads" '(237 -90) 1 1 0 )
(command "insert" "mroads" '(193 -49) 1 1 0 )
(command "insert" "mroads" '(183 -34) 1 1 0 )
(command "insert" "mroads" '(253 -87) 1 1 0 )
(command "insert" "mroads" '(218 -43) 1 1 0 )
(command "insert" "mroads" '(238 -46) 1 1 0 )
(command "insert" "mroads" '(195 -39) 1 1 0 )
(command "insert" "mroads" '(225 -75) 1 1 0 )
(command "insert" "mroads" '(189 -37) 1 1 0 )
(command "insert" "mroads" '(172 -35) 1 1 0 )
(command "insert" "mroads" '(265 -90) 1 1 0 )
(command "insert" "mroads" '(250 -53) 1 1 0 )
(command "insert" "mroads" '(197 -37) 1 1 0 )
(command "insert" "mroads" '(245 -91) 1 1 0 )
(command "insert" "mroads" '(191 -51) 1 1 0 )
(command "insert" "mroads" '(267 -92) 1 1 0 )
(command "insert" "mroads" '(178 -36) 1 1 0 )
(command "insert" "mroads" '(217 -71) 1 1 0 )
(command "insert" "mroads" '(199 -51) 1 1 0 )
(command "insert" "mroads" '(229 -47) 1 1 0 )
(command "insert" "mroads" '(203 -52) 1 1 0 )
(command "insert" "mroads" '(208 -57) 1 1 0 )
(command "insert" "mroads" '(204 -56) 1 1 0 )
(command "insert" "mroads" '(205 -54) 1 1 0 )
(command "insert" "mroads" '(210 -67) 1 1 0 )
(command "insert" "mroads" '(168 -30) 1 1 0 )
(command "insert" "mroads" '(180 -38) 1 1 0 )
(command "insert" "mroads" '(184 -33) 1 1 0 )
(command "insert" "mroads" '(224 -72) 1 1 0 )
(command "insert" "mroads" '(268 -62) 1 1 0 )
(command "insert" "mroads" '(192 -33) 1 1 0 )
(command "insert" "mroads" '(238 -49) 1 1 0 )
(command "insert" "mroads" '(212 -44) 1 1 0 )
(command "insert" "mroads" '(258 -51) 1 1 0 )
(command "insert" "mroads" '(169 -33) 1 1 0 )
(command "insert" "mroads" '(225 -76) 1 1 0 )
(command "insert" "mroads" '(183 -37) 1 1 0 )
(command "insert" "mroads" '(246 -49) 1 1 0 )
(command "insert" "mroads" '(210 -71) 1 1 0 )
(command "insert" "mroads" '(166 -32) 1 1 0 )
(command "insert" "mroads" '(216 -68) 1 1 0 )
(command "insert" "mroads" '(227 -82) 1 1 0 )
(command "insert" "mroads" '(196 -53) 1 1 0 )
(command "insert" "mroads" '(218 -70) 1 1 0 )
(command "insert" "mroads" '(199 -40) 1 1 0 )
(command "insert" "mroads" '(164 -30) 1 1 0 )
(command "insert" "mroads" '(269 -87) 1 1 0 )
(command "insert" "mroads" '(273 -63) 1 1 0 )
(command "insert" "mroads" '(203 -40) 1 1 0 )
(command "insert" "mroads" '(261 -91) 1 1 0 )
(command "insert" "mroads" '(262 -91) 1 1 0 )
(command "insert" "mroads" '(194 -35) 1 1 0 )
(command "insert" "mroads" '(153 -28) 1 1 0 )
(command "insert" "mroads" '(206 -54) 1 1 0 )
(command "insert" "mroads" '(180 -45) 1 1 0 )
(command "insert" "mroads" '(184 -40) 1 1 0 )
(command "insert" "mroads" '(174 -31) 1 1 0 )
(command "insert" "mroads" '(239 -87) 1 1 0 )
(command "insert" "mroads" '(224 -79) 1 1 0 )
(command "insert" "mroads" '(187 -53) 1 1 0 )
(command "insert" "mroads" '(208 -61) 1 1 0 )
(command "insert" "mroads" '(182 -47) 1 1 0 )
(command "insert" "mroads" '(212 -43) 1 1 0 )
(command "insert" "mroads" '(186 -34) 1 1 0 )
(command "insert" "mroads" '(225 -69) 1 1 0 )
(command "insert" "mroads" '(226 -77) 1 1 0 )
(command "insert" "mroads" '(204 -51) 1 1 0 )
(command "insert" "mroads" '(202 -65) 1 1 0 )
(command "insert" "mroads" '(194 -34) 1 1 0 )
(command "insert" "mroads" '(188 -44) 1 1 0 )
(command "insert" "mroads" '(227 -91) 1 1 0 )
(command "insert" "mroads" '(191 -33) 1 1 0 )
(command "insert" "mroads" '(232 -46) 1 1 0 )
(command "insert" "mroads" '(152 -29) 1 1 0 )
(command "insert" "mroads" '(229 -81) 1 1 0 )
(command "insert" "mroads" '(177 -43) 1 1 0 )
(command "insert" "mroads" '(272 -59) 1 1 0 )
(command "insert" "mroads" '(208 -55) 1 1 0 )
(command "insert" "mroads" '(261 -51) 1 1 0 )
(command "insert" "mroads" '(154 -31) 1 1 0 )
(command "insert" "mroads" '(219 -71) 1 1 0 )
(command "insert" "mroads" '(202 -53) 1 1 0 )
(command "insert" "mroads" '(233 -49) 1 1 0 )
(command "insert" "mroads" '(205 -40) 1 1 0 )
(command "insert" "mroads" '(260 -88) 1 1 0 )
(command "insert" "mroads" '(205 -50) 1 1 0 )
(command "insert" "mroads" '(240 -45) 1 1 0 )
(command "insert" "mroads" '(221 -69) 1 1 0 )
(command "insert" "mroads" '(252 -50) 1 1 0 )
(command "insert" "mroads" '(242 -47) 1 1 0 )
(command "insert" "mroads" '(223 -83) 1 1 0 )
(command "insert" "mroads" '(206 -57) 1 1 0 )
(command "insert" "mroads" '(184 -47) 1 1 0 )
(command "insert" "mroads" '(239 -92) 1 1 0 )
(command "insert" "mroads" '(224 -70) 1 1 0 )
(command "insert" "mroads" '(151 -32) 1 1 0 )
(command "insert" "mroads" '(182 -38) 1 1 0 )
(command "insert" "mroads" '(275 -55) 1 1 0 )
(command "insert" "mroads" '(186 -45) 1 1 0 )
(command "insert" "mroads" '(159 -32) 1 1 0 )
(command "insert" "mroads" '(226 -68) 1 1 0 )
(command "insert" "mroads" '(189 -48) 1 1 0 )
(command "insert" "mroads" '(257 -56) 1 1 0 )
(command "insert" "mroads" '(197 -48) 1 1 0 )
(command "insert" "mroads" '(188 -43) 1 1 0 )
(command "insert" "mroads" '(228 -82) 1 1 0 )
(command "insert" "mroads" '(191 -46) 1 1 0 )
(command "insert" "mroads" '(249 -51) 1 1 0 )
(command "insert" "mroads" '(204 -70) 1 1 0 )
(command "insert" "mroads" '(190 -49) 1 1 0 )
(command "insert" "mroads" '(203 -65) 1 1 0 )
(command "insert" "mroads" '(229 -90) 1 1 0 )
(command "insert" "mroads" '(230 -88) 1 1 0 )
(command "insert" "mroads" '(177 -44) 1 1 0 )
(command "insert" "mroads" '(271 -67) 1 1 0 )
(command "insert" "mroads" '(225 -42) 1 1 0 )
(command "insert" "mroads" '(198 -49) 1 1 0 )
(command "insert" "mroads" '(220 -70) 1 1 0 )
(command "insert" "mroads" '(241 -50) 1 1 0 )
(command "insert" "mroads" '(210 -44) 1 1 0 )
(command "insert" "mroads" '(204 -58) 1 1 0 )
(command "insert" "mroads" '(222 -72) 1 1 0 )
(command "insert" "mroads" '(238 -91) 1 1 0 )
(command "insert" "mroads" '(223 -88) 1 1 0 )
(command "insert" "mroads" '(269 -61) 1 1 0 )
(command "insert" "mroads" '(227 -71) 1 1 0 )
(command "insert" "mroads" '(265 -55) 1 1 0 )
(command "insert" "mroads" '(271 -59) 1 1 0 )
(command "insert" "mroads" '(275 -60) 1 1 0 )
(command "insert" "mroads" '(186 -52) 1 1 0 )
(command "insert" "mroads" '(225 -87) 1 1 0 )
(command "insert" "mroads" '(194 -52) 1 1 0 )
(command "insert" "mroads" '(188 -34) 1 1 0 )
(command "insert" "mroads" '(227 -73) 1 1 0 )
(command "insert" "mroads" '(228 -89) 1 1 0 )
(command "insert" "mroads" '(204 -67) 1 1 0 )
(command "insert" "mroads" '(249 -52) 1 1 0 )
(command "insert" "mroads" '(196 -34) 1 1 0 )
(command "insert" "mroads" '(200 -37) 1 1 0 )
(command "insert" "mroads" '(173 -32) 1 1 0 )
(command "insert" "mroads" '(266 -52) 1 1 0 )
(command "insert" "mroads" '(230 -83) 1 1 0 )
(command "insert" "mroads" '(177 -37) 1 1 0 )
(command "insert" "mroads" '(269 -66) 1 1 0 )
(command "insert" "mroads" '(198 -40) 1 1 0 )
(command "insert" "mroads" '(202 -39) 1 1 0 )
(command "insert" "mroads" '(184 -37) 1 1 0 )
(command "insert" "mroads" '(210 -39) 1 1 0 )
(command "insert" "mroads" '(263 -51) 1 1 0 )
(command "insert" "mroads" '(240 -91) 1 1 0 )
(command "insert" "mroads" '(204 -49) 1 1 0 )
(command "insert" "mroads" '(209 -58) 1 1 0 )
(command "insert" "mroads" '(269 -54) 1 1 0 )
(command "insert" "mroads" '(267 -57) 1 1 0 )
(command "insert" "mroads" '(232 -87) 1 1 0 )
(command "insert" "mroads" '(224 -84) 1 1 0 )
(command "insert" "mroads" '(179 -39) 1 1 0 )
(command "insert" "mroads" '(227 -45) 1 1 0 )
(command "insert" "mroads" '(248 -90) 1 1 0 )
(command "insert" "mroads" '(226 -86) 1 1 0 )
(command "insert" "mroads" '(207 -40) 1 1 0 )
(command "insert" "mroads" '(181 -37) 1 1 0 )
(command "insert" "mroads" '(185 -34) 1 1 0 )
(command "insert" "mroads" '(241 -47) 1 1 0 )
(command "insert" "mroads" '(227 -78) 1 1 0 )
(command "insert" "mroads" '(193 -34) 1 1 0 )
(command "insert" "mroads" '(267 -65) 1 1 0 )
(command "insert" "mroads" '(205 -66) 1 1 0 )
(command "insert" "mroads" '(190 -35) 1 1 0 )
(command "insert" "mroads" '(229 -76) 1 1 0 )
(command "insert" "mroads" '(230 -74) 1 1 0 )
(command "insert" "mroads" '(195 -52) 1 1 0 )
(command "insert" "mroads" '(251 -51) 1 1 0 )
(command "insert" "mroads" '(206 -70) 1 1 0 )
(command "insert" "mroads" '(163 -31) 1 1 0 )
(command "insert" "mroads" '(202 -57) 1 1 0 )
(command "insert" "mroads" '(260 -53) 1 1 0 )
(command "insert" "mroads" '(226 -42) 1 1 0 )
(command "insert" "mroads" '(222 -70) 1 1 0 )
(command "insert" "mroads" '(209 -51) 1 1 0 )
(command "insert" "mroads" '(246 -88) 1 1 0 )
(command "insert" "mroads" '(262 -52) 1 1 0 )
(command "insert" "mroads" '(242 -88) 1 1 0 )
(command "insert" "mroads" '(223 -78) 1 1 0 )
(command "insert" "mroads" '(237 -48) 1 1 0 )
(command "insert" "mroads" '(211 -69) 1 1 0 )
(command "insert" "mroads" '(179 -44) 1 1 0 )
(command "insert" "mroads" '(205 -64) 1 1 0 )
(command "insert" "mroads" '(213 -71) 1 1 0 )
(command "insert" "mroads" '(234 -92) 1 1 0 )
(command "insert" "mroads" '(226 -81) 1 1 0 )
(command "insert" "mroads" '(270 -54) 1 1 0 )
(command "insert" "mroads" '(181 -46) 1 1 0 )
(command "insert" "mroads" '(185 -43) 1 1 0 )
(command "insert" "mroads" '(250 -91) 1 1 0 )
(command "insert" "mroads" '(251 -91) 1 1 0 )
(command "insert" "mroads" '(188 -48) 1 1 0 )
(command "insert" "mroads" '(236 -90) 1 1 0 )
(command "insert" "mroads" '(228 -79) 1 1 0 )
(command "insert" "mroads" '(256 -56) 1 1 0 )
(command "insert" "mroads" '(183 -40) 1 1 0 )
(command "insert" "mroads" '(213 -40) 1 1 0 )
(command "insert" "mroads" '(187 -45) 1 1 0 )
(command "insert" "mroads" '(230 -77) 1 1 0 )
(command "insert" "mroads" '(243 -87) 1 1 0 )
(command "insert" "mroads" '(207 -69) 1 1 0 )
(command "insert" "mroads" '(204 -55) 1 1 0 )
(command "insert" "mroads" '(202 -41) 1 1 0 )
(command "insert" "mroads" '(233 -45) 1 1 0 )
(command "insert" "mroads" '(244 -89) 1 1 0 )
(command "insert" "mroads" '(201 -52) 1 1 0 )
(command "insert" "mroads" '(222 -73) 1 1 0 )
(command "insert" "mroads" '(251 -53) 1 1 0 )
(command "insert" "mroads" '(209 -52) 1 1 0 )
(command "insert" "mroads" '(191 -36) 1 1 0 )
(command "insert" "mroads" '(266 -53) 1 1 0 )
(command "insert" "mroads" '(192 -48) 1 1 0 )
(command "insert" "mroads" '(206 -68) 1 1 0 )
(command "insert" "mroads" '(254 -51) 1 1 0 )
(command "insert" "mroads" '(214 -71) 1 1 0 )
(command "insert" "mroads" '(241 -46) 1 1 0 )
(command "insert" "mroads" '(233 -89) 1 1 0 )
(command "insert" "mroads" '(209 -69) 1 1 0 )
(command "insert" "mroads" '(196 -49) 1 1 0 )
(command "insert" "mroads" '(207 -62) 1 1 0 )
(command "insert" "mroads" '(274 -68) 1 1 0 )
(command "insert" "mroads" '(185 -44) 1 1 0 )
(command "insert" "mroads" '(175 -33) 1 1 0 )
(command "insert" "mroads" '(214 -68) 1 1 0 )
(command "insert" "mroads" '(183 -33) 1 1 0 )
(command "insert" "mroads" '(187 -34) 1 1 0 )
(command "insert" "mroads" '(200 -52) 1 1 0 )
(command "insert" "mroads" '(253 -90) 1 1 0 )
(command "insert" "mroads" '(218 -44) 1 1 0 )
(command "insert" "mroads" '(190 -45) 1 1 0 )
(command "insert" "mroads" '(164 -32) 1 1 0 )
(command "insert" "mroads" '(195 -34) 1 1 0 )
(command "insert" "mroads" '(243 -92) 1 1 0 )
(command "insert" "mroads" '(207 -66) 1 1 0 )
(command "insert" "mroads" '(172 -32) 1 1 0 )
(command "insert" "mroads" '(220 -42) 1 1 0 )
(command "insert" "mroads" '(176 -35) 1 1 0 )
(command "insert" "mroads" '(224 -45) 1 1 0 )
(command "insert" "mroads" '(223 -47) 1 1 0 )
(command "insert" "mroads" '(187 -35) 1 1 0 )
(command "insert" "mroads" '(201 -61) 1 1 0 )
(command "insert" "mroads" '(244 -92) 1 1 0 )
(command "insert" "mroads" '(267 -91) 1 1 0 )
(command "insert" "mroads" '(178 -41) 1 1 0 )
(command "insert" "mroads" '(217 -66) 1 1 0 )
(command "insert" "mroads" '(253 -91) 1 1 0 )
(command "insert" "mroads" '(247 -88) 1 1 0 )
(command "insert" "mroads" '(203 -51) 1 1 0 )
(command "insert" "mroads" '(208 -70) 1 1 0 )
(command "insert" "mroads" '(176 -31) 1 1 0 )
(command "insert" "mroads" '(205 -57) 1 1 0 )
(command "insert" "mroads" '(210 -68) 1 1 0 )
(command "insert" "mroads" '(232 -49) 1 1 0 )
(command "insert" "mroads" '(222 -68) 1 1 0 )
(command "insert" "mroads" '(230 -71) 1 1 0 )
(command "insert" "mroads" '(206 -40) 1 1 0 )
(command "insert" "mroads" '(245 -53) 1 1 0 )
(command "insert" "mroads" '(193 -53) 1 1 0 )
(command "insert" "mroads" '(202 -54) 1 1 0 )
(command "insert" "mroads" '(219 -46) 1 1 0 )
(command "insert" "mroads" '(238 -50) 1 1 0 )
(command "insert" "mroads" '(258 -52) 1 1 0 )
(command "insert" "mroads" '(225 -79) 1 1 0 )
(command "insert" "mroads" '(189 -33) 1 1 0 )
(command "insert" "mroads" '(172 -31) 1 1 0 )
(command "insert" "mroads" '(246 -50) 1 1 0 )
(command "insert" "mroads" '(250 -49) 1 1 0 )
(command "insert" "mroads" '(207 -67) 1 1 0 )
(command "insert" "mroads" '(214 -43) 1 1 0 )
(command "insert" "mroads" '(197 -33) 1 1 0 )
(command "insert" "mroads" '(194 -33) 1 1 0 )
(command "insert" "mroads" '(227 -81) 1 1 0 )
(command "insert" "mroads" '(201 -38) 1 1 0 )
(command "insert" "mroads" '(267 -66) 1 1 0 )
(command "insert" "mroads" '(275 -67) 1 1 0 )
(command "insert" "mroads" '(178 -32) 1 1 0 )
(command "insert" "mroads" '(257 -90) 1 1 0 )
(command "insert" "mroads" '(269 -90) 1 1 0 )
(command "insert" "mroads" '(180 -30) 1 1 0 )
(command "insert" "mroads" '(263 -92) 1 1 0 )
(command "insert" "mroads" '(259 -92) 1 1 0 )
(command "insert" "mroads" '(236 -48) 1 1 0 )
(command "insert" "mroads" '(273 -58) 1 1 0 )
(command "insert" "mroads" '(206 -51) 1 1 0 )
(command "insert" "mroads" '(180 -34) 1 1 0 )
(command "insert" "mroads" '(263 -88) 1 1 0 )
(command "insert" "mroads" '(221 -44) 1 1 0 )
(command "insert" "mroads" '(157 -32) 1 1 0 )
(command "insert" "mroads" '(224 -76) 1 1 0 )
(command "insert" "mroads" '(187 -48) 1 1 0 )
(command "insert" "mroads" '(192 -37) 1 1 0 )
(command "insert" "mroads" '(182 -40) 1 1 0 )
(command "insert" "mroads" '(212 -40) 1 1 0 )
(command "insert" "mroads" '(160 -30) 1 1 0 )
(command "insert" "mroads" '(226 -78) 1 1 0 )
(command "insert" "mroads" '(246 -53) 1 1 0 )
(command "insert" "mroads" '(201 -53) 1 1 0 )
(command "insert" "mroads" '(264 -89) 1 1 0 )
(command "insert" "mroads" '(272 -60) 1 1 0 )
(command "insert" "mroads" '(227 -86) 1 1 0 )
(command "insert" "mroads" '(256 -89) 1 1 0 )
(command "insert" "mroads" '(265 -53) 1 1 0 )
(command "insert" "mroads" '(268 -89) 1 1 0 )
(command "insert" "mroads" '(218 -66) 1 1 0 )
(command "insert" "mroads" '(199 -36) 1 1 0 )
(command "insert" "mroads" '(229 -84) 1 1 0 )
(command "insert" "mroads" '(208 -52) 1 1 0 )
(command "insert" "mroads" '(261 -54) 1 1 0 )
(command "insert" "mroads" '(219 -66) 1 1 0 )
(command "insert" "mroads" '(265 -51) 1 1 0 )
(command "insert" "mroads" '(220 -71) 1 1 0 )
(command "insert" "mroads" '(205 -43) 1 1 0 )
(command "insert" "mroads" '(209 -66) 1 1 0 )
(command "insert" "mroads" '(236 -47) 1 1 0 )
(command "insert" "mroads" '(226 -46) 1 1 0 )
(command "insert" "mroads" '(156 -30) 1 1 0 )
(command "insert" "mroads" '(158 -28) 1 1 0 )
(command "insert" "mroads" '(242 -48) 1 1 0 )
(command "insert" "mroads" '(223 -86) 1 1 0 )
(command "insert" "mroads" '(206 -58) 1 1 0 )
(command "insert" "mroads" '(180 -41) 1 1 0 )
(command "insert" "mroads" '(184 -44) 1 1 0 )
(command "insert" "mroads" '(174 -35) 1 1 0 )
(command "insert" "mroads" '(224 -67) 1 1 0 )
(command "insert" "mroads" '(182 -35) 1 1 0 )
(command "insert" "mroads" '(186 -46) 1 1 0 )
(command "insert" "mroads" '(225 -89) 1 1 0 )
(command "insert" "mroads" '(226 -73) 1 1 0 )
(command "insert" "mroads" '(189 -51) 1 1 0 )
(command "insert" "mroads" '(163 -32) 1 1 0 )
(command "insert" "mroads" '(171 -32) 1 1 0 )
(command "insert" "mroads" '(219 -42) 1 1 0 )
(command "insert" "mroads" '(191 -45) 1 1 0 )
(command "insert" "mroads" '(190 -50) 1 1 0 )
(command "insert" "mroads" '(203 -38) 1 1 0 )
(command "insert" "mroads" '(258 -90) 1 1 0 )
(command "insert" "mroads" '(229 -78) 1 1 0 )
(command "insert" "mroads" '(208 -43) 1 1 0 )
(command "insert" "mroads" '(198 -50) 1 1 0 )
(command "insert" "mroads" '(154 -27) 1 1 0 )
(command "insert" "mroads" '(222 -85) 1 1 0 )
(command "insert" "mroads" '(265 -52) 1 1 0 )
(command "insert" "mroads" '(231 -91) 1 1 0 )
(command "insert" "mroads" '(205 -36) 1 1 0 )
(command "insert" "mroads" '(222 -81) 1 1 0 )
(command "insert" "mroads" '(251 -49) 1 1 0 )
(command "insert" "mroads" '(255 -52) 1 1 0 )
(command "insert" "mroads" '(206 -61) 1 1 0 )
(command "insert" "mroads" '(239 -88) 1 1 0 )
(command "insert" "mroads" '(205 -58) 1 1 0 )
(command "insert" "mroads" '(192 -51) 1 1 0 )
(command "insert" "mroads" '(271 -66) 1 1 0 )
(command "insert" "mroads" '(275 -59) 1 1 0 )
(command "insert" "mroads" '(225 -82) 1 1 0 )
(command "insert" "mroads" '(217 -45) 1 1 0 )
(command "insert" "mroads" '(204 -65) 1 1 0 )
(command "insert" "mroads" '(227 -68) 1 1 0 )
(command "insert" "mroads" '(256 -87) 1 1 0 )
(command "insert" "mroads" '(165 -35) 1 1 0 )
(command "insert" "mroads" '(204 -66) 1 1 0 )
(command "insert" "mroads" '(196 -39) 1 1 0 )
(command "insert" "mroads" '(200 -48) 1 1 0 )
(command "insert" "mroads" '(190 -53) 1 1 0 )
(command "insert" "mroads" '(173 -35) 1 1 0 )
(command "insert" "mroads" '(229 -70) 1 1 0 )
(command "insert" "mroads" '(230 -92) 1 1 0 )
(command "insert" "mroads" '(177 -32) 1 1 0 )
(command "insert" "mroads" '(225 -46) 1 1 0 )
(command "insert" "mroads" '(198 -53) 1 1 0 )
(command "insert" "mroads" '(228 -45) 1 1 0 )
(command "insert" "mroads" '(220 -66) 1 1 0 )
(command "insert" "mroads" '(231 -50) 1 1 0 )
(command "insert" "mroads" '(210 -40) 1 1 0 )
(command "insert" "mroads" '(263 -54) 1 1 0 )
(command "insert" "mroads" '(240 -88) 1 1 0 )
(command "insert" "mroads" '(230 -47) 1 1 0 )
(command "insert" "mroads" '(204 -54) 1 1 0 )
(command "insert" "mroads" '(235 -48) 1 1 0 )
(command "insert" "mroads" '(151 -29) 1 1 0 )
(command "insert" "mroads" '(223 -68) 1 1 0 )
(command "insert" "mroads" '(269 -57) 1 1 0 )
(command "insert" "mroads" '(224 -81) 1 1 0 )
(command "insert" "mroads" '(179 -34) 1 1 0 )
(command "insert" "mroads" '(248 -87) 1 1 0 )
(command "insert" "mroads" '(156 -32) 1 1 0 )
(command "insert" "mroads" '(212 -69) 1 1 0 )
(command "insert" "mroads" '(186 -48) 1 1 0 )
(command "insert" "mroads" '(207 -70) 1 1 0 )
(command "insert" "mroads" '(226 -91) 1 1 0 )
(command "insert" "mroads" '(211 -40) 1 1 0 )
(command "insert" "mroads" '(194 -48) 1 1 0 )
(command "insert" "mroads" '(168 -35) 1 1 0 )
(command "insert" "mroads" '(171 -30) 1 1 0 )
(command "insert" "mroads" '(227 -77) 1 1 0 )
(command "insert" "mroads" '(228 -69) 1 1 0 )
(command "insert" "mroads" '(207 -63) 1 1 0 )
(command "insert" "mroads" '(228 -87) 1 1 0 )
(command "insert" "mroads" '(200 -41) 1 1 0 )
(command "insert" "mroads" '(229 -79) 1 1 0 )
(command "insert" "mroads" '(230 -87) 1 1 0 )
(command "insert" "mroads" '(195 -51) 1 1 0 )
(command "insert" "mroads" '(209 -61) 1 1 0 )
(command "insert" "mroads" '(206 -67) 1 1 0 )
(command "insert" "mroads" '(254 -89) 1 1 0 )
(command "insert" "mroads" '(207 -71) 1 1 0 )
(command "insert" "mroads" '(215 -71) 1 1 0 )
(command "insert" "mroads" '(179 -31) 1 1 0 )
(command "insert" "mroads" '(244 -87) 1 1 0 )
(command "insert" "mroads" '(222 -67) 1 1 0 )
(command "insert" "mroads" '(272 -61) 1 1 0 )
(command "insert" "mroads" '(167 -30) 1 1 0 )
(command "insert" "mroads" '(223 -77) 1 1 0 )
(command "insert" "mroads" '(274 -63) 1 1 0 )
(command "insert" "mroads" '(232 -91) 1 1 0 )
(command "insert" "mroads" '(179 -43) 1 1 0 )
(command "insert" "mroads" '(226 -82) 1 1 0 )
(command "insert" "mroads" '(207 -52) 1 1 0 )
(command "insert" "mroads" '(181 -33) 1 1 0 )
(command "insert" "mroads" '(185 -38) 1 1 0 )
(command "insert" "mroads" '(175 -31) 1 1 0 )
(command "insert" "mroads" '(186 -44) 1 1 0 )
(command "insert" "mroads" '(188 -53) 1 1 0 )
(command "insert" "mroads" '(162 -32) 1 1 0 )
(command "insert" "mroads" '(228 -76) 1 1 0 )
(command "insert" "mroads" '(193 -38) 1 1 0 )
(command "insert" "mroads" '(183 -47) 1 1 0 )
(command "insert" "mroads" '(239 -50) 1 1 0 )
(command "insert" "mroads" '(213 -43) 1 1 0 )
(command "insert" "mroads" '(170 -32) 1 1 0 )
(command "insert" "mroads" '(247 -50) 1 1 0 )
(command "insert" "mroads" '(230 -78) 1 1 0 )
(command "insert" "mroads" '(167 -35) 1 1 0 )
(command "insert" "mroads" '(198 -39) 1 1 0 )
(command "insert" "mroads" '(197 -50) 1 1 0 )
(command "insert" "mroads" '(253 -53) 1 1 0 )
(command "insert" "mroads" '(201 -55) 1 1 0 )
(command "insert" "mroads" '(241 -88) 1 1 0 )
(command "insert" "mroads" '(222 -74) 1 1 0 )
(command "insert" "mroads" '(235 -46) 1 1 0 )
(command "insert" "mroads" '(209 -55) 1 1 0 )
(command "insert" "mroads" '(246 -92) 1 1 0 )
(command "insert" "mroads" '(203 -57) 1 1 0 )
(command "insert" "mroads" '(223 -74) 1 1 0 )
(command "insert" "mroads" '(195 -40) 1 1 0 )
(command "insert" "mroads" '(274 -54) 1 1 0 )
(command "insert" "mroads" '(202 -49) 1 1 0 )
(command "insert" "mroads" '(209 -64) 1 1 0 )
(command "insert" "mroads" '(249 -89) 1 1 0 )
(command "insert" "mroads" '(213 -67) 1 1 0 )
(command "insert" "mroads" '(234 -88) 1 1 0 )
(command "insert" "mroads" '(235 -90) 1 1 0 )
(command "insert" "mroads" '(207 -61) 1 1 0 )
(command "insert" "mroads" '(181 -42) 1 1 0 )
(command "insert" "mroads" '(185 -47) 1 1 0 )
(command "insert" "mroads" '(189 -34) 1 1 0 )
(command "insert" "mroads" '(216 -43) 1 1 0 )
(command "insert" "mroads" '(228 -75) 1 1 0 )
(command "insert" "mroads" '(183 -36) 1 1 0 )
(command "insert" "mroads" '(187 -33) 1 1 0 )
(command "insert" "mroads" '(151 -31) 1 1 0 )
(command "insert" "mroads" '(190 -46) 1 1 0 )
(command "insert" "mroads" '(248 -49) 1 1 0 )
(command "insert" "mroads" '(203 -60) 1 1 0 )
(command "insert" "mroads" '(195 -33) 1 1 0 )
(command "insert" "mroads" '(243 -91) 1 1 0 )
(command "insert" "mroads" '(207 -65) 1 1 0 )
(command "insert" "mroads" '(255 -91) 1 1 0 )
(command "insert" "mroads" '(220 -47) 1 1 0 )
(command "insert" "mroads" '(176 -32) 1 1 0 )
(command "insert" "mroads" '(224 -42) 1 1 0 )
(command "insert" "mroads" '(260 -56) 1 1 0 )
(command "insert" "mroads" '(183 -48) 1 1 0 )
(command "insert" "mroads" '(201 -56) 1 1 0 )
(command "insert" "mroads" '(191 -53) 1 1 0 )
(command "insert" "mroads" '(222 -77) 1 1 0 )
(command "insert" "mroads" '(178 -42) 1 1 0 )
(command "insert" "mroads" '(209 -40) 1 1 0 )
(command "insert" "mroads" '(199 -53) 1 1 0 )
(command "insert" "mroads" '(246 -87) 1 1 0 )
(command "insert" "mroads" '(203 -62) 1 1 0 )
(command "insert" "mroads" '(234 -48) 1 1 0 )
(command "insert" "mroads" '(208 -67) 1 1 0 )
(command "insert" "mroads" '(204 -63) 1 1 0 )
(command "insert" "mroads" '(230 -91) 1 1 0 )
(command "insert" "mroads" '(228 -86) 1 1 0 )
(command "insert" "mroads" '(205 -60) 1 1 0 )
(command "insert" "mroads" '(227 -46) 1 1 0 )
(command "insert" "mroads" '(178 -30) 1 1 0 )
(command "insert" "mroads" '(207 -58) 1 1 0 )
(command "insert" "mroads" '(155 -32) 1 1 0 )
(command "insert" "mroads" '(274 -64) 1 1 0 )
(command "insert" "mroads" '(185 -48) 1 1 0 )
(command "insert" "mroads" '(206 -37) 1 1 0 )
(command "insert" "mroads" '(237 -89) 1 1 0 )
(command "insert" "mroads" '(193 -48) 1 1 0 )
(command "insert" "mroads" '(187 -38) 1 1 0 )
(command "insert" "mroads" '(268 -61) 1 1 0 )
(command "insert" "mroads" '(238 -47) 1 1 0 )
(command "insert" "mroads" '(195 -38) 1 1 0 )
(command "insert" "mroads" '(225 -74) 1 1 0 )
(command "insert" "mroads" '(189 -36) 1 1 0 )
(command "insert" "mroads" '(265 -89) 1 1 0 )
(command "insert" "mroads" '(250 -50) 1 1 0 )
(command "insert" "mroads" '(223 -43) 1 1 0 )
(command "insert" "mroads" '(197 -36) 1 1 0 )
(command "insert" "mroads" '(245 -90) 1 1 0 )
(command "insert" "mroads" '(191 -50) 1 1 0 )
(command "insert" "mroads" '(178 -37) 1 1 0 )
(command "insert" "mroads" '(217 -70) 1 1 0 )
(command "insert" "mroads" '(262 -53) 1 1 0 )
(command "insert" "mroads" '(229 -46) 1 1 0 )
(command "insert" "mroads" '(203 -55) 1 1 0 )
(command "insert" "mroads" '(208 -58) 1 1 0 )
(command "insert" "mroads" '(205 -53) 1 1 0 )
(command "insert" "mroads" '(240 -48) 1 1 0 )
(command "insert" "mroads" '(161 -28) 1 1 0 )
(command "insert" "mroads" '(216 -67) 1 1 0 )
(command "insert" "mroads" '(266 -90) 1 1 0 )
(command "insert" "mroads" '(168 -31) 1 1 0 )
(command "insert" "mroads" '(215 -67) 1 1 0 )
(command "insert" "mroads" '(180 -39) 1 1 0 )
(command "insert" "mroads" '(184 -34) 1 1 0 )
(command "insert" "mroads" '(254 -92) 1 1 0 )
(command "insert" "mroads" '(224 -73) 1 1 0 )
(command "insert" "mroads" '(270 -63) 1 1 0 )
(command "insert" "mroads" '(161 -32) 1 1 0 )
(command "insert" "mroads" '(269 -91) 1 1 0 )
(command "insert" "mroads" '(192 -34) 1 1 0 )
(command "insert" "mroads" '(169 -32) 1 1 0 )
(command "insert" "mroads" '(225 -67) 1 1 0 )
(command "insert" "mroads" '(204 -50) 1 1 0 )
(command "insert" "mroads" '(166 -33) 1 1 0 )
(command "insert" "mroads" '(216 -69) 1 1 0 )
(command "insert" "mroads" '(227 -85) 1 1 0 )
(command "insert" "mroads" '(259 -51) 1 1 0 )
(command "insert" "mroads" '(218 -71) 1 1 0 )
(command "insert" "mroads" '(164 -31) 1 1 0 )
(command "insert" "mroads" '(229 -87) 1 1 0 )
(command "insert" "mroads" '(271 -62) 1 1 0 )
(command "insert" "mroads" '(272 -58) 1 1 0 )
(command "insert" "mroads" '(273 -62) 1 1 0 )
(command "insert" "mroads" '(261 -90) 1 1 0 )
(command "insert" "mroads" '(262 -88) 1 1 0 )
(command "insert" "mroads" '(252 -49) 1 1 0 )
(command "insert" "mroads" '(223 -85) 1 1 0 )
(command "insert" "mroads" '(206 -55) 1 1 0 )
(command "insert" "mroads" '(180 -46) 1 1 0 )
(command "insert" "mroads" '(184 -41) 1 1 0 )
(command "insert" "mroads" '(273 -59) 1 1 0 )
(command "insert" "mroads" '(187 -52) 1 1 0 )
(command "insert" "mroads" '(182 -44) 1 1 0 )
(command "insert" "mroads" '(226 -71) 1 1 0 )
(command "insert" "mroads" '(186 -35) 1 1 0 )
(command "insert" "mroads" '(225 -68) 1 1 0 )
(command "insert" "mroads" '(226 -74) 1 1 0 )
(command "insert" "mroads" '(266 -91) 1 1 0 )
(command "insert" "mroads" '(215 -68) 1 1 0 )
(command "insert" "mroads" '(188 -45) 1 1 0 )
(command "insert" "mroads" '(227 -90) 1 1 0 )
(command "insert" "mroads" '(228 -84) 1 1 0 )
(command "insert" "mroads" '(232 -47) 1 1 0 )
(command "insert" "mroads" '(259 -56) 1 1 0 )
(command "insert" "mroads" '(152 -30) 1 1 0 )
(command "insert" "mroads" '(253 -88) 1 1 0 )
(command "insert" "mroads" '(229 -80) 1 1 0 )
(command "insert" "mroads" '(257 -87) 1 1 0 )
(command "insert" "mroads" '(177 -42) 1 1 0 )
(command "insert" "mroads" '(264 -53) 1 1 0 )
(command "insert" "mroads" '(234 -45) 1 1 0 )
(command "insert" "mroads" '(208 -40) 1 1 0 )
(command "insert" "mroads" '(154 -28) 1 1 0 )
(command "insert" "mroads" '(219 -70) 1 1 0 )
(command "insert" "mroads" '(202 -50) 1 1 0 )
(command "insert" "mroads" '(233 -48) 1 1 0 )
(command "insert" "mroads" '(205 -39) 1 1 0 )
(command "insert" "mroads" '(260 -89) 1 1 0 )
(command "insert" "mroads" '(273 -55) 1 1 0 )
(command "insert" "mroads" '(240 -46) 1 1 0 )
(command "insert" "mroads" '(221 -68) 1 1 0 )
(command "insert" "mroads" '(222 -82) 1 1 0 )
(command "insert" "mroads" '(222 -75) 1 1 0 )
(command "insert" "mroads" '(223 -82) 1 1 0 )
(command "insert" "mroads" '(206 -62) 1 1 0 )
(command "insert" "mroads" '(154 -32) 1 1 0 )
(command "insert" "mroads" '(199 -41) 1 1 0 )
(command "insert" "mroads" '(184 -48) 1 1 0 )
(command "insert" "mroads" '(224 -71) 1 1 0 )
(command "insert" "mroads" '(268 -55) 1 1 0 )
(command "insert" "mroads" '(271 -61) 1 1 0 )
(command "insert" "mroads" '(182 -39) 1 1 0 )
(command "insert" "mroads" '(275 -54) 1 1 0 )
(command "insert" "mroads" '(186 -42) 1 1 0 )
(command "insert" "mroads" '(150 -28) 1 1 0 )
(command "insert" "mroads" '(226 -69) 1 1 0 )
(command "insert" "mroads" '(188 -36) 1 1 0 )
(command "insert" "mroads" '(227 -67) 1 1 0 )
(command "insert" "mroads" '(228 -83) 1 1 0 )
(command "insert" "mroads" '(222 -44) 1 1 0 )
(command "insert" "mroads" '(249 -50) 1 1 0 )
(command "insert" "mroads" '(204 -71) 1 1 0 )
(command "insert" "mroads" '(196 -36) 1 1 0 )
(command "insert" "mroads" '(229 -89) 1 1 0 )
(command "insert" "mroads" '(230 -89) 1 1 0 )
(command "insert" "mroads" '(177 -35) 1 1 0 )
(command "insert" "mroads" '(202 -61) 1 1 0 )
(command "insert" "mroads" '(184 -36) 1 1 0 )
(command "insert" "mroads" '(231 -87) 1 1 0 )
(command "insert" "mroads" '(263 -53) 1 1 0 )
(command "insert" "mroads" '(244 -91) 1 1 0 )
(command "insert" "mroads" '(204 -59) 1 1 0 )
(command "insert" "mroads" '(159 -27) 1 1 0 )
(command "insert" "mroads" '(238 -88) 1 1 0 )
(command "insert" "mroads" '(177 -31) 1 1 0 )
(command "insert" "mroads" '(269 -60) 1 1 0 )
(command "insert" "mroads" '(179 -33) 1 1 0 )
(command "insert" "mroads" '(227 -42) 1 1 0 )
(command "insert" "mroads" '(271 -58) 1 1 0 )
(command "insert" "mroads" '(275 -63) 1 1 0 )
(command "insert" "mroads" '(186 -53) 1 1 0 )
(command "insert" "mroads" '(160 -32) 1 1 0 )
(command "insert" "mroads" '(225 -86) 1 1 0 )
(command "insert" "mroads" '(226 -92) 1 1 0 )
(command "insert" "mroads" '(211 -39) 1 1 0 )
(command "insert" "mroads" '(194 -53) 1 1 0 )
(command "insert" "mroads" '(168 -32) 1 1 0 )
(command "insert" "mroads" '(188 -35) 1 1 0 )
(command "insert" "mroads" '(227 -72) 1 1 0 )
(command "insert" "mroads" '(228 -90) 1 1 0 )
(command "insert" "mroads" '(261 -56) 1 1 0 )
(command "insert" "mroads" '(196 -35) 1 1 0 )
(command "insert" "mroads" '(200 -38) 1 1 0 )
(command "insert" "mroads" '(173 -31) 1 1 0 )
(command "insert" "mroads" '(230 -80) 1 1 0 )
(command "insert" "mroads" '(177 -36) 1 1 0 )
(command "insert" "mroads" '(269 -65) 1 1 0 )
(command "insert" "mroads" '(198 -41) 1 1 0 )
(command "insert" "mroads" '(254 -90) 1 1 0 )
(command "insert" "mroads" '(202 -36) 1 1 0 )
(command "insert" "mroads" '(202 -56) 1 1 0 )
(command "insert" "mroads" '(160 -29) 1 1 0 )
(command "insert" "mroads" '(209 -71) 1 1 0 )
(command "insert" "mroads" '(240 -92) 1 1 0 )
(command "insert" "mroads" '(267 -55) 1 1 0 )
(command "insert" "mroads" '(209 -57) 1 1 0 )
(command "insert" "mroads" '(262 -55) 1 1 0 )
(command "insert" "mroads" '(232 -88) 1 1 0 )
(command "insert" "mroads" '(224 -85) 1 1 0 )
(command "insert" "mroads" '(179 -38) 1 1 0 )
(command "insert" "mroads" '(205 -65) 1 1 0 )
(command "insert" "mroads" '(248 -91) 1 1 0 )
(command "insert" "mroads" '(275 -68) 1 1 0 )
(command "insert" "mroads" '(226 -87) 1 1 0 )
(command "insert" "mroads" '(207 -43) 1 1 0 )
(command "insert" "mroads" '(181 -36) 1 1 0 )
(command "insert" "mroads" '(211 -44) 1 1 0 )
(command "insert" "mroads" '(185 -33) 1 1 0 )
(command "insert" "mroads" '(236 -92) 1 1 0 )
(command "insert" "mroads" '(193 -33) 1 1 0 )
(command "insert" "mroads" '(239 -49) 1 1 0 )
(command "insert" "mroads" '(231 -92) 1 1 0 )
(command "insert" "mroads" '(268 -66) 1 1 0 )
(command "insert" "mroads" '(229 -75) 1 1 0 )
(command "insert" "mroads" '(230 -75) 1 1 0 )
(command "insert" "mroads" '(251 -50) 1 1 0 )
(command "insert" "mroads" '(247 -49) 1 1 0 )
(command "insert" "mroads" '(206 -71) 1 1 0 )
(command "insert" "mroads" '(163 -30) 1 1 0 )
(command "insert" "mroads" '(222 -88) 1 1 0 )
(command "insert" "mroads" '(197 -53) 1 1 0 )
(command "insert" "mroads" '(201 -50) 1 1 0 )
(command "insert" "mroads" '(241 -91) 1 1 0 )
(command "insert" "mroads" '(222 -71) 1 1 0 )
(command "insert" "mroads" '(235 -45) 1 1 0 )
(command "insert" "mroads" '(246 -89) 1 1 0 )
(command "insert" "mroads" '(191 -37) 1 1 0 )
(command "insert" "mroads" '(242 -89) 1 1 0 )
(command "insert" "mroads" '(223 -73) 1 1 0 )
(command "insert" "mroads" '(215 -40) 1 1 0 )
(command "insert" "mroads" '(237 -47) 1 1 0 )
(command "insert" "mroads" '(211 -68) 1 1 0 )
(command "insert" "mroads" '(233 -87) 1 1 0 )
(command "insert" "mroads" '(153 -32) 1 1 0 )
(command "insert" "mroads" '(209 -67) 1 1 0 )
(command "insert" "mroads" '(213 -70) 1 1 0 )
(command "insert" "mroads" '(159 -30) 1 1 0 )
(command "insert" "mroads" '(235 -89) 1 1 0 )
(command "insert" "mroads" '(270 -55) 1 1 0 )
(command "insert" "mroads" '(181 -45) 1 1 0 )
(command "insert" "mroads" '(185 -42) 1 1 0 )
(command "insert" "mroads" '(250 -88) 1 1 0 )
(command "insert" "mroads" '(251 -90) 1 1 0 )
(command "insert" "mroads" '(214 -66) 1 1 0 )
(command "insert" "mroads" '(188 -49) 1 1 0 )
(command "insert" "mroads" '(236 -91) 1 1 0 )
(command "insert" "mroads" '(228 -72) 1 1 0 )
(command "insert" "mroads" '(243 -52) 1 1 0 )
(command "insert" "mroads" '(187 -44) 1 1 0 )
(command "insert" "mroads" '(200 -51) 1 1 0 )
(command "insert" "mroads" '(189 -46) 1 1 0 )
(command "insert" "mroads" '(220 -44) 1 1 0 )
(command "insert" "mroads" '(260 -54) 1 1 0 )
(command "insert" "mroads" '(244 -90) 1 1 0 )
(command "insert" "mroads" '(201 -59) 1 1 0 )
(command "insert" "mroads" '(241 -92) 1 1 0 )
(command "insert" "mroads" '(222 -78) 1 1 0 )
(command "insert" "mroads" '(161 -30) 1 1 0 )
(command "insert" "mroads" '(209 -43) 1 1 0 )
(command "insert" "mroads" '(253 -92) 1 1 0 )
(command "insert" "mroads" '(203 -61) 1 1 0 )
(command "insert" "mroads" '(271 -68) 1 1 0 )
(command "insert" "mroads" '(208 -64) 1 1 0 )
(command "insert" "mroads" '(254 -48) 1 1 0 )
(command "insert" "mroads" '(150 -31) 1 1 0 )
(command "insert" "mroads" '(241 -45) 1 1 0 )
(command "insert" "mroads" '(233 -88) 1 1 0 )
(command "insert" "mroads" '(205 -63) 1 1 0 )
(command "insert" "mroads" '(209 -68) 1 1 0 )
(command "insert" "mroads" '(232 -48) 1 1 0 )
(command "insert" "mroads" '(207 -57) 1 1 0 )
(command "insert" "mroads" '(204 -41) 1 1 0 )
(command "insert" "mroads" '(175 -32) 1 1 0 )
(command "insert" "mroads" '(214 -69) 1 1 0 )
(command "insert" "mroads" '(206 -38) 1 1 0 )
(command "insert" "mroads" '(237 -92) 1 1 0 )
(command "insert" "mroads" '(193 -51) 1 1 0 )
(command "insert" "mroads" '(187 -37) 1 1 0 )
(command "insert" "mroads" '(244 -88) 1 1 0 )
(command "insert" "mroads" '(253 -89) 1 1 0 )
(command "insert" "mroads" '(218 -45) 1 1 0 )
(command "insert" "mroads" '(248 -53) 1 1 0 )
(command "insert" "mroads" '(230 -69) 1 1 0 )
(command "insert" "mroads" '(195 -37) 1 1 0 )
(command "insert" "mroads" '(172 -33) 1 1 0 )
(command "insert" "mroads" '(220 -43) 1 1 0 )
(command "insert" "mroads" '(224 -46) 1 1 0 )
(command "insert" "mroads" '(223 -46) 1 1 0 )
(command "insert" "mroads" '(197 -39) 1 1 0 )
(command "insert" "mroads" '(227 -43) 1 1 0 )
(command "insert" "mroads" '(201 -60) 1 1 0 )
(command "insert" "mroads" '(191 -49) 1 1 0 )
(command "insert" "mroads" '(275 -64) 1 1 0 )
(command "insert" "mroads" '(267 -90) 1 1 0 )
(command "insert" "mroads" '(178 -38) 1 1 0 )
(command "insert" "mroads" '(226 -44) 1 1 0 )
(command "insert" "mroads" '(209 -44) 1 1 0 )
(command "insert" "mroads" '(199 -49) 1 1 0 )
(command "insert" "mroads" '(247 -91) 1 1 0 )
(command "insert" "mroads" '(203 -50) 1 1 0 )
(command "insert" "mroads" '(208 -71) 1 1 0 )
(command "insert" "mroads" '(231 -47) 1 1 0 )
(command "insert" "mroads" '(268 -59) 1 1 0 )
(command "insert" "mroads" '(210 -69) 1 1 0 )
(command "insert" "mroads" '(235 -87) 1 1 0 )
(command "insert" "mroads" '(215 -70) 1 1 0 )
(command "insert" "mroads" '(180 -36) 1 1 0 )
(command "insert" "mroads" '(193 -52) 1 1 0 )
(command "insert" "mroads" '(221 -45) 1 1 0 )
(command "insert" "mroads" '(170 -30) 1 1 0 )
(command "insert" "mroads" '(258 -89) 1 1 0 )
(command "insert" "mroads" '(264 -87) 1 1 0 )
(command "insert" "mroads" '(257 -53) 1 1 0 )
(command "insert" "mroads" '(274 -59) 1 1 0 )
(command "insert" "mroads" '(258 -53) 1 1 0 )
(command "insert" "mroads" '(169 -35) 1 1 0 )
(command "insert" "mroads" '(225 -78) 1 1 0 )
(command "insert" "mroads" '(268 -92) 1 1 0 )
(command "insert" "mroads" '(246 -51) 1 1 0 )
(command "insert" "mroads" '(166 -34) 1 1 0 )
(command "insert" "mroads" '(216 -66) 1 1 0 )
(command "insert" "mroads" '(227 -80) 1 1 0 )
(command "insert" "mroads" '(201 -37) 1 1 0 )
(command "insert" "mroads" '(178 -33) 1 1 0 )
(command "insert" "mroads" '(257 -89) 1 1 0 )
(command "insert" "mroads" '(208 -62) 1 1 0 )
(command "insert" "mroads" '(180 -31) 1 1 0 )
(command "insert" "mroads" '(166 -30) 1 1 0 )
(command "insert" "mroads" '(205 -49) 1 1 0 )
(command "insert" "mroads" '(260 -87) 1 1 0 )
(command "insert" "mroads" '(272 -64) 1 1 0 )
(command "insert" "mroads" '(236 -49) 1 1 0 )
(command "insert" "mroads" '(273 -57) 1 1 0 )
(command "insert" "mroads" '(152 -32) 1 1 0 )
(command "insert" "mroads" '(262 -51) 1 1 0 )
(command "insert" "mroads" '(206 -48) 1 1 0 )
(command "insert" "mroads" '(180 -35) 1 1 0 )
(command "insert" "mroads" '(184 -38) 1 1 0 )
(command "insert" "mroads" '(224 -77) 1 1 0 )
(command "insert" "mroads" '(187 -51) 1 1 0 )
(command "insert" "mroads" '(205 -69) 1 1 0 )
(command "insert" "mroads" '(192 -38) 1 1 0 )
(command "insert" "mroads" '(182 -41) 1 1 0 )
(command "insert" "mroads" '(212 -41) 1 1 0 )
(command "insert" "mroads" '(186 -36) 1 1 0 )
(command "insert" "mroads" '(160 -31) 1 1 0 )
(command "insert" "mroads" '(225 -71) 1 1 0 )
(command "insert" "mroads" '(226 -79) 1 1 0 )
(command "insert" "mroads" '(194 -36) 1 1 0 )
(command "insert" "mroads" '(197 -41) 1 1 0 )
(command "insert" "mroads" '(227 -89) 1 1 0 )
(command "insert" "mroads" '(256 -90) 1 1 0 )
(command "insert" "mroads" '(196 -50) 1 1 0 )
(command "insert" "mroads" '(152 -27) 1 1 0 )
(command "insert" "mroads" '(200 -53) 1 1 0 )
(command "insert" "mroads" '(199 -39) 1 1 0 )
(command "insert" "mroads" '(229 -83) 1 1 0 )
(command "insert" "mroads" '(234 -46) 1 1 0 )
(command "insert" "mroads" '(208 -53) 1 1 0 )
(command "insert" "mroads" '(202 -60) 1 1 0 )
(command "insert" "mroads" '(219 -69) 1 1 0 )
(command "insert" "mroads" '(202 -55) 1 1 0 )
(command "insert" "mroads" '(205 -42) 1 1 0 )
(command "insert" "mroads" '(156 -31) 1 1 0 )
(command "insert" "mroads" '(221 -71) 1 1 0 )
(command "insert" "mroads" '(262 -92) 1 1 0 )
(command "insert" "mroads" '(271 -54) 1 1 0 )
(command "insert" "mroads" '(158 -29) 1 1 0 )
(command "insert" "mroads" '(223 -81) 1 1 0 )
(command "insert" "mroads" '(206 -59) 1 1 0 )
(command "insert" "mroads" '(180 -42) 1 1 0 )
(command "insert" "mroads" '(184 -45) 1 1 0 )
(command "insert" "mroads" '(174 -32) 1 1 0 )
(command "insert" "mroads" '(224 -68) 1 1 0 )
(command "insert" "mroads" '(205 -59) 1 1 0 )
(command "insert" "mroads" '(182 -32) 1 1 0 )
(command "insert" "mroads" '(186 -47) 1 1 0 )
(command "insert" "mroads" '(225 -88) 1 1 0 )
(command "insert" "mroads" '(226 -70) 1 1 0 )
(command "insert" "mroads" '(189 -50) 1 1 0 )
(command "insert" "mroads" '(171 -35) 1 1 0 )
(command "insert" "mroads" '(228 -80) 1 1 0 )
(command "insert" "mroads" '(150 -27) 1 1 0 )
(command "insert" "mroads" '(222 -42) 1 1 0 )
(command "insert" "mroads" '(183 -43) 1 1 0 )
(command "insert" "mroads" '(190 -51) 1 1 0 )
(command "insert" "mroads" '(229 -92) 1 1 0 )
(command "insert" "mroads" '(221 -47) 1 1 0 )
(command "insert" "mroads" '(258 -91) 1 1 0 )
(command "insert" "mroads" '(208 -44) 1 1 0 )
(command "insert" "mroads" '(198 -51) 1 1 0 )
(command "insert" "mroads" '(220 -68) 1 1 0 )
(command "insert" "mroads" '(203 -37) 1 1 0 )
(command "insert" "mroads" '(231 -90) 1 1 0 )
(command "insert" "mroads" '(263 -56) 1 1 0 )
(command "insert" "mroads" '(222 -86) 1 1 0 )
(command "insert" "mroads" '(199 -50) 1 1 0 )
(command "insert" "mroads" '(262 -87) 1 1 0 )
(command "insert" "mroads" '(255 -55) 1 1 0 )
(command "insert" "mroads" '(269 -63) 1 1 0 )
(command "insert" "mroads" '(267 -63) 1 1 0 )
(command "insert" "mroads" '(239 -91) 1 1 0 )
(command "insert" "mroads" '(208 -63) 1 1 0 )
(command "insert" "mroads" '(271 -57) 1 1 0 )
(command "insert" "mroads" '(275 -58) 1 1 0 )
(command "insert" "mroads" '(225 -81) 1 1 0 )
(command "insert" "mroads" '(217 -44) 1 1 0 )
(command "insert" "mroads" '(257 -51) 1 1 0 )
(command "insert" "mroads" '(245 -49) 1 1 0 )
(command "insert" "mroads" '(150 -32) 1 1 0 )
(command "insert" "mroads" '(165 -34) 1 1 0 )
(command "insert" "mroads" '(239 -47) 1 1 0 )
(command "insert" "mroads" '(222 -45) 1 1 0 )
(command "insert" "mroads" '(161 -31) 1 1 0 )
(command "insert" "mroads" '(173 -34) 1 1 0 )
(command "insert" "mroads" '(229 -69) 1 1 0 )
(command "insert" "mroads" '(177 -39) 1 1 0 )
(command "insert" "mroads" '(225 -45) 1 1 0 )
(command "insert" "mroads" '(269 -68) 1 1 0 )
(command "insert" "mroads" '(254 -87) 1 1 0 )
(command "insert" "mroads" '(228 -46) 1 1 0 )
(command "insert" "mroads" '(220 -67) 1 1 0 )
(command "insert" "mroads" '(207 -68) 1 1 0 )
(command "insert" "mroads" '(215 -69) 1 1 0 )
(command "insert" "mroads" '(210 -41) 1 1 0 )
(command "insert" "mroads" '(240 -89) 1 1 0 )
(command "insert" "mroads" '(222 -89) 1 1 0 )
(command "insert" "mroads" '(238 -92) 1 1 0 )
(command "insert" "mroads" '(223 -71) 1 1 0 )
(command "insert" "mroads" '(269 -56) 1 1 0 )
(command "insert" "mroads" '(224 -82) 1 1 0 )
(command "insert" "mroads" '(179 -37) 1 1 0 )
(command "insert" "mroads" '(204 -62) 1 1 0 )
(command "insert" "mroads" '(248 -88) 1 1 0 )
(command "insert" "mroads" '(212 -70) 1 1 0 )
(command "insert" "mroads" '(186 -49) 1 1 0 )
(command "insert" "mroads" '(169 -31) 1 1 0 )
(command "insert" "mroads" '(234 -87) 1 1 0 )
(command "insert" "mroads" '(226 -88) 1 1 0 )
(command "insert" "mroads" '(181 -39) 1 1 0 )
(command "insert" "mroads" '(211 -43) 1 1 0 )
(command "insert" "mroads" '(257 -52) 1 1 0 )
(command "insert" "mroads" '(227 -76) 1 1 0 )
(command "insert" "mroads" '(228 -70) 1 1 0 )
(command "insert" "mroads" '(153 -29) 1 1 0 )
(command "insert" "mroads" '(205 -68) 1 1 0 )
(command "insert" "mroads" '(252 -92) 1 1 0 )
(command "insert" "mroads" '(247 -52) 1 1 0 )
(command "insert" "mroads" '(230 -84) 1 1 0 )
(command "insert" "mroads" '(195 -50) 1 1 0 )
(command "insert" "mroads" '(264 -56) 1 1 0 )
(command "insert" "mroads" '(206 -64) 1 1 0 )
(command "insert" "mroads" '(205 -71) 1 1 0 )
(command "insert" "mroads" '(241 -48) 1 1 0 )
(command "insert" "mroads" '(179 -30) 1 1 0 )
(command "insert" "mroads" '(165 -31) 1 1 0 )
(command "insert" "mroads" '(272 -62) 1 1 0 )
(command "insert" "mroads" '(246 -90) 1 1 0 )
(command "insert" "mroads" '(242 -90) 1 1 0 )
(command "insert" "mroads" '(223 -76) 1 1 0 )
(command "insert" "mroads" '(195 -41) 1 1 0 )
(command "insert" "mroads" '(237 -50) 1 1 0 )
(command "insert" "mroads" '(211 -67) 1 1 0 )
(command "insert" "mroads" '(232 -92) 1 1 0 )
(command "insert" "mroads" '(179 -42) 1 1 0 )
(command "insert" "mroads" '(249 -87) 1 1 0 )
(command "insert" "mroads" '(159 -29) 1 1 0 )
(command "insert" "mroads" '(226 -83) 1 1 0 )
(command "insert" "mroads" '(165 -32) 1 1 0 )
(command "insert" "mroads" '(181 -32) 1 1 0 )
(command "insert" "mroads" '(185 -37) 1 1 0 )
(command "insert" "mroads" '(175 -30) 1 1 0 )
(command "insert" "mroads" '(251 -89) 1 1 0 )
(command "insert" "mroads" '(236 -88) 1 1 0 )
(command "insert" "mroads" '(228 -77) 1 1 0 )
(command "insert" "mroads" '(193 -37) 1 1 0 )
(command "insert" "mroads" '(183 -46) 1 1 0 )
(command "insert" "mroads" '(213 -42) 1 1 0 )
(command "insert" "mroads" '(187 -43) 1 1 0 )
(command "insert" "mroads" '(170 -33) 1 1 0 )
(command "insert" "mroads" '(190 -36) 1 1 0 )
(command "insert" "mroads" '(230 -79) 1 1 0 )
(command "insert" "mroads" '(167 -34) 1 1 0 )
(command "insert" "mroads" '(198 -36) 1 1 0 )
(command "insert" "mroads" '(263 -90) 1 1 0 )
(command "insert" "mroads" '(233 -47) 1 1 0 )
(command "insert" "mroads" '(197 -49) 1 1 0 )
(command "insert" "mroads" '(253 -52) 1 1 0 )
(command "insert" "mroads" '(245 -87) 1 1 0 )
(command "insert" "mroads" '(201 -54) 1 1 0 )
(command "insert" "mroads" '(240 -87) 1 1 0 )
(command "insert" "mroads" '(204 -37) 1 1 0 )
(command "insert" "mroads" '(209 -54) 1 1 0 )
(command "insert" "mroads" '(262 -56) 1 1 0 )
(command "insert" "mroads" '(155 -30) 1 1 0 )
(command "insert" "mroads" '(203 -56) 1 1 0 )
(command "insert" "mroads" '(222 -80) 1 1 0 )
(command "insert" "mroads" '(274 -55) 1 1 0 )
(command "insert" "mroads" '(157 -28) 1 1 0 )
(command "insert" "mroads" '(233 -91) 1 1 0 )
(command "insert" "mroads" '(272 -68) 1 1 0 )
(command "insert" "mroads" '(249 -88) 1 1 0 )
(command "insert" "mroads" '(213 -66) 1 1 0 )
(command "insert" "mroads" '(234 -89) 1 1 0 )
(command "insert" "mroads" '(250 -92) 1 1 0 )
(command "insert" "mroads" '(207 -60) 1 1 0 )
(command "insert" "mroads" '(181 -41) 1 1 0 )
(command "insert" "mroads" '(185 -46) 1 1 0 )
(command "insert" "mroads" '(216 -44) 1 1 0 )
(command "insert" "mroads" '(236 -87) 1 1 0 )
(command "insert" "mroads" '(183 -39) 1 1 0 )
(command "insert" "mroads" '(151 -30) 1 1 0 )
(command "insert" "mroads" '(218 -46) 1 1 0 )
(command "insert" "mroads" '(190 -47) 1 1 0 )
(command "insert" "mroads" '(248 -50) 1 1 0 )
(command "insert" "mroads" '(230 -70) 1 1 0 )
(command "insert" "mroads" '(243 -90) 1 1 0 )
(command "insert" "mroads" '(207 -64) 1 1 0 )
(command "insert" "mroads" '(255 -90) 1 1 0 )
(command "insert" "mroads" '(265 -87) 1 1 0 )
(command "insert" "mroads" '(176 -33) 1 1 0 )
(command "insert" "mroads" '(224 -43) 1 1 0 )
(command "insert" "mroads" '(223 -45) 1 1 0 )
(command "insert" "mroads" '(258 -56) 1 1 0 )
(command "insert" "mroads" '(201 -63) 1 1 0 )
(command "insert" "mroads" '(191 -52) 1 1 0 )
(command "insert" "mroads" '(267 -89) 1 1 0 )
(command "insert" "mroads" '(178 -43) 1 1 0 )
(command "insert" "mroads" '(199 -52) 1 1 0 )
(command "insert" "mroads" '(203 -49) 1 1 0 )
(command "insert" "mroads" '(234 -49) 1 1 0 )
(command "insert" "mroads" '(208 -68) 1 1 0 )
(command "insert" "mroads" '(254 -52) 1 1 0 )
(command "insert" "mroads" '(233 -92) 1 1 0 )
(command "insert" "mroads" '(268 -56) 1 1 0 )
(command "insert" "mroads" '(210 -70) 1 1 0 )
(command "insert" "mroads" '(161 -29) 1 1 0 )
(command "insert" "mroads" '(178 -31) 1 1 0 )
(command "insert" "mroads" '(261 -87) 1 1 0 )
(command "insert" "mroads" '(274 -65) 1 1 0 )
(command "insert" "mroads" '(251 -87) 1 1 0 )
(command "insert" "mroads" '(206 -42) 1 1 0 )
(command "insert" "mroads" '(237 -88) 1 1 0 )
(command "insert" "mroads" '(256 -52) 1 1 0 )
(command "insert" "mroads" '(270 -62) 1 1 0 )
(command "insert" "mroads" '(269 -92) 1 1 0 )
(command "insert" "mroads" '(212 -39) 1 1 0 )
(command "insert" "mroads" '(258 -54) 1 1 0 )
(command "insert" "mroads" '(229 -72) 1 1 0 )
(command "insert" "mroads" '(189 -35) 1 1 0 )
(command "insert" "mroads" '(265 -88) 1 1 0 )
(command "insert" "mroads" '(243 -53) 1 1 0 )
(command "insert" "mroads" '(250 -51) 1 1 0 )
(command "insert" "mroads" '(223 -42) 1 1 0 )
(command "insert" "mroads" '(197 -35) 1 1 0 )
(command "insert" "mroads" '(227 -47) 1 1 0 )
(command "insert" "mroads" '(178 -34) 1 1 0 )
(command "insert" "mroads" '(217 -69) 1 1 0 )
(command "insert" "mroads" '(247 -87) 1 1 0 )
(command "insert" "mroads" '(203 -54) 1 1 0 )
(command "insert" "mroads" '(271 -63) 1 1 0 )
(command "insert" "mroads" '(266 -55) 1 1 0 )
(command "insert" "mroads" '(272 -57) 1 1 0 )
(command "insert" "mroads" '(208 -59) 1 1 0 )
(command "insert" "mroads" '(216 -47) 1 1 0 )
(command "insert" "mroads" '(205 -52) 1 1 0 )
(command "insert" "mroads" '(259 -54) 1 1 0 )
(command "insert" "mroads" '(259 -90) 1 1 0 )
(command "insert" "mroads" '(222 -84) 1 1 0 )
(command "insert" "mroads" '(182 -30) 1 1 0 )
(command "insert" "mroads" '(240 -49) 1 1 0 )
(command "insert" "mroads" '(275 -56) 1 1 0 )
(command "insert" "mroads" '(229 -45) 1 1 0 )
(command "insert" "mroads" '(268 -91) 1 1 0 )
(command "insert" "mroads" '(152 -28) 1 1 0 )
(command "insert" "mroads" '(215 -66) 1 1 0 )
(command "insert" "mroads" '(180 -32) 1 1 0 )
(command "insert" "mroads" '(184 -35) 1 1 0 )
(command "insert" "mroads" '(224 -74) 1 1 0 )
(command "insert" "mroads" '(217 -46) 1 1 0 )
(command "insert" "mroads" '(192 -35) 1 1 0 )
(command "insert" "mroads" '(182 -42) 1 1 0 )
(command "insert" "mroads" '(160 -28) 1 1 0 )
(command "insert" "mroads" '(225 -66) 1 1 0 )
(command "insert" "mroads" '(216 -70) 1 1 0 )
(command "insert" "mroads" '(162 -30) 1 1 0 )
(command "insert" "mroads" '(227 -84) 1 1 0 )
(command "insert" "mroads" '(201 -41) 1 1 0 )
(command "insert" "mroads" '(259 -53) 1 1 0 )
(command "insert" "mroads" '(267 -87) 1 1 0 )
(command "insert" "mroads" '(252 -52) 1 1 0 )
(command "insert" "mroads" '(218 -68) 1 1 0 )
(command "insert" "mroads" '(244 -50) 1 1 0 )
(command "insert" "mroads" '(229 -86) 1 1 0 )
(command "insert" "mroads" '(271 -65) 1 1 0 )
(command "insert" "mroads" '(236 -45) 1 1 0 )
(command "insert" "mroads" '(273 -61) 1 1 0 )
(command "insert" "mroads" '(156 -28) 1 1 0 )
(command "insert" "mroads" '(261 -89) 1 1 0 )
(command "insert" "mroads" '(262 -89) 1 1 0 )
(command "insert" "mroads" '(204 -36) 1 1 0 )
(command "insert" "mroads" '(241 -89) 1 1 0 )
(command "insert" "mroads" '(158 -30) 1 1 0 )
(command "insert" "mroads" '(223 -84) 1 1 0 )
(command "insert" "mroads" '(206 -52) 1 1 0 )
(command "insert" "mroads" '(180 -47) 1 1 0 )
(command "insert" "mroads" '(227 -69) 1 1 0 )
(command "insert" "mroads" '(263 -87) 1 1 0 )
(command "insert" "mroads" '(183 -50) 1 1 0 )
(command "insert" "mroads" '(201 -65) 1 1 0 )
(command "insert" "mroads" '(182 -45) 1 1 0 )
(command "insert" "mroads" '(225 -91) 1 1 0 )
(command "insert" "mroads" '(226 -75) 1 1 0 )
(command "insert" "mroads" '(189 -53) 1 1 0 )
(command "insert" "mroads" '(266 -88) 1 1 0 )
(command "insert" "mroads" '(214 -39) 1 1 0 )
(command "insert" "mroads" '(188 -46) 1 1 0 )
(command "insert" "mroads" '(155 -31) 1 1 0 )
(command "insert" "mroads" '(228 -85) 1 1 0 )
(command "insert" "mroads" '(222 -47) 1 1 0 )
(command "insert" "mroads" '(152 -31) 1 1 0 )
(command "insert" "mroads" '(269 -64) 1 1 0 )
(command "insert" "mroads" '(266 -54) 1 1 0 )
(command "insert" "mroads" '(203 -36) 1 1 0 )
(command "insert" "mroads" '(177 -41) 1 1 0 )
(command "insert" "mroads" '(208 -41) 1 1 0 )
(command "insert" "mroads" '(154 -29) 1 1 0 )
(command "insert" "mroads" '(202 -51) 1 1 0 )
(command "insert" "mroads" '(231 -89) 1 1 0 )
(command "insert" "mroads" '(205 -38) 1 1 0 )
(command "insert" "mroads" '(260 -90) 1 1 0 )
(command "insert" "mroads" '(273 -54) 1 1 0 )
(command "insert" "mroads" '(156 -27) 1 1 0 )
(command "insert" "mroads" '(221 -67) 1 1 0 )
(command "insert" "mroads" '(204 -61) 1 1 0 )
(command "insert" "mroads" '(251 -52) 1 1 0 )
(command "insert" "mroads" '(270 -59) 1 1 0 )
(command "insert" "mroads" '(264 -92) 1 1 0 )
(command "insert" "mroads" '(242 -45) 1 1 0 )
(command "insert" "mroads" '(229 -71) 1 1 0 )
(command "insert" "mroads" '(206 -63) 1 1 0 )
(command "insert" "mroads" '(184 -49) 1 1 0 )
(command "insert" "mroads" '(224 -88) 1 1 0 )
(command "insert" "mroads" '(192 -49) 1 1 0 )
(command "insert" "mroads" '(182 -36) 1 1 0 )
(command "insert" "mroads" '(275 -57) 1 1 0 )
(command "insert" "mroads" '(186 -43) 1 1 0 )
(command "insert" "mroads" '(225 -92) 1 1 0 )
(command "insert" "mroads" '(226 -66) 1 1 0 )
(command "insert" "mroads" '(264 -91) 1 1 0 )
(command "insert" "mroads" '(157 -29) 1 1 0 )
(command "insert" "mroads" '(188 -37) 1 1 0 )
(command "insert" "mroads" '(227 -66) 1 1 0 )
(command "insert" "mroads" '(228 -92) 1 1 0 )
(command "insert" "mroads" '(249 -49) 1 1 0 )
(command "insert" "mroads" '(204 -64) 1 1 0 )
(command "insert" "mroads" '(196 -37) 1 1 0 )
(command "insert" "mroads" '(229 -88) 1 1 0 )
(command "insert" "mroads" '(221 -43) 1 1 0 )
(command "insert" "mroads" '(177 -34) 1 1 0 )
(command "insert" "mroads" '(270 -60) 1 1 0 )
(command "insert" "mroads" '(202 -58) 1 1 0 )
(command "insert" "mroads" '(272 -67) 1 1 0 )
(command "insert" "mroads" '(210 -42) 1 1 0 )
(command "insert" "mroads" '(263 -52) 1 1 0 )
(command "insert" "mroads" '(204 -52) 1 1 0 )
(command "insert" "mroads" '(225 -73) 1 1 0 )
(command "insert" "mroads" '(255 -51) 1 1 0 )
(command "insert" "mroads" '(238 -89) 1 1 0 )
(command "insert" "mroads" '(262 -54) 1 1 0 )
(command "insert" "mroads" '(177 -30) 1 1 0 )
(command "insert" "mroads" '(269 -59) 1 1 0 )
(command "insert" "mroads" '(151 -27) 1 1 0 )
(command "insert" "mroads" '(179 -32) 1 1 0 )
(command "insert" "mroads" '(196 -41) 1 1 0 )
(command "insert" "mroads" '(275 -62) 1 1 0 )
(command "insert" "mroads" '(186 -50) 1 1 0 )
(command "insert" "mroads" '(225 -85) 1 1 0 )
(command "insert" "mroads" '(191 -38) 1 1 0 )
(command "insert" "mroads" '(194 -50) 1 1 0 )
(command "insert" "mroads" '(168 -33) 1 1 0 )
(command "insert" "mroads" '(227 -75) 1 1 0 )
(command "insert" "mroads" '(228 -91) 1 1 0 )
(command "insert" "mroads" '(268 -68) 1 1 0 )
(command "insert" "mroads" '(200 -39) 1 1 0 )
(command "insert" "mroads" '(214 -44) 1 1 0 )
(command "insert" "mroads" '(173 -30) 1 1 0 )
(command "insert" "mroads" '(230 -81) 1 1 0 )
(command "insert" "mroads" '(195 -49) 1 1 0 )
(command "insert" "mroads" '(208 -39) 1 1 0 )
(command "insert" "mroads" '(254 -91) 1 1 0 )
(command "insert" "mroads" '(202 -37) 1 1 0 )
(command "insert" "mroads" '(256 -92) 1 1 0 )
(command "insert" "mroads" '(259 -88) 1 1 0 )
(command "insert" "mroads" '(267 -54) 1 1 0 )
(command "insert" "mroads" '(209 -56) 1 1 0 )
(command "insert" "mroads" '(181 -31) 1 1 0 )
(command "insert" "mroads" '(255 -56) 1 1 0 )
(command "insert" "mroads" '(223 -67) 1 1 0 )
(command "insert" "mroads" '(253 -49) 1 1 0 )
(command "insert" "mroads" '(215 -41) 1 1 0 )
(command "insert" "mroads" '(232 -89) 1 1 0 )
(command "insert" "mroads" '(224 -86) 1 1 0 )
(command "insert" "mroads" '(179 -41) 1 1 0 )
(command "insert" "mroads" '(205 -56) 1 1 0 )
(command "insert" "mroads" '(248 -92) 1 1 0 )
(command "insert" "mroads" '(212 -66) 1 1 0 )
(command "insert" "mroads" '(245 -50) 1 1 0 )
(command "insert" "mroads" '(222 -46) 1 1 0 )
(command "insert" "mroads" '(226 -84) 1 1 0 )
(command "insert" "mroads" '(207 -42) 1 1 0 )
(command "insert" "mroads" '(181 -35) 1 1 0 )
(command "insert" "mroads" '(183 -45) 1 1 0 )
(command "insert" "mroads" '(239 -48) 1 1 0 )
(command "insert" "mroads" '(273 -64) 1 1 0 )
(command "insert" "mroads" '(268 -67) 1 1 0 )
(command "insert" "mroads" '(252 -88) 1 1 0 )
(command "insert" "mroads" '(274 -60) 1 1 0 )
(command "insert" "mroads" '(190 -33) 1 1 0 )
(command "insert" "mroads" '(223 -69) 1 1 0 )
(command "insert" "mroads" '(247 -48) 1 1 0 )
(command "insert" "mroads" '(230 -72) 1 1 0 )
(command "insert" "mroads" '(167 -33) 1 1 0 )
(command "insert" "mroads" '(267 -61) 1 1 0 )
(command "insert" "mroads" '(215 -43) 1 1 0 )
(command "insert" "mroads" '(260 -55) 1 1 0 )
(command "insert" "mroads" '(153 -27) 1 1 0 )
(command "insert" "mroads" '(201 -49) 1 1 0 )
(command "insert" "mroads" '(241 -90) 1 1 0 )
(command "insert" "mroads" '(204 -42) 1 1 0 )
(command "insert" "mroads" '(155 -29) 1 1 0 )
(command "insert" "mroads" '(201 -51) 1 1 0 )
(command "insert" "mroads" '(223 -72) 1 1 0 )
(command "insert" "mroads" '(237 -46) 1 1 0 )
(command "insert" "mroads" '(274 -56) 1 1 0 )
(command "insert" "mroads" '(157 -31) 1 1 0 )
(command "insert" "mroads" '(272 -65) 1 1 0 )
(command "insert" "mroads" '(249 -91) 1 1 0 )
(command "insert" "mroads" '(213 -69) 1 1 0 )
(command "insert" "mroads" '(234 -90) 1 1 0 )
(command "insert" "mroads" '(235 -88) 1 1 0 )
(command "insert" "mroads" '(207 -51) 1 1 0 )
(command "insert" "mroads" '(181 -44) 1 1 0 )
(command "insert" "mroads" '(204 -40) 1 1 0 )
(command "insert" "mroads" '(185 -41) 1 1 0 )
(command "insert" "mroads" '(250 -89) 1 1 0 )
(command "insert" "mroads" '(214 -67) 1 1 0 )
(command "insert" "mroads" '(188 -50) 1 1 0 )
(command "insert" "mroads" '(228 -73) 1 1 0 )
(command "insert" "mroads" '(183 -42) 1 1 0 )
(command "insert" "mroads" '(187 -47) 1 1 0 )
(command "insert" "mroads" '(252 -87) 1 1 0 )
(command "insert" "mroads" '(244 -52) 1 1 0 )
(command "insert" "mroads" '(243 -89) 1 1 0 )
(command "insert" "mroads" '(270 -64) 1 1 0 )
(command "insert" "mroads" '(255 -89) 1 1 0 )
(command "insert" "mroads" '(220 -45) 1 1 0 )
(command "insert" "mroads" '(192 -52) 1 1 0 )
(command "insert" "mroads" '(204 -60) 1 1 0 )
(command "insert" "mroads" '(219 -47) 1 1 0 )
(command "insert" "mroads" '(253 -48) 1 1 0 )
(command "insert" "mroads" '(155 -27) 1 1 0 )
(command "insert" "mroads" '(201 -58) 1 1 0 )
(command "insert" "mroads" '(204 -69) 1 1 0 )
(command "insert" "mroads" '(275 -65) 1 1 0 )
(command "insert" "mroads" '(222 -79) 1 1 0 )
(command "insert" "mroads" '(178 -44) 1 1 0 )
(command "insert" "mroads" '(268 -60) 1 1 0 )
(command "insert" "mroads" '(209 -42) 1 1 0 )
(command "insert" "mroads" '(264 -52) 1 1 0 )
(command "insert" "mroads" '(266 -51) 1 1 0 )
(command "insert" "mroads" '(234 -50) 1 1 0 )
(command "insert" "mroads" '(208 -65) 1 1 0 )
(command "insert" "mroads" '(254 -49) 1 1 0 )
(command "insert" "mroads" '(256 -55) 1 1 0 )
(command "insert" "mroads" '(231 -49) 1 1 0 )
(command "insert" "mroads" '(205 -62) 1 1 0 )
(command "insert" "mroads" '(249 -92) 1 1 0 )
(command "insert" "mroads" '(207 -56) 1 1 0 )
(command "insert" "mroads" '(274 -66) 1 1 0 )
(command "insert" "mroads" '(185 -50) 1 1 0 )
(command "insert" "mroads" '(175 -35) 1 1 0 )
(command "insert" "mroads" '(206 -39) 1 1 0 )
(command "insert" "mroads" '(237 -91) 1 1 0 )
(command "insert" "mroads" '(193 -50) 1 1 0 )
(command "insert" "mroads" '(183 -35) 1 1 0 )
(command "insert" "mroads" '(187 -36) 1 1 0 )
(command "insert" "mroads" '(244 -51) 1 1 0 )
(command "insert" "mroads" '(218 -42) 1 1 0 )
(command "insert" "mroads" '(257 -54) 1 1 0 )
(command "insert" "mroads" '(274 -58) 1 1 0 )
(command "insert" "mroads" '(195 -36) 1 1 0 )
(command "insert" "mroads" '(247 -53) 1 1 0 )
(command "insert" "mroads" '(189 -38) 1 1 0 )
(command "insert" "mroads" '(172 -34) 1 1 0 )
(command "insert" "mroads" '(265 -91) 1 1 0 )
(command "insert" "mroads" '(250 -52) 1 1 0 )
(command "insert" "mroads" '(224 -47) 1 1 0 )
(command "insert" "mroads" '(197 -38) 1 1 0 )
(command "insert" "mroads" '(245 -92) 1 1 0 )
(command "insert" "mroads" '(243 -48) 1 1 0 )
(command "insert" "mroads" '(191 -48) 1 1 0 )
(command "insert" "mroads" '(178 -39) 1 1 0 )
(command "insert" "mroads" '(226 -45) 1 1 0 )
(command "insert" "mroads" '(199 -48) 1 1 0 )
(command "insert" "mroads" '(247 -90) 1 1 0 )
(command "insert" "mroads" '(203 -53) 1 1 0 )
(command "insert" "mroads" '(208 -56) 1 1 0 )
(command "insert" "mroads" '(229 -77) 1 1 0 )
(command "insert" "mroads" '(170 -34) 1 1 0 )
(command "insert" "mroads" '(265 -56) 1 1 0 )
(command "insert" "mroads" '(202 -63) 1 1 0 )
(command "insert" "mroads" '(231 -46) 1 1 0 )
(command "insert" "mroads" '(205 -55) 1 1 0 )
(command "insert" "mroads" '(210 -66) 1 1 0 )
(command "insert" "mroads" '(242 -50) 1 1 0 )
(command "insert" "mroads" '(180 -37) 1 1 0 )
(command "insert" "mroads" '(170 -31) 1 1 0 )
(command "insert" "mroads" '(264 -88) 1 1 0 )
(command "insert" "mroads" '(238 -48) 1 1 0 )
(command "insert" "mroads" '(169 -34) 1 1 0 )
(command "insert" "mroads" '(225 -77) 1 1 0 )
(command "insert" "mroads" '(246 -48) 1 1 0 )
(command "insert" "mroads" '(265 -92) 1 1 0 )
(command "insert" "mroads" '(159 -31) 1 1 0 )
(command "insert" "mroads" '(166 -35) 1 1 0 )
(command "insert" "mroads" '(214 -41) 1 1 0 )
(command "insert" "mroads" '(200 -40) 1 1 0 )
(command "insert" "mroads" '(227 -83) 1 1 0 )
(command "insert" "mroads" '(201 -36) 1 1 0 )
(command "insert" "mroads" '(196 -52) 1 1 0 )
(command "insert" "mroads" '(214 -40) 1 1 0 )
(command "insert" "mroads" '(214 -70) 1 1 0 )
(command "insert" "mroads" '(257 -88) 1 1 0 )
(command "insert" "mroads" '(269 -88) 1 1 0 )
(command "insert" "mroads" '(267 -60) 1 1 0 )
(command "insert" "mroads" '(166 -31) 1 1 0 )
(command "insert" "mroads" '(194 -49) 1 1 0 )
(command "insert" "mroads" '(205 -48) 1 1 0 )
(command "insert" "mroads" '(236 -50) 1 1 0 )
(command "insert" "mroads" '(273 -56) 1 1 0 )
(command "insert" "mroads" '(261 -92) 1 1 0 )
(command "insert" "mroads" '(262 -90) 1 1 0 )
(command "insert" "mroads" '(158 -32) 1 1 0 )
(command "insert" "mroads" '(158 -27) 1 1 0 )
(command "insert" "mroads" '(206 -49) 1 1 0 )
(command "insert" "mroads" '(180 -44) 1 1 0 )
(command "insert" "mroads" '(184 -39) 1 1 0 )
(command "insert" "mroads" '(183 -49) 1 1 0 )
(command "insert" "mroads" '(224 -78) 1 1 0 )
(command "insert" "mroads" '(187 -50) 1 1 0 )
(command "insert" "mroads" '(268 -63) 1 1 0 )
(command "insert" "mroads" '(182 -46) 1 1 0 )
(command "insert" "mroads" '(212 -42) 1 1 0 )
(command "insert" "mroads" '(186 -37) 1 1 0 )
(command "insert" "mroads" '(225 -70) 1 1 0 )
(command "insert" "mroads" '(226 -76) 1 1 0 )
(command "insert" "mroads" '(202 -64) 1 1 0 )
(command "insert" "mroads" '(194 -37) 1 1 0 )
(command "insert" "mroads" '(197 -40) 1 1 0 )
(command "insert" "mroads" '(227 -88) 1 1 0 )
(command "insert" "mroads" '(256 -91) 1 1 0 )
(command "insert" "mroads" '(243 -49) 1 1 0 )
(command "insert" "mroads" '(232 -45) 1 1 0 )
(command "insert" "mroads" '(196 -51) 1 1 0 )
(command "insert" "mroads" '(252 -48) 1 1 0 )
(command "insert" "mroads" '(199 -38) 1 1 0 )
(command "insert" "mroads" '(270 -67) 1 1 0 )
(command "insert" "mroads" '(229 -82) 1 1 0 )
(command "insert" "mroads" '(253 -50) 1 1 0 )
(command "insert" "mroads" '(234 -47) 1 1 0 )
(command "insert" "mroads" '(208 -54) 1 1 0 )
(command "insert" "mroads" '(261 -52) 1 1 0 )
(command "insert" "mroads" '(154 -30) 1 1 0 )
(command "insert" "mroads" '(219 -68) 1 1 0 )
(command "insert" "mroads" '(202 -52) 1 1 0 )
(command "insert" "mroads" '(233 -50) 1 1 0 )
(command "insert" "mroads" '(205 -41) 1 1 0 )
(command "insert" "mroads" '(249 -53) 1 1 0 )
(command "insert" "mroads" '(221 -70) 1 1 0 )
(command "insert" "mroads" '(242 -46) 1 1 0 )
(command "insert" "mroads" '(223 -80) 1 1 0 )
(command "insert" "mroads" '(206 -56) 1 1 0 )
(command "insert" "mroads" '(180 -43) 1 1 0 )
(command "insert" "mroads" '(245 -89) 1 1 0 )
(command "insert" "mroads" '(184 -46) 1 1 0 )
(command "insert" "mroads" '(174 -33) 1 1 0 )
(command "insert" "mroads" '(224 -69) 1 1 0 )
(command "insert" "mroads" '(270 -61) 1 1 0 )
(command "insert" "mroads" '(269 -89) 1 1 0 )
(command "insert" "mroads" '(182 -33) 1 1 0 )
(command "insert" "mroads" '(267 -62) 1 1 0 )
(command "insert" "mroads" '(267 -58) 1 1 0 )
(command "insert" "mroads" '(150 -30) 1 1 0 )
(command "insert" "mroads" '(217 -42) 1 1 0 )
(command "insert" "mroads" '(189 -49) 1 1 0 )
(command "insert" "mroads" '(222 -66) 1 1 0 )
(command "insert" "mroads" '(259 -52) 1 1 0 )
(command "insert" "mroads" '(188 -42) 1 1 0 )
(command "insert" "mroads" '(171 -34) 1 1 0 )
(command "insert" "mroads" '(228 -81) 1 1 0 )
(command "insert" "mroads" '(191 -47) 1 1 0 )
(command "insert" "mroads" '(222 -43) 1 1 0 )
(command "insert" "mroads" '(190 -48) 1 1 0 )
(command "insert" "mroads" '(229 -91) 1 1 0 )
(command "insert" "mroads" '(221 -46) 1 1 0 )
(command "insert" "mroads" '(258 -88) 1 1 0 )
(command "insert" "mroads" '(225 -43) 1 1 0 )
(command "insert" "mroads" '(198 -48) 1 1 0 )
(command "insert" "mroads" '(220 -69) 1 1 0 )
(command "insert" "mroads" '(189 -47) 1 1 0 )
(command "insert" "mroads" '(273 -68) 1 1 0 )
(command "insert" "mroads" '(267 -67) 1 1 0 )
(command "insert" "mroads" '(222 -87) 1 1 0 )
(command "insert" "mroads" '(255 -54) 1 1 0 )
(command "insert" "mroads" '(238 -90) 1 1 0 )
(command "insert" "mroads" '(252 -51) 1 1 0 )
(command "insert" "mroads" '(223 -89) 1 1 0 )
(command "insert" "mroads" '(269 -62) 1 1 0 )
(command "insert" "mroads" '(256 -51) 1 1 0 )
(command "insert" "mroads" '(239 -90) 1 1 0 )
(command "insert" "mroads" '(167 -31) 1 1 0 )
(command "insert" "mroads" '(192 -53) 1 1 0 )
(command "insert" "mroads" '(223 -66) 1 1 0 )
(command "insert" "mroads" '(275 -61) 1 1 0 )
(command "insert" "mroads" '(225 -80) 1 1 0 )
(command "insert" "mroads" '(203 -64) 1 1 0 )
(command "insert" "mroads" '(219 -44) 1 1 0 )
(command "insert" "mroads" '(268 -54) 1 1 0 )
(command "insert" "mroads" '(188 -33) 1 1 0 )
(command "insert" "mroads" '(227 -70) 1 1 0 )
(command "insert" "mroads" '(228 -88) 1 1 0 )
(command "insert" "mroads" '(153 -30) 1 1 0 )
(command "insert" "mroads" '(239 -46) 1 1 0 )
(command "insert" "mroads" '(213 -39) 1 1 0 )
(command "insert" "mroads" '(196 -33) 1 1 0 )
(command "insert" "mroads" '(258 -92) 1 1 0 )
(command "insert" "mroads" '(173 -33) 1 1 0 )
(command "insert" "mroads" '(230 -82) 1 1 0 )
(command "insert" "mroads" '(177 -38) 1 1 0 )
(command "insert" "mroads" '(264 -55) 1 1 0 )
(command "insert" "mroads" '(225 -44) 1 1 0 )
(command "insert" "mroads" '(269 -67) 1 1 0 )
(command "insert" "mroads" '(228 -47) 1 1 0 )
(command "insert" "mroads" '(202 -38) 1 1 0 )
(command "insert" "mroads" '(241 -49) 1 1 0 )
(command "insert" "mroads" '(240 -90) 1 1 0 )
(command "insert" "mroads" '(230 -45) 1 1 0 )
(command "insert" "mroads" '(252 -91) 1 1 0 )
(command "insert" "mroads" '(174 -30) 1 1 0 )
(command "insert" "mroads" '(235 -50) 1 1 0 )
(command "insert" "mroads" '(209 -59) 1 1 0 )
(command "insert" "mroads" '(204 -39) 1 1 0 )
(command "insert" "mroads" '(223 -70) 1 1 0 )
(command "insert" "mroads" '(269 -55) 1 1 0 )
(command "insert" "mroads" '(245 -48) 1 1 0 )
(command "insert" "mroads" '(265 -54) 1 1 0 )
(command "insert" "mroads" '(224 -83) 1 1 0 )
(command "insert" "mroads" '(268 -65) 1 1 0 )
(command "insert" "mroads" '(248 -89) 1 1 0 )
(command "insert" "mroads" '(212 -71) 1 1 0 )
(command "insert" "mroads" '(169 -30) 1 1 0 )
(command "insert" "mroads" '(272 -55) 1 1 0 )
(command "insert" "mroads" '(226 -89) 1 1 0 )
(command "insert" "mroads" '(165 -33) 1 1 0 )
(command "insert" "mroads" '(181 -38) 1 1 0 )
(command "insert" "mroads" '(211 -42) 1 1 0 )
(command "insert" "mroads" '(185 -35) 1 1 0 )
(command "insert" "mroads" '(227 -79) 1 1 0 )
(command "insert" "mroads" '(228 -71) 1 1 0 )
(command "insert" "mroads" '(193 -35) 1 1 0 )
(command "insert" "mroads" '(196 -40) 1 1 0 )
(command "insert" "mroads" '(190 -34) 1 1 0 )
(command "insert" "mroads" '(203 -58) 1 1 0 )
(command "insert" "mroads" '(230 -85) 1 1 0 )
(command "insert" "mroads" '(195 -53) 1 1 0 )
(command "insert" "mroads" '(251 -48) 1 1 0 )
(command "insert" "mroads" '(206 -65) 1 1 0 )
(command "insert" "mroads" '(255 -87) 1 1 0 )
(command "insert" "mroads" '(263 -91) 1 1 0 )
(command "insert" "mroads" '(200 -36) 1 1 0 )
(command "insert" "mroads" '(165 -30) 1 1 0 )
(command "insert" "mroads" '(240 -47) 1 1 0 )
(command "insert" "mroads" '(209 -60) 1 1 0 )
(command "insert" "mroads" '(246 -91) 1 1 0 )
(command "insert" "mroads" '(242 -91) 1 1 0 )
(command "insert" "mroads" '(223 -79) 1 1 0 )
(command "insert" "mroads" '(222 -83) 1 1 0 )
(command "insert" "mroads" '(211 -66) 1 1 0 )
(command "insert" "mroads" '(252 -90) 1 1 0 )
(command "insert" "mroads" '(229 -74) 1 1 0 )
(command "insert" "mroads" '(227 -44) 1 1 0 )
(command "insert" "mroads" '(159 -28) 1 1 0 )
(command "insert" "mroads" '(226 -80) 1 1 0 )
(command "insert" "mroads" '(207 -54) 1 1 0 )
(command "insert" "mroads" '(181 -47) 1 1 0 )
(command "insert" "mroads" '(270 -58) 1 1 0 )
(command "insert" "mroads" '(185 -36) 1 1 0 )
(command "insert" "mroads" '(250 -90) 1 1 0 )
(command "insert" "mroads" '(251 -88) 1 1 0 )
(command "insert" "mroads" '(236 -89) 1 1 0 )
(command "insert" "mroads" '(228 -78) 1 1 0 )
(command "insert" "mroads" '(193 -36) 1 1 0 )
(command "insert" "mroads" '(183 -41) 1 1 0 )
(command "insert" "mroads" '(213 -41) 1 1 0 )
(command "insert" "mroads" '(187 -42) 1 1 0 )
(command "insert" "mroads" '(190 -37) 1 1 0 )
(command "insert" "mroads" '(230 -76) 1 1 0 )
(command "insert" "mroads" '(215 -39) 1 1 0 )
(command "insert" "mroads" '(198 -37) 1 1 0 )
(command "insert" "mroads" '(255 -92) 1 1 0 )
(command "insert" "mroads" '(202 -40) 1 1 0 )
(command "insert" "mroads" '(233 -46) 1 1 0 )
(command "insert" "mroads" '(260 -51) 1 1 0 )
(command "insert" "mroads" '(153 -31) 1 1 0 )
(command "insert" "mroads" '(264 -54) 1 1 0 )
(command "insert" "mroads" '(204 -38) 1 1 0 )
(command "insert" "mroads" '(272 -54) 1 1 0 )
(command "insert" "mroads" '(203 -59) 1 1 0 )
(command "insert" "mroads" '(254 -50) 1 1 0 )
(command "insert" "mroads" '(157 -27) 1 1 0 )
(command "insert" "mroads" '(233 -90) 1 1 0 )
(command "insert" "mroads" '(209 -70) 1 1 0 )
(command "insert" "mroads" '(266 -56) 1 1 0 )
(command "insert" "mroads" '(252 -89) 1 1 0 )
(command "insert" "mroads" '(235 -92) 1 1 0 )
(command "insert" "mroads" '(270 -56) 1 1 0 )
(command "insert" "mroads" '(181 -40) 1 1 0 )
(command "insert" "mroads" '(266 -92) 1 1 0 )
(command "insert" "mroads" '(185 -45) 1 1 0 )
(command "insert" "mroads" '(216 -45) 1 1 0 )
(command "insert" "mroads" '(183 -38) 1 1 0 )
(command "insert" "mroads" '(190 -38) 1 1 0 )
(command "insert" "mroads" '(270 -57) 1 1 0 )
(command "insert" "mroads" '(244 -48) 1 1 0 )
(command "insert" "mroads" '(218 -47) 1 1 0 )
(command "insert" "mroads" '(248 -51) 1 1 0 )
(command "insert" "mroads" '(253 -51) 1 1 0 )
(command "insert" "mroads" '(195 -35) 1 1 0 )
(command "insert" "mroads" '(229 -73) 1 1 0 )
(command "insert" "mroads" '(270 -68) 1 1 0 )
(command "insert" "mroads" '(267 -64) 1 1 0 )
(command "insert" "mroads" '(204 -48) 1 1 0 )
(command "insert" "mroads" '(176 -34) 1 1 0 )
(command "insert" "mroads" '(224 -44) 1 1 0 )
(command "insert" "mroads" '(223 -44) 1 1 0 )
(command "insert" "mroads" '(201 -62) 1 1 0 )
(command "insert" "mroads" '(241 -87) 1 1 0 )
(command "insert" "mroads" '(267 -88) 1 1 0 )
(command "insert" "mroads" '(178 -40) 1 1 0 )
(command "insert" "mroads" '(217 -67) 1 1 0 )
(command "insert" "mroads" '(247 -89) 1 1 0 )
(command "insert" "mroads" '(203 -48) 1 1 0 )
(command "insert" "mroads" '(271 -60) 1 1 0 )
(command "insert" "mroads" '(272 -56) 1 1 0 )
(command "insert" "mroads" '(208 -69) 1 1 0 )
(command "insert" "mroads" '(206 -69) 1 1 0 )
(command "insert" "mroads" '(254 -53) 1 1 0 )
(command "insert" "mroads" '(216 -46) 1 1 0 )
(command "insert" "mroads" '(176 -30) 1 1 0 )
(command "insert" "mroads" '(231 -45) 1 1 0 )
(command "insert" "mroads" '(268 -57) 1 1 0 )
(command "insert" "mroads" '(259 -91) 1 1 0 )
(command "insert" "mroads" '(273 -66) 1 1 0 )
(command "insert" "mroads" '(267 -59) 1 1 0 )
(command "insert" "mroads" '(259 -55) 1 1 0 )
(command "insert" "mroads" '(184 -42) 1 1 0 )
(command "insert" "mroads" '(206 -43) 1 1 0 )
(command "insert" "mroads" '(237 -87) 1 1 0 )
(command "insert" "mroads" '(256 -53) 1 1 0 )
(command "insert" "mroads" '(150 -29) 1 1 0 )
(command "insert" "mroads" '(218 -67) 1 1 0 )
(command "insert" "mroads" '(217 -47) 1 1 0 )
(command "insert" "mroads" '(238 -45) 1 1 0 )
(command "insert" "mroads" '(258 -55) 1 1 0 )
(command "insert" "mroads" '(259 -89) 1 1 0 )
(command "insert" "mroads" '(225 -72) 1 1 0 )
(command "insert" "mroads" '(161 -27) 1 1 0 )
(command "insert" "mroads" '(172 -30) 1 1 0 )
(command "insert" "mroads" '(266 -87) 1 1 0 )
(command "insert" "mroads" '(250 -48) 1 1 0 )
(command "insert" "mroads" '(214 -42) 1 1 0 )
(command "insert" "mroads" '(197 -34) 1 1 0 )
(command "insert" "mroads" '(245 -88) 1 1 0 )
(command "insert" "mroads" '(201 -39) 1 1 0 )
(command "insert" "mroads" '(178 -35) 1 1 0 )
(command "insert" "mroads" '(217 -68) 1 1 0 )
(command "insert" "mroads" '(209 -39) 1 1 0 )
(command "insert" "mroads" '(244 -49) 1 1 0 )
(command "insert" "mroads" '(257 -91) 1 1 0 )
(command "insert" "mroads" '(201 -48) 1 1 0 )
(command "insert" "mroads" '(208 -60) 1 1 0 )
(command "insert" "mroads" '(270 -66) 1 1 0 )
(command "insert" "mroads" '(205 -51) 1 1 0 )
(command "insert" "mroads" '(248 -52) 1 1 0 )
(command "insert" "mroads" '(182 -31) 1 1 0 )
(command "insert" "mroads" '(240 -50) 1 1 0 )
(command "insert" "mroads" '(261 -53) 1 1 0 )
(command "insert" "mroads" '(222 -69) 1 1 0 )
(command "insert" "mroads" '(179 -36) 1 1 0 )
(command "insert" "mroads" '(200 -50) 1 1 0 )
(command "insert" "mroads" '(206 -50) 1 1 0 )
(command "insert" "mroads" '(180 -33) 1 1 0 )
(command "insert" "mroads" '(245 -52) 1 1 0 )
(command "insert" "mroads" '(263 -89) 1 1 0 )
(command "insert" "mroads" '(224 -75) 1 1 0 )
(command "insert" "mroads" '(187 -49) 1 1 0 )
(command "insert" "mroads" '(189 -45) 1 1 0 )
(command "insert" "mroads" '(192 -36) 1 1 0 )
(command "insert" "mroads" '(182 -43) 1 1 0 )
(command "insert" "mroads" '(186 -38) 1 1 0 )
(command "insert" "mroads" '(209 -62) 1 1 0 )
(command "insert" "mroads" '(246 -52) 1 1 0 )
(command "insert" "mroads" '(194 -38) 1 1 0 )
(command "insert" "mroads" '(216 -71) 1 1 0 )
(command "insert" "mroads" '(206 -44) 1 1 0 )
(command "insert" "mroads" '(162 -31) 1 1 0 )
(command "insert" "mroads" '(227 -87) 1 1 0 )
(command "insert" "mroads" '(201 -40) 1 1 0 )
(command "insert" "mroads" '(256 -88) 1 1 0 )
(command "insert" "mroads" '(275 -66) 1 1 0 )
(command "insert" "mroads" '(268 -88) 1 1 0 )
(command "insert" "mroads" '(252 -53) 1 1 0 )
(command "insert" "mroads" '(218 -69) 1 1 0 )
(command "insert" "mroads" '(199 -37) 1 1 0 )
(command "insert" "mroads" '(229 -85) 1 1 0 )
(command "insert" "mroads" '(257 -92) 1 1 0 )
(command "insert" "mroads" '(208 -51) 1 1 0 )
(command "insert" "mroads" '(261 -55) 1 1 0 )
(command "insert" "mroads" '(219 -67) 1 1 0 )
(command "insert" "mroads" '(268 -64) 1 1 0 )
(command "insert" "mroads" '(205 -44) 1 1 0 )
(command "insert" "mroads" '(260 -92) 1 1 0 )
(command "insert" "mroads" '(236 -46) 1 1 0 )
(command "insert" "mroads" '(273 -60) 1 1 0 )
(command "insert" "mroads" '(156 -29) 1 1 0 )
(command "insert" "mroads" '(207 -41) 1 1 0 )
(command "insert" "mroads" '(261 -88) 1 1 0 )
(command "insert" "mroads" '(268 -90) 1 1 0 )
(command "insert" "mroads" '(158 -31) 1 1 0 )
(command "insert" "mroads" '(223 -87) 1 1 0 )
(command "insert" "mroads" '(206 -53) 1 1 0 )
(command "insert" "mroads" '(180 -40) 1 1 0 )
(command "insert" "mroads" '(184 -43) 1 1 0 )
(command "insert" "mroads" '(174 -34) 1 1 0 )
(command "insert" "mroads" '(224 -66) 1 1 0 )
(command "insert" "mroads" '(258 -87) 1 1 0 )
(command "insert" "mroads" '(201 -64) 1 1 0 )
(command "insert" "mroads" '(182 -34) 1 1 0 )
(command "insert" "mroads" '(211 -70) 1 1 0 )
(command "insert" "mroads" '(186 -33) 1 1 0 )
(command "insert" "mroads" '(225 -90) 1 1 0 )
(command "insert" "mroads" '(226 -72) 1 1 0 )
(command "insert" "mroads" '(189 -52) 1 1 0 )
(command "insert" "mroads" '(266 -89) 1 1 0 )
(command "insert" "mroads" '(264 -90) 1 1 0 )
(command "insert" "mroads" '(188 -47) 1 1 0 )
(command "insert" "mroads" '(171 -33) 1 1 0 )
(command "insert" "mroads" '(227 -92) 1 1 0 )
(command "insert" "mroads" '(219 -43) 1 1 0 )
(command "insert" "mroads" '(191 -34) 1 1 0 )
(command "insert" "mroads" '(268 -87) 1 1 0 )
(command "insert" "mroads" '(203 -39) 1 1 0 )
(command "insert" "mroads" '(177 -40) 1 1 0 )
(command "insert" "mroads" '(208 -42) 1 1 0 )
(command "insert" "mroads" '(202 -48) 1 1 0 )
(command "insert" "mroads" '(231 -88) 1 1 0 )
(command "insert" "mroads" '(205 -37) 1 1 0 )
(command "insert" "mroads" '(260 -91) 1 1 0 )
(command "insert" "mroads" '(272 -66) 1 1 0 )
(command "insert" "mroads" '(226 -47) 1 1 0 )
(command "insert" "mroads" '(221 -66) 1 1 0 )
(command "insert" "mroads" '(242 -49) 1 1 0 )
(command "insert" "mroads" '(255 -53) 1 1 0 )
(command "insert" "mroads" '(238 -87) 1 1 0 )
(command "insert" "mroads" '(206 -60) 1 1 0 )
(command "insert" "mroads" '(184 -50) 1 1 0 )
(command "insert" "mroads" '(239 -89) 1 1 0 )
(command "insert" "mroads" '(224 -89) 1 1 0 )
(command "insert" "mroads" '(205 -67) 1 1 0 )
(command "insert" "mroads" '(192 -50) 1 1 0 )
(command "insert" "mroads" '(182 -37) 1 1 0 )
(command "insert" "mroads" '(209 -53) 1 1 0 )
(command "insert" "mroads" '(225 -83) 1 1 0 )
(command "insert" "mroads" '(226 -67) 1 1 0 )
(command "insert" "mroads" '(207 -39) 1 1 0 )
(command "insert" "mroads" '(215 -44) 1 1 0 )
(command "insert" "mroads" '(188 -38) 1 1 0 )
(command "insert" "mroads" '(245 -51) 1 1 0 )
(command "insert" "mroads" '(249 -48) 1 1 0 )
(command "insert" "mroads" '(239 -45) 1 1 0 )
(command "insert" "mroads" '(267 -68) 1 1 0 )
(command "insert" "mroads" '(196 -38) 1 1 0 )
(command "insert" "mroads" '(190 -52) 1 1 0 )
(command "insert" "mroads" '(273 -67) 1 1 0 )
(command "insert" "mroads" '(206 -41) 1 1 0 )
(command "insert" "mroads" '(221 -42) 1 1 0 )
(command "insert" "mroads" '(177 -33) 1 1 0 )
(command "insert" "mroads" '(225 -47) 1 1 0 )
(command "insert" "mroads" '(198 -52) 1 1 0 )
(command "insert" "mroads" '(202 -59) 1 1 0 )
(command "insert" "mroads" '(210 -43) 1 1 0 )
(command "insert" "mroads" '(263 -55) 1 1 0 )
(command "insert" "mroads" '(230 -46) 1 1 0 )
(command "insert" "mroads" '(204 -53) 1 1 0 )
(command "insert" "mroads" '(235 -49) 1 1 0 )
(command "insert" "mroads" '(259 -87) 1 1 0 )
(command "insert" "mroads" '(160 -27) 1 1 0 )
(command "insert" "mroads" '(269 -58) 1 1 0 )
(command "insert" "mroads" '(224 -80) 1 1 0 )
(command "insert" "mroads" '(179 -35) 1 1 0 )
(command "insert" "mroads" '(268 -58) 1 1 0 )
(command "insert" "mroads" '(212 -68) 1 1 0 )
(command "insert" "mroads" '(186 -51) 1 1 0 )
(command "insert" "mroads" '(225 -84) 1 1 0 )
(command "insert" "mroads" '(226 -90) 1 1 0 )
(command "insert" "mroads" '(207 -44) 1 1 0 )
(command "insert" "mroads" '(211 -41) 1 1 0 )
(command "insert" "mroads" '(194 -51) 1 1 0 )
(command "insert" "mroads" '(168 -34) 1 1 0 )
(command "insert" "mroads" '(171 -31) 1 1 0 )
(command "insert" "mroads" '(227 -74) 1 1 0 )
(command "insert" "mroads" '(243 -50) 1 1 0 )
(command "insert" "mroads" '(273 -65) 1 1 0 )
(command "insert" "mroads" '(205 -70) 1 1 0 )
(command "insert" "mroads" '(200 -49) 1 1 0 )
(command "insert" "mroads" '(217 -43) 1 1 0 )
(command "insert" "mroads" '(226 -43) 1 1 0 )
(command "insert" "mroads" '(230 -86) 1 1 0 )
(command "insert" "mroads" '(195 -48) 1 1 0 )
(command "insert" "mroads" '(206 -66) 1 1 0 )
(command "insert" "mroads" '(254 -88) 1 1 0 )
(command "insert" "mroads" '(207 -55) 1 1 0 )
(command "insert" "mroads" '(260 -52) 1 1 0 )
(command "insert" "mroads" '(271 -56) 1 1 0 )
(command "insert" "mroads" '(267 -56) 1 1 0 )
(command "insert" "mroads" '(204 -44) 1 1 0 )
(command "insert" "mroads" '(271 -55) 1 1 0 )
(command "insert" "mroads" '(209 -63) 1 1 0 )
(command "insert" "mroads" '(181 -30) 1 1 0 )
(command "insert" "mroads" '(244 -53) 1 1 0 )
(command "insert" "mroads" '(242 -92) 1 1 0 )
(command "insert" "mroads" '(191 -35) 1 1 0 )
(command "insert" "mroads" '(274 -62) 1 1 0 )
(command "insert" "mroads" '(232 -90) 1 1 0 )
(command "insert" "mroads" '(224 -87) 1 1 0 )
(command "insert" "mroads" '(179 -40) 1 1 0 )
(command "insert" "mroads" '(248 -48) 1 1 0 )
(command "insert" "mroads" '(212 -67) 1 1 0 )
(command "insert" "mroads" '(226 -85) 1 1 0 )
(command "insert" "mroads" '(207 -53) 1 1 0 )
(command "insert" "mroads" '(181 -34) 1 1 0 )
(command "insert" "mroads" '(185 -39) 1 1 0 )
(command "insert" "mroads" '(188 -52) 1 1 0 )
(command "insert" "mroads" '(183 -44) 1 1 0 )
(command "insert" "mroads" '(213 -44) 1 1 0 )
(command "insert" "mroads" '(219 -45) 1 1 0 )
(command "insert" "mroads" '(170 -35) 1 1 0 )
(command "insert" "mroads" '(204 -57) 1 1 0 )
(command "insert" "mroads" '(247 -51) 1 1 0 )
(command "insert" "mroads" '(230 -73) 1 1 0 )
(command "insert" "mroads" '(167 -32) 1 1 0 )
(command "insert" "mroads" '(272 -63) 1 1 0 )
(command "insert" "mroads" '(215 -42) 1 1 0 )
(command "insert" "mroads" '(198 -38) 1 1 0 )
(command "insert" "mroads" '(211 -71) 1 1 0 )
(command "insert" "mroads" '(197 -51) 1 1 0 )
(command "insert" "mroads" '(264 -51) 1 1 0 )
(command "insert" "mroads" '(204 -68) 1 1 0 )
(command "insert" "mroads" '(232 -50) 1 1 0 )
(command "insert" "mroads" '(204 -43) 1 1 0 )
(command "insert" "mroads" '(235 -47) 1 1 0 )
(command "insert" "mroads" '(155 -28) 1 1 0 )
(command "insert" "mroads" '(242 -87) 1 1 0 )
(command "insert" "mroads" '(223 -75) 1 1 0 )
(command "insert" "mroads" '(237 -45) 1 1 0 )
(command "insert" "mroads" '(274 -57) 1 1 0 )
(command "insert" "mroads" '(256 -54) 1 1 0 )
(command "insert" "mroads" '(157 -30) 1 1 0 )
(command "insert" "mroads" '(209 -65) 1 1 0 )
(command "insert" "mroads" '(243 -51) 1 1 0 )
(command "insert" "mroads" '(249 -90) 1 1 0 )
(command "insert" "mroads" '(213 -68) 1 1 0 )
(command "insert" "mroads" '(234 -91) 1 1 0 )
(command "insert" "mroads" '(235 -91) 1 1 0 )
(command "insert" "mroads" '(181 -43) 1 1 0 )
(command "insert" "mroads" '(185 -40) 1 1 0 )
(command "insert" "mroads" '(251 -92) 1 1 0 )
(command "insert" "mroads" '(216 -42) 1 1 0 )
(command "insert" "mroads" '(188 -51) 1 1 0 )
(command "insert" "mroads" '(228 -74) 1 1 0 )
(command "insert" "mroads" '(230 -90) 1 1 0 )
(command "insert" "mroads" '(187 -46) 1 1 0 )
(command "insert" "mroads" '(237 -49) 1 1 0 )
(command "insert" "mroads" '(151 -28) 1 1 0 )
(command "insert" "mroads" '(203 -41) 1 1 0 )
(command "insert" "mroads" '(257 -55) 1 1 0 )
(command "insert" "mroads" '(274 -61) 1 1 0 )
(command "insert" "mroads" '(243 -88) 1 1 0 )
(command "insert" "mroads" '(250 -87) 1 1 0 )
(command "insert" "mroads" '(270 -65) 1 1 0 )
(command "insert" "mroads" '(255 -88) 1 1 0 )
(command "insert" "mroads" '(220 -46) 1 1 0 )
(command "insert" "mroads" '(201 -57) 1 1 0 )
(command "insert" "mroads" '(197 -52) 1 1 0 )
(command "layer" "m" "edge" "" )
(command "insert" "edge" '(153 -16) 1 1 0 )
(command "insert" "edge" '(150 -23) 1 1 0 )
(command "insert" "edge" '(155 -21) 1 1 0 )
(command "insert" "edge" '(154 -23) 1 1 0 )
(command "insert" "edge" '(160 -19) 1 1 0 )
(command "insert" "edge" '(156 -22) 1 1 0 )
(command "insert" "edge" '(161 -18) 1 1 0 )
(command "insert" "edge" '(150 -9) 1 1 0 )
(command "insert" "edge" '(157 -23) 1 1 0 )
(command "insert" "edge" '(155 -11) 1 1 0 )
(command "insert" "edge" '(151 -12) 1 1 0 )
(command "insert" "edge" '(156 -12) 1 1 0 )
(command "insert" "edge" '(152 -18) 1 1 0 )
(command "insert" "edge" '(159 -18) 1 1 0 )
(command "insert" "edge" '(153 -19) 1 1 0 )
(command "insert" "edge" '(150 -16) 1 1 0 )
(command "insert" "edge" '(155 -16) 1 1 0 )
(command "insert" "edge" '(151 -21) 1 1 0 )
(command "insert" "edge" '(150 -10) 1 1 0 )
(command "insert" "edge" '(151 -22) 1 1 0 )
(command "insert" "edge" '(151 -15) 1 1 0 )
(command "insert" "edge" '(159 -11) 1 1 0 )
(command "insert" "edge" '(151 -19) 1 1 0 )
(command "insert" "edge" '(158 -20) 1 1 0 )
(command "insert" "edge" '(152 -15) 1 1 0 )
(command "insert" "edge" '(159 -17) 1 1 0 )
(command "insert" "edge" '(153 -14) 1 1 0 )
(command "insert" "edge" '(154 -13) 1 1 0 )
(command "insert" "edge" '(157 -16) 1 1 0 )
(command "insert" "edge" '(158 -15) 1 1 0 )
(command "insert" "edge" '(156 -11) 1 1 0 )
(command "insert" "edge" '(161 -13) 1 1 0 )
(command "insert" "edge" '(159 -14) 1 1 0 )
(command "insert" "edge" '(157 -10) 1 1 0 )
(command "insert" "edge" '(158 -17) 1 1 0 )
(command "insert" "edge" '(153 -20) 1 1 0 )
(command "insert" "edge" '(152 -12) 1 1 0 )
(command "insert" "edge" '(159 -20) 1 1 0 )
(command "insert" "edge" '(154 -19) 1 1 0 )
(command "insert" "edge" '(153 -9) 1 1 0 )
(command "insert" "edge" '(160 -23) 1 1 0 )
(command "insert" "edge" '(156 -18) 1 1 0 )
(command "insert" "edge" '(154 -14) 1 1 0 )
(command "insert" "edge" '(161 -22) 1 1 0 )
(command "insert" "edge" '(150 -13) 1 1 0 )
(command "insert" "edge" '(157 -19) 1 1 0 )
(command "insert" "edge" '(155 -15) 1 1 0 )
(command "insert" "edge" '(160 -13) 1 1 0 )
(command "insert" "edge" '(160 -18) 1 1 0 )
(command "insert" "edge" '(160 -9) 1 1 0 )
(command "insert" "edge" '(159 -13) 1 1 0 )
(command "insert" "edge" '(157 -13) 1 1 0 )
(command "insert" "edge" '(152 -22) 1 1 0 )
(command "insert" "edge" '(158 -18) 1 1 0 )
(command "insert" "edge" '(153 -23) 1 1 0 )
(command "insert" "edge" '(152 -9) 1 1 0 )
(command "insert" "edge" '(150 -20) 1 1 0 )
(command "insert" "edge" '(155 -20) 1 1 0 )
(command "insert" "edge" '(154 -20) 1 1 0 )
(command "insert" "edge" '(160 -20) 1 1 0 )
(command "insert" "edge" '(156 -23) 1 1 0 )
(command "insert" "edge" '(161 -17) 1 1 0 )
(command "insert" "edge" '(150 -14) 1 1 0 )
(command "insert" "edge" '(157 -22) 1 1 0 )
(command "insert" "edge" '(155 -10) 1 1 0 )
(command "insert" "edge" '(160 -10) 1 1 0 )
(command "insert" "edge" '(156 -13) 1 1 0 )
(command "insert" "edge" '(161 -11) 1 1 0 )
(command "insert" "edge" '(152 -19) 1 1 0 )
(command "insert" "edge" '(153 -18) 1 1 0 )
(command "insert" "edge" '(150 -17) 1 1 0 )
(command "insert" "edge" '(155 -19) 1 1 0 )
(command "insert" "edge" '(154 -9) 1 1 0 )
(command "insert" "edge" '(151 -20) 1 1 0 )
(command "insert" "edge" '(156 -20) 1 1 0 )
(command "insert" "edge" '(150 -11) 1 1 0 )
(command "insert" "edge" '(155 -9) 1 1 0 )
(command "insert" "edge" '(159 -10) 1 1 0 )
(command "insert" "edge" '(160 -17) 1 1 0 )
(command "insert" "edge" '(158 -21) 1 1 0 )
(command "insert" "edge" '(152 -16) 1 1 0 )
(command "insert" "edge" '(159 -16) 1 1 0 )
(command "insert" "edge" '(153 -13) 1 1 0 )
(command "insert" "edge" '(150 -18) 1 1 0 )
(command "insert" "edge" '(151 -18) 1 1 0 )
(command "insert" "edge" '(151 -11) 1 1 0 )
(command "insert" "edge" '(158 -12) 1 1 0 )
(command "insert" "edge" '(161 -12) 1 1 0 )
(command "insert" "edge" '(159 -9) 1 1 0 )
(command "insert" "edge" '(157 -9) 1 1 0 )
(command "insert" "edge" '(158 -22) 1 1 0 )
(command "insert" "edge" '(152 -13) 1 1 0 )
(command "insert" "edge" '(159 -23) 1 1 0 )
(command "insert" "edge" '(154 -16) 1 1 0 )
(command "insert" "edge" '(156 -19) 1 1 0 )
(command "insert" "edge" '(154 -15) 1 1 0 )
(command "insert" "edge" '(161 -21) 1 1 0 )
(command "insert" "edge" '(157 -18) 1 1 0 )
(command "insert" "edge" '(155 -14) 1 1 0 )
(command "insert" "edge" '(160 -14) 1 1 0 )
(command "insert" "edge" '(158 -9) 1 1 0 )
(command "insert" "edge" '(156 -9) 1 1 0 )
(command "insert" "edge" '(161 -15) 1 1 0 )
(command "insert" "edge" '(159 -12) 1 1 0 )
(command "insert" "edge" '(157 -12) 1 1 0 )
(command "insert" "edge" '(160 -16) 1 1 0 )
(command "insert" "edge" '(152 -23) 1 1 0 )
(command "insert" "edge" '(158 -19) 1 1 0 )
(command "insert" "edge" '(153 -22) 1 1 0 )
(command "insert" "edge" '(152 -10) 1 1 0 )
(command "insert" "edge" '(150 -21) 1 1 0 )
(command "insert" "edge" '(155 -23) 1 1 0 )
(command "insert" "edge" '(154 -21) 1 1 0 )
(command "insert" "edge" '(153 -11) 1 1 0 )
(command "insert" "edge" '(160 -21) 1 1 0 )
(command "insert" "edge" '(156 -16) 1 1 0 )
(command "insert" "edge" '(161 -16) 1 1 0 )
(command "insert" "edge" '(150 -15) 1 1 0 )
(command "insert" "edge" '(157 -21) 1 1 0 )
(command "insert" "edge" '(155 -13) 1 1 0 )
(command "insert" "edge" '(151 -14) 1 1 0 )
(command "insert" "edge" '(158 -10) 1 1 0 )
(command "insert" "edge" '(156 -14) 1 1 0 )
(command "insert" "edge" '(161 -10) 1 1 0 )
(command "insert" "edge" '(157 -15) 1 1 0 )
(command "insert" "edge" '(152 -20) 1 1 0 )
(command "insert" "edge" '(153 -17) 1 1 0 )
(command "insert" "edge" '(150 -22) 1 1 0 )
(command "insert" "edge" '(155 -18) 1 1 0 )
(command "insert" "edge" '(154 -22) 1 1 0 )
(command "insert" "edge" '(151 -23) 1 1 0 )
(command "insert" "edge" '(156 -21) 1 1 0 )
(command "insert" "edge" '(161 -19) 1 1 0 )
(command "insert" "edge" '(151 -13) 1 1 0 )
(command "insert" "edge" '(152 -17) 1 1 0 )
(command "insert" "edge" '(159 -19) 1 1 0 )
(command "insert" "edge" '(153 -12) 1 1 0 )
(command "insert" "edge" '(150 -19) 1 1 0 )
(command "insert" "edge" '(155 -17) 1 1 0 )
(command "insert" "edge" '(154 -11) 1 1 0 )
(command "insert" "edge" '(151 -16) 1 1 0 )
(command "insert" "edge" '(160 -12) 1 1 0 )
(command "insert" "edge" '(158 -13) 1 1 0 )
(command "insert" "edge" '(158 -23) 1 1 0 )
(command "insert" "edge" '(152 -14) 1 1 0 )
(command "insert" "edge" '(159 -22) 1 1 0 )
(command "insert" "edge" '(154 -17) 1 1 0 )
(command "insert" "edge" '(153 -15) 1 1 0 )
(command "insert" "edge" '(154 -12) 1 1 0 )
(command "insert" "edge" '(161 -20) 1 1 0 )
(command "insert" "edge" '(157 -17) 1 1 0 )
(command "insert" "edge" '(160 -15) 1 1 0 )
(command "insert" "edge" '(158 -14) 1 1 0 )
(command "insert" "edge" '(151 -10) 1 1 0 )
(command "insert" "edge" '(156 -10) 1 1 0 )
(command "insert" "edge" '(154 -10) 1 1 0 )
(command "insert" "edge" '(161 -14) 1 1 0 )
(command "insert" "edge" '(159 -15) 1 1 0 )
(command "insert" "edge" '(157 -11) 1 1 0 )
(command "insert" "edge" '(158 -16) 1 1 0 )
(command "insert" "edge" '(153 -21) 1 1 0 )
(command "insert" "edge" '(152 -11) 1 1 0 )
(command "insert" "edge" '(159 -21) 1 1 0 )
(command "insert" "edge" '(155 -22) 1 1 0 )
(command "insert" "edge" '(154 -18) 1 1 0 )
(command "insert" "edge" '(153 -10) 1 1 0 )
(command "insert" "edge" '(160 -22) 1 1 0 )
(command "insert" "edge" '(156 -17) 1 1 0 )
(command "insert" "edge" '(161 -23) 1 1 0 )
(command "insert" "edge" '(150 -12) 1 1 0 )
(command "insert" "edge" '(157 -20) 1 1 0 )
(command "insert" "edge" '(151 -17) 1 1 0 )
(command "insert" "edge" '(155 -12) 1 1 0 )
(command "insert" "edge" '(160 -11) 1 1 0 )
(command "insert" "edge" '(151 -9) 1 1 0 )
(command "insert" "edge" '(158 -11) 1 1 0 )
(command "insert" "edge" '(156 -15) 1 1 0 )
(command "insert" "edge" '(161 -9) 1 1 0 )
(command "insert" "edge" '(157 -14) 1 1 0 )
(command "insert" "edge" '(152 -21) 1 1 0 )
(command "layer" "m" "ped" "" )
(command "insert" "ped" '(46 -42) 1 1 0 )
(command "insert" "ped" '(56 -38) 1 1 0 )
(command "insert" "ped" '(40 -41) 1 1 0 )
(command "insert" "ped" '(64 -38) 1 1 0 )
(command "insert" "ped" '(79 -38) 1 1 0 )
(command "insert" "ped" '(84 -41) 1 1 0 )
(command "insert" "ped" '(58 -36) 1 1 0 )
(command "insert" "ped" '(90 -42) 1 1 0 )
(command "insert" "ped" '(64 -41) 1 1 0 )
(command "insert" "ped" '(62 -38) 1 1 0 )
(command "insert" "ped" '(61 -38) 1 1 0 )
(command "insert" "ped" '(69 -41) 1 1 0 )
(command "insert" "ped" '(68 -39) 1 1 0 )
(command "insert" "ped" '(48 -37) 1 1 0 )
(command "insert" "ped" '(63 -39) 1 1 0 )
(command "insert" "ped" '(95 -41) 1 1 0 )
(command "insert" "ped" '(69 -38) 1 1 0 )
(command "insert" "ped" '(93 -41) 1 1 0 )
(command "insert" "ped" '(71 -39) 1 1 0 )
(command "insert" "ped" '(76 -43) 1 1 0 )
(command "insert" "ped" '(82 -40) 1 1 0 )
(command "insert" "ped" '(63 -33) 1 1 0 )
(command "insert" "ped" '(77 -42) 1 1 0 )
(command "insert" "ped" '(47 -40) 1 1 0 )
(command "insert" "ped" '(52 -37) 1 1 0 )
(command "insert" "ped" '(49 -38) 1 1 0 )
(command "insert" "ped" '(83 -40) 1 1 0 )
(command "insert" "ped" '(55 -37) 1 1 0 )
(command "insert" "ped" '(96 -38) 1 1 0 )
(command "insert" "ped" '(86 -41) 1 1 0 )
(command "insert" "ped" '(44 -36) 1 1 0 )
(command "insert" "ped" '(73 -36) 1 1 0 )
(command "insert" "ped" '(97 -39) 1 1 0 )
(command "insert" "ped" '(96 -41) 1 1 0 )
(command "insert" "ped" '(70 -44) 1 1 0 )
(command "insert" "ped" '(99 -36) 1 1 0 )
(command "insert" "ped" '(98 -36) 1 1 0 )
(command "insert" "ped" '(71 -41) 1 1 0 )
(command "insert" "ped" '(45 -44) 1 1 0 )
(command "insert" "ped" '(75 -42) 1 1 0 )
(command "insert" "ped" '(81 -41) 1 1 0 )
(command "insert" "ped" '(101 -38) 1 1 0 )
(command "insert" "ped" '(65 -39) 1 1 0 )
(command "insert" "ped" '(103 -39) 1 1 0 )
(command "insert" "ped" '(70 -39) 1 1 0 )
(command "insert" "ped" '(46 -43) 1 1 0 )
(command "insert" "ped" '(78 -36) 1 1 0 )
(command "insert" "ped" '(57 -38) 1 1 0 )
(command "insert" "ped" '(64 -39) 1 1 0 )
(command "insert" "ped" '(58 -37) 1 1 0 )
(command "insert" "ped" '(65 -38) 1 1 0 )
(command "insert" "ped" '(67 -39) 1 1 0 )
(command "insert" "ped" '(61 -37) 1 1 0 )
(command "insert" "ped" '(69 -40) 1 1 0 )
(command "insert" "ped" '(48 -38) 1 1 0 )
(command "insert" "ped" '(63 -38) 1 1 0 )
(command "insert" "ped" '(95 -37) 1 1 0 )
(command "insert" "ped" '(95 -40) 1 1 0 )
(command "insert" "ped" '(69 -37) 1 1 0 )
(command "insert" "ped" '(93 -40) 1 1 0 )
(command "insert" "ped" '(74 -42) 1 1 0 )
(command "insert" "ped" '(71 -38) 1 1 0 )
(command "insert" "ped" '(70 -42) 1 1 0 )
(command "insert" "ped" '(50 -36) 1 1 0 )
(command "insert" "ped" '(76 -36) 1 1 0 )
(command "insert" "ped" '(82 -41) 1 1 0 )
(command "insert" "ped" '(103 -41) 1 1 0 )
(command "insert" "ped" '(70 -38) 1 1 0 )
(command "insert" "ped" '(51 -37) 1 1 0 )
(command "insert" "ped" '(47 -43) 1 1 0 )
(command "insert" "ped" '(52 -38) 1 1 0 )
(command "insert" "ped" '(64 -33) 1 1 0 )
(command "insert" "ped" '(59 -33) 1 1 0 )
(command "insert" "ped" '(42 -38) 1 1 0 )
(command "insert" "ped" '(91 -44) 1 1 0 )
(command "insert" "ped" '(72 -42) 1 1 0 )
(command "insert" "ped" '(96 -39) 1 1 0 )
(command "insert" "ped" '(44 -37) 1 1 0 )
(command "insert" "ped" '(73 -43) 1 1 0 )
(command "insert" "ped" '(97 -38) 1 1 0 )
(command "insert" "ped" '(104 -39) 1 1 0 )
(command "insert" "ped" '(98 -37) 1 1 0 )
(command "insert" "ped" '(71 -40) 1 1 0 )
(command "insert" "ped" '(81 -40) 1 1 0 )
(command "insert" "ped" '(102 -39) 1 1 0 )
(command "insert" "ped" '(101 -37) 1 1 0 )
(command "insert" "ped" '(65 -33) 1 1 0 )
(command "insert" "ped" '(46 -40) 1 1 0 )
(command "insert" "ped" '(90 -43) 1 1 0 )
(command "insert" "ped" '(78 -37) 1 1 0 )
(command "insert" "ped" '(57 -37) 1 1 0 )
(command "insert" "ped" '(59 -38) 1 1 0 )
(command "insert" "ped" '(58 -34) 1 1 0 )
(command "insert" "ped" '(90 -40) 1 1 0 )
(command "insert" "ped" '(59 -37) 1 1 0 )
(command "insert" "ped" '(60 -33) 1 1 0 )
(command "insert" "ped" '(90 -39) 1 1 0 )
(command "insert" "ped" '(62 -36) 1 1 0 )
(command "insert" "ped" '(61 -36) 1 1 0 )
(command "insert" "ped" '(85 -39) 1 1 0 )
(command "insert" "ped" '(64 -35) 1 1 0 )
(command "insert" "ped" '(73 -44) 1 1 0 )
(command "insert" "ped" '(72 -36) 1 1 0 )
(command "insert" "ped" '(70 -36) 1 1 0 )
(command "insert" "ped" '(69 -36) 1 1 0 )
(command "insert" "ped" '(93 -39) 1 1 0 )
(command "insert" "ped" '(74 -43) 1 1 0 )
(command "insert" "ped" '(80 -36) 1 1 0 )
(command "insert" "ped" '(70 -43) 1 1 0 )
(command "insert" "ped" '(50 -37) 1 1 0 )
(command "insert" "ped" '(74 -38) 1 1 0 )
(command "insert" "ped" '(76 -37) 1 1 0 )
(command "insert" "ped" '(103 -40) 1 1 0 )
(command "insert" "ped" '(51 -36) 1 1 0 )
(command "insert" "ped" '(47 -42) 1 1 0 )
(command "insert" "ped" '(47 -39) 1 1 0 )
(command "insert" "ped" '(54 -38) 1 1 0 )
(command "insert" "ped" '(53 -38) 1 1 0 )
(command "insert" "ped" '(43 -36) 1 1 0 )
(command "insert" "ped" '(57 -35) 1 1 0 )
(command "insert" "ped" '(64 -34) 1 1 0 )
(command "insert" "ped" '(42 -36) 1 1 0 )
(command "insert" "ped" '(42 -40) 1 1 0 )
(command "insert" "ped" '(65 -35) 1 1 0 )
(command "insert" "ped" '(68 -40) 1 1 0 )
(command "insert" "ped" '(42 -39) 1 1 0 )
(command "insert" "ped" '(66 -40) 1 1 0 )
(command "insert" "ped" '(72 -43) 1 1 0 )
(command "insert" "ped" '(62 -34) 1 1 0 )
(command "insert" "ped" '(94 -40) 1 1 0 )
(command "insert" "ped" '(89 -41) 1 1 0 )
(command "insert" "ped" '(73 -42) 1 1 0 )
(command "insert" "ped" '(97 -37) 1 1 0 )
(command "insert" "ped" '(104 -40) 1 1 0 )
(command "insert" "ped" '(99 -38) 1 1 0 )
(command "insert" "ped" '(71 -43) 1 1 0 )
(command "insert" "ped" '(75 -44) 1 1 0 )
(command "insert" "ped" '(44 -39) 1 1 0 )
(command "insert" "ped" '(101 -36) 1 1 0 )
(command "insert" "ped" '(46 -41) 1 1 0 )
(command "insert" "ped" '(47 -44) 1 1 0 )
(command "insert" "ped" '(57 -36) 1 1 0 )
(command "insert" "ped" '(43 -37) 1 1 0 )
(command "insert" "ped" '(58 -35) 1 1 0 )
(command "insert" "ped" '(41 -41) 1 1 0 )
(command "insert" "ped" '(65 -36) 1 1 0 )
(command "insert" "ped" '(89 -39) 1 1 0 )
(command "insert" "ped" '(85 -41) 1 1 0 )
(command "insert" "ped" '(84 -39) 1 1 0 )
(command "insert" "ped" '(67 -41) 1 1 0 )
(command "insert" "ped" '(65 -41) 1 1 0 )
(command "insert" "ped" '(62 -37) 1 1 0 )
(command "insert" "ped" '(61 -35) 1 1 0 )
(command "insert" "ped" '(92 -39) 1 1 0 )
(command "insert" "ped" '(91 -41) 1 1 0 )
(command "insert" "ped" '(72 -37) 1 1 0 )
(command "insert" "ped" '(87 -39) 1 1 0 )
(command "insert" "ped" '(70 -37) 1 1 0 )
(command "insert" "ped" '(94 -38) 1 1 0 )
(command "insert" "ped" '(93 -38) 1 1 0 )
(command "insert" "ped" '(49 -37) 1 1 0 )
(command "insert" "ped" '(80 -37) 1 1 0 )
(command "insert" "ped" '(70 -40) 1 1 0 )
(command "insert" "ped" '(75 -37) 1 1 0 )
(command "insert" "ped" '(98 -40) 1 1 0 )
(command "insert" "ped" '(76 -38) 1 1 0 )
(command "insert" "ped" '(44 -38) 1 1 0 )
(command "insert" "ped" '(82 -39) 1 1 0 )
(command "insert" "ped" '(92 -40) 1 1 0 )
(command "insert" "ped" '(46 -39) 1 1 0 )
(command "insert" "ped" '(45 -39) 1 1 0 )
(command "insert" "ped" '(53 -37) 1 1 0 )
(command "insert" "ped" '(57 -34) 1 1 0 )
(command "insert" "ped" '(89 -40) 1 1 0 )
(command "insert" "ped" '(79 -37) 1 1 0 )
(command "insert" "ped" '(59 -35) 1 1 0 )
(command "insert" "ped" '(42 -41) 1 1 0 )
(command "insert" "ped" '(41 -39) 1 1 0 )
(command "insert" "ped" '(65 -34) 1 1 0 )
(command "insert" "ped" '(60 -36) 1 1 0 )
(command "insert" "ped" '(68 -41) 1 1 0 )
(command "insert" "ped" '(95 -36) 1 1 0 )
(command "insert" "ped" '(66 -41) 1 1 0 )
(command "insert" "ped" '(63 -41) 1 1 0 )
(command "insert" "ped" '(62 -35) 1 1 0 )
(command "insert" "ped" '(69 -44) 1 1 0 )
(command "insert" "ped" '(43 -41) 1 1 0 )
(command "insert" "ped" '(92 -41) 1 1 0 )
(command "insert" "ped" '(39 -39) 1 1 0 )
(command "insert" "ped" '(97 -36) 1 1 0 )
(command "insert" "ped" '(87 -41) 1 1 0 )
(command "insert" "ped" '(104 -41) 1 1 0 )
(command "insert" "ped" '(97 -41) 1 1 0 )
(command "insert" "ped" '(71 -42) 1 1 0 )
(command "insert" "ped" '(102 -40) 1 1 0 )
(command "insert" "ped" '(45 -40) 1 1 0 )
(command "insert" "ped" '(88 -39) 1 1 0 )
(command "insert" "ped" '(83 -39) 1 1 0 )
(command "insert" "ped" '(41 -40) 1 1 0 )
(command "insert" "ped" '(85 -40) 1 1 0 )
(command "insert" "ped" '(67 -40) 1 1 0 )
(command "insert" "ped" '(91 -39) 1 1 0 )
(command "insert" "ped" '(65 -40) 1 1 0 )
(command "insert" "ped" '(86 -39) 1 1 0 )
(command "insert" "ped" '(91 -40) 1 1 0 )
(command "insert" "ped" '(72 -38) 1 1 0 )
(command "insert" "ped" '(94 -39) 1 1 0 )
(command "insert" "ped" '(93 -37) 1 1 0 )
(command "insert" "ped" '(49 -36) 1 1 0 )
(command "insert" "ped" '(39 -41) 1 1 0 )
(command "insert" "ped" '(80 -38) 1 1 0 )
(command "insert" "ped" '(95 -38) 1 1 0 )
(command "insert" "ped" '(75 -36) 1 1 0 )
(command "insert" "ped" '(74 -36) 1 1 0 )
(command "insert" "ped" '(98 -41) 1 1 0 )
(command "insert" "ped" '(81 -39) 1 1 0 )
(command "insert" "ped" '(71 -44) 1 1 0 )
(command "insert" "ped" '(100 -36) 1 1 0 )
(command "insert" "ped" '(95 -39) 1 1 0 )
(command "insert" "ped" '(77 -38) 1 1 0 )
(command "insert" "ped" '(51 -38) 1 1 0 )
(command "insert" "ped" '(55 -36) 1 1 0 )
(command "insert" "ped" '(56 -36) 1 1 0 )
(command "insert" "ped" '(54 -36) 1 1 0 )
(command "insert" "ped" '(53 -36) 1 1 0 )
(command "insert" "ped" '(57 -33) 1 1 0 )
(command "insert" "ped" '(40 -39) 1 1 0 )
(command "insert" "ped" '(64 -36) 1 1 0 )
(command "insert" "ped" '(79 -36) 1 1 0 )
(command "insert" "ped" '(59 -34) 1 1 0 )
(command "insert" "ped" '(58 -38) 1 1 0 )
(command "insert" "ped" '(90 -44) 1 1 0 )
(command "insert" "ped" '(60 -37) 1 1 0 )
(command "insert" "ped" '(43 -39) 1 1 0 )
(command "insert" "ped" '(42 -37) 1 1 0 )
(command "insert" "ped" '(63 -40) 1 1 0 )
(command "insert" "ped" '(69 -43) 1 1 0 )
(command "insert" "ped" '(43 -40) 1 1 0 )
(command "insert" "ped" '(92 -42) 1 1 0 )
(command "insert" "ped" '(63 -37) 1 1 0 )
(command "insert" "ped" '(87 -40) 1 1 0 )
(command "insert" "ped" '(97 -40) 1 1 0 )
(command "insert" "ped" '(71 -37) 1 1 0 )
(command "insert" "ped" '(77 -44) 1 1 0 )
(command "insert" "ped" '(94 -41) 1 1 0 )
(command "insert" "ped" '(72 -44) 1 1 0 )
(command "insert" "ped" '(45 -41) 1 1 0 )
(command "insert" "ped" '(88 -40) 1 1 0 )
(command "insert" "ped" '(58 -33) 1 1 0 )
(command "insert" "ped" '(61 -33) 1 1 0 )
(command "insert" "ped" '(91 -43) 1 1 0 )
(command "insert" "ped" '(63 -34) 1 1 0 )
(command "insert" "ped" '(96 -36) 1 1 0 )
(command "insert" "ped" '(94 -36) 1 1 0 )
(command "insert" "ped" '(93 -36) 1 1 0 )
(command "insert" "ped" '(92 -44) 1 1 0 )
(command "insert" "ped" '(73 -38) 1 1 0 )
(command "insert" "ped" '(45 -43) 1 1 0 )
(command "insert" "ped" '(74 -37) 1 1 0 )
(command "insert" "ped" '(98 -38) 1 1 0 )
(command "insert" "ped" '(100 -37) 1 1 0 )
(command "insert" "ped" '(77 -37) 1 1 0 )
(command "insert" "ped" '(60 -35) 1 1 0 )
(command "insert" "ped" '(75 -43) 1 1 0 )
(command "insert" "ped" '(59 -36) 1 1 0 )
(command "insert" "ped" '(39 -40) 1 1 0 )
(command "insert" "ped" '(56 -37) 1 1 0 )
(command "insert" "ped" '(54 -37) 1 1 0 )
(command "insert" "ped" '(78 -38) 1 1 0 )
(command "insert" "ped" '(40 -40) 1 1 0 )
(command "insert" "ped" '(64 -37) 1 1 0 )
(command "insert" "ped" '(84 -40) 1 1 0 )
(command "insert" "ped" '(61 -34) 1 1 0 )
(command "insert" "ped" '(64 -40) 1 1 0 )
(command "insert" "ped" '(60 -38) 1 1 0 )
(command "insert" "ped" '(43 -38) 1 1 0 )
(command "insert" "ped" '(66 -39) 1 1 0 )
(command "insert" "ped" '(62 -33) 1 1 0 )
(command "insert" "ped" '(69 -42) 1 1 0 )
(command "insert" "ped" '(92 -43) 1 1 0 )
(command "insert" "ped" '(48 -36) 1 1 0 )
(command "insert" "ped" '(63 -36) 1 1 0 )
(command "insert" "ped" '(69 -39) 1 1 0 )
(command "insert" "ped" '(74 -44) 1 1 0 )
(command "insert" "ped" '(71 -36) 1 1 0 )
(command "insert" "ped" '(50 -38) 1 1 0 )
(command "insert" "ped" '(90 -41) 1 1 0 )
(command "insert" "ped" '(63 -35) 1 1 0 )
(command "insert" "ped" '(76 -42) 1 1 0 )
(command "insert" "ped" '(77 -43) 1 1 0 )
(command "insert" "ped" '(60 -34) 1 1 0 )
(command "insert" "ped" '(44 -41) 1 1 0 )
(command "insert" "ped" '(46 -44) 1 1 0 )
(command "insert" "ped" '(47 -41) 1 1 0 )
(command "insert" "ped" '(102 -41) 1 1 0 )
(command "insert" "ped" '(52 -36) 1 1 0 )
(command "insert" "ped" '(88 -41) 1 1 0 )
(command "insert" "ped" '(83 -41) 1 1 0 )
(command "insert" "ped" '(70 -41) 1 1 0 )
(command "insert" "ped" '(91 -42) 1 1 0 )
(command "insert" "ped" '(96 -37) 1 1 0 )
(command "insert" "ped" '(86 -40) 1 1 0 )
(command "insert" "ped" '(94 -37) 1 1 0 )
(command "insert" "ped" '(73 -37) 1 1 0 )
(command "insert" "ped" '(96 -40) 1 1 0 )
(command "insert" "ped" '(45 -42) 1 1 0 )
(command "insert" "ped" '(75 -38) 1 1 0 )
(command "insert" "ped" '(99 -37) 1 1 0 )
(command "insert" "ped" '(98 -39) 1 1 0 )
(command "insert" "ped" '(55 -38) 1 1 0 )
(command "insert" "ped" '(100 -38) 1 1 0 )
(command "insert" "ped" '(65 -37) 1 1 0 )
(command "insert" "ped" '(77 -36) 1 1 0 )
(command "insert" "ped" '(76 -44) 1 1 0 )
(command "insert" "ped" '(44 -40) 1 1 0 )
(command "layer" "m" "Center" "" )
(command "insert" "Center" '(139 -16) 1 1 0 )
(command "insert" "Center" '(115 -18) 1 1 0 )
(command "insert" "Center" '(127 -18) 1 1 0 )
(command "insert" "Center" '(129 -26) 1 1 0 )
(command "insert" "Center" '(141 -26) 1 1 0 )
(command "insert" "Center" '(113 -24) 1 1 0 )
(command "insert" "Center" '(131 -28) 1 1 0 )
(command "insert" "Center" '(143 -36) 1 1 0 )
(command "insert" "Center" '(147 -33) 1 1 0 )
(command "insert" "Center" '(133 -30) 1 1 0 )
(command "insert" "Center" '(119 -13) 1 1 0 )
(command "insert" "Center" '(149 -27) 1 1 0 )
(command "insert" "Center" '(132 -37) 1 1 0 )
(command "insert" "Center" '(136 -32) 1 1 0 )
(command "insert" "Center" '(135 -24) 1 1 0 )
(command "insert" "Center" '(121 -25) 1 1 0 )
(command "insert" "Center" '(124 -34) 1 1 0 )
(command "insert" "Center" '(144 -32) 1 1 0 )
(command "insert" "Center" '(123 -31) 1 1 0 )
(command "insert" "Center" '(113 -37) 1 1 0 )
(command "insert" "Center" '(125 -29) 1 1 0 )
(command "insert" "Center" '(143 -25) 1 1 0 )
(command "insert" "Center" '(115 -27) 1 1 0 )
(command "insert" "Center" '(127 -27) 1 1 0 )
(command "insert" "Center" '(129 -19) 1 1 0 )
(command "insert" "Center" '(141 -19) 1 1 0 )
(command "insert" "Center" '(117 -17) 1 1 0 )
(command "insert" "Center" '(113 -17) 1 1 0 )
(command "insert" "Center" '(119 -31) 1 1 0 )
(command "insert" "Center" '(117 -37) 1 1 0 )
(command "insert" "Center" '(136 -39) 1 1 0 )
(command "insert" "Center" '(135 -17) 1 1 0 )
(command "insert" "Center" '(121 -34) 1 1 0 )
(command "insert" "Center" '(111 -19) 1 1 0 )
(command "insert" "Center" '(120 -9) 1 1 0 )
(command "insert" "Center" '(138 -37) 1 1 0 )
(command "insert" "Center" '(123 -20) 1 1 0 )
(command "insert" "Center" '(126 -35) 1 1 0 )
(command "insert" "Center" '(109 -25) 1 1 0 )
(command "insert" "Center" '(146 -37) 1 1 0 )
(command "insert" "Center" '(125 -22) 1 1 0 )
(command "insert" "Center" '(136 -19) 1 1 0 )
(command "insert" "Center" '(139 -14) 1 1 0 )
(command "insert" "Center" '(124 -13) 1 1 0 )
(command "insert" "Center" '(129 -20) 1 1 0 )
(command "insert" "Center" '(117 -26) 1 1 0 )
(command "insert" "Center" '(128 -15) 1 1 0 )
(command "insert" "Center" '(119 -20) 1 1 0 )
(command "insert" "Center" '(130 -13) 1 1 0 )
(command "insert" "Center" '(118 -11) 1 1 0 )
(command "insert" "Center" '(129 -32) 1 1 0 )
(command "insert" "Center" '(135 -14) 1 1 0 )
(command "insert" "Center" '(111 -24) 1 1 0 )
(command "insert" "Center" '(148 -22) 1 1 0 )
(command "insert" "Center" '(144 -30) 1 1 0 )
(command "insert" "Center" '(134 -33) 1 1 0 )
(command "insert" "Center" '(120 -16) 1 1 0 )
(command "insert" "Center" '(119 -40) 1 1 0 )
(command "insert" "Center" '(126 -42) 1 1 0 )
(command "insert" "Center" '(109 -18) 1 1 0 )
(command "insert" "Center" '(146 -28) 1 1 0 )
(command "insert" "Center" '(122 -10) 1 1 0 )
(command "insert" "Center" '(136 -26) 1 1 0 )
(command "insert" "Center" '(138 -16) 1 1 0 )
(command "insert" "Center" '(126 -22) 1 1 0 )
(command "insert" "Center" '(140 -30) 1 1 0 )
(command "insert" "Center" '(112 -24) 1 1 0 )
(command "insert" "Center" '(132 -18) 1 1 0 )
(command "insert" "Center" '(111 -33) 1 1 0 )
(command "insert" "Center" '(148 -29) 1 1 0 )
(command "insert" "Center" '(144 -21) 1 1 0 )
(command "insert" "Center" '(134 -24) 1 1 0 )
(command "insert" "Center" '(120 -23) 1 1 0 )
(command "insert" "Center" '(119 -33) 1 1 0 )
(command "insert" "Center" '(123 -34) 1 1 0 )
(command "insert" "Center" '(146 -23) 1 1 0 )
(command "insert" "Center" '(122 -21) 1 1 0 )
(command "insert" "Center" '(140 -33) 1 1 0 )
(command "insert" "Center" '(125 -40) 1 1 0 )
(command "insert" "Center" '(112 -35) 1 1 0 )
(command "insert" "Center" '(142 -27) 1 1 0 )
(command "insert" "Center" '(138 -27) 1 1 0 )
(command "insert" "Center" '(126 -25) 1 1 0 )
(command "insert" "Center" '(128 -29) 1 1 0 )
(command "insert" "Center" '(140 -21) 1 1 0 )
(command "insert" "Center" '(116 -23) 1 1 0 )
(command "insert" "Center" '(130 -31) 1 1 0 )
(command "insert" "Center" '(114 -29) 1 1 0 )
(command "insert" "Center" '(132 -25) 1 1 0 )
(command "insert" "Center" '(128 -41) 1 1 0 )
(command "insert" "Center" '(131 -36) 1 1 0 )
(command "insert" "Center" '(134 -19) 1 1 0 )
(command "insert" "Center" '(120 -30) 1 1 0 )
(command "insert" "Center" '(133 -38) 1 1 0 )
(command "insert" "Center" '(137 -35) 1 1 0 )
(command "insert" "Center" '(122 -28) 1 1 0 )
(command "insert" "Center" '(125 -33) 1 1 0 )
(command "insert" "Center" '(145 -35) 1 1 0 )
(command "insert" "Center" '(124 -26) 1 1 0 )
(command "insert" "Center" '(128 -20) 1 1 0 )
(command "insert" "Center" '(140 -12) 1 1 0 )
(command "insert" "Center" '(112 -22) 1 1 0 )
(command "insert" "Center" '(130 -22) 1 1 0 )
(command "insert" "Center" '(118 -28) 1 1 0 )
(command "insert" "Center" '(114 -20) 1 1 0 )
(command "insert" "Center" '(128 -32) 1 1 0 )
(command "insert" "Center" '(148 -35) 1 1 0 )
(command "insert" "Center" '(116 -34) 1 1 0 )
(command "insert" "Center" '(120 -37) 1 1 0 )
(command "insert" "Center" '(110 -24) 1 1 0 )
(command "insert" "Center" '(118 -40) 1 1 0 )
(command "insert" "Center" '(137 -36) 1 1 0 )
(command "insert" "Center" '(122 -39) 1 1 0 )
(command "insert" "Center" '(108 -22) 1 1 0 )
(command "insert" "Center" '(145 -36) 1 1 0 )
(command "insert" "Center" '(135 -41) 1 1 0 )
(command "insert" "Center" '(121 -10) 1 1 0 )
(command "insert" "Center" '(124 -17) 1 1 0 )
(command "insert" "Center" '(127 -36) 1 1 0 )
(command "insert" "Center" '(138 -13) 1 1 0 )
(command "insert" "Center" '(123 -12) 1 1 0 )
(command "insert" "Center" '(137 -16) 1 1 0 )
(command "insert" "Center" '(125 -14) 1 1 0 )
(command "insert" "Center" '(130 -17) 1 1 0 )
(command "insert" "Center" '(118 -23) 1 1 0 )
(command "insert" "Center" '(129 -12) 1 1 0 )
(command "insert" "Center" '(114 -15) 1 1 0 )
(command "insert" "Center" '(132 -15) 1 1 0 )
(command "insert" "Center" '(128 -39) 1 1 0 )
(command "insert" "Center" '(131 -18) 1 1 0 )
(command "insert" "Center" '(146 -33) 1 1 0 )
(command "insert" "Center" '(134 -13) 1 1 0 )
(command "insert" "Center" '(119 -12) 1 1 0 )
(command "insert" "Center" '(147 -23) 1 1 0 )
(command "insert" "Center" '(130 -37) 1 1 0 )
(command "insert" "Center" '(133 -40) 1 1 0 )
(command "insert" "Center" '(118 -35) 1 1 0 )
(command "insert" "Center" '(149 -21) 1 1 0 )
(command "insert" "Center" '(145 -29) 1 1 0 )
(command "insert" "Center" '(135 -38) 1 1 0 )
(command "insert" "Center" '(121 -19) 1 1 0 )
(command "insert" "Center" '(139 -35) 1 1 0 )
(command "insert" "Center" '(124 -40) 1 1 0 )
(command "insert" "Center" '(137 -25) 1 1 0 )
(command "insert" "Center" '(143 -23) 1 1 0 )
(command "insert" "Center" '(139 -31) 1 1 0 )
(command "insert" "Center" '(115 -17) 1 1 0 )
(command "insert" "Center" '(127 -17) 1 1 0 )
(command "insert" "Center" '(141 -29) 1 1 0 )
(command "insert" "Center" '(117 -11) 1 1 0 )
(command "insert" "Center" '(113 -27) 1 1 0 )
(command "insert" "Center" '(131 -27) 1 1 0 )
(command "insert" "Center" '(147 -28) 1 1 0 )
(command "insert" "Center" '(133 -17) 1 1 0 )
(command "insert" "Center" '(122 -41) 1 1 0 )
(command "insert" "Center" '(149 -30) 1 1 0 )
(command "insert" "Center" '(145 -22) 1 1 0 )
(command "insert" "Center" '(135 -31) 1 1 0 )
(command "insert" "Center" '(121 -20) 1 1 0 )
(command "insert" "Center" '(124 -39) 1 1 0 )
(command "insert" "Center" '(127 -42) 1 1 0 )
(command "insert" "Center" '(123 -26) 1 1 0 )
(command "insert" "Center" '(141 -34) 1 1 0 )
(command "insert" "Center" '(109 -35) 1 1 0 )
(command "insert" "Center" '(143 -28) 1 1 0 )
(command "insert" "Center" '(139 -20) 1 1 0 )
(command "insert" "Center" '(115 -22) 1 1 0 )
(command "insert" "Center" '(127 -30) 1 1 0 )
(command "insert" "Center" '(129 -30) 1 1 0 )
(command "insert" "Center" '(141 -22) 1 1 0 )
(command "insert" "Center" '(117 -20) 1 1 0 )
(command "insert" "Center" '(113 -28) 1 1 0 )
(command "insert" "Center" '(143 -32) 1 1 0 )
(command "insert" "Center" '(115 -34) 1 1 0 )
(command "insert" "Center" '(133 -26) 1 1 0 )
(command "insert" "Center" '(132 -33) 1 1 0 )
(command "insert" "Center" '(136 -36) 1 1 0 )
(command "insert" "Center" '(135 -20) 1 1 0 )
(command "insert" "Center" '(121 -29) 1 1 0 )
(command "insert" "Center" '(111 -22) 1 1 0 )
(command "insert" "Center" '(144 -36) 1 1 0 )
(command "insert" "Center" '(138 -38) 1 1 0 )
(command "insert" "Center" '(123 -19) 1 1 0 )
(command "insert" "Center" '(109 -28) 1 1 0 )
(command "insert" "Center" '(146 -38) 1 1 0 )
(command "insert" "Center" '(125 -25) 1 1 0 )
(command "insert" "Center" '(136 -16) 1 1 0 )
(command "insert" "Center" '(139 -13) 1 1 0 )
(command "insert" "Center" '(129 -23) 1 1 0 )
(command "insert" "Center" '(117 -29) 1 1 0 )
(command "insert" "Center" '(128 -12) 1 1 0 )
(command "insert" "Center" '(113 -21) 1 1 0 )
(command "insert" "Center" '(119 -27) 1 1 0 )
(command "insert" "Center" '(130 -14) 1 1 0 )
(command "insert" "Center" '(129 -35) 1 1 0 )
(command "insert" "Center" '(149 -32) 1 1 0 )
(command "insert" "Center" '(132 -40) 1 1 0 )
(command "insert" "Center" '(117 -33) 1 1 0 )
(command "insert" "Center" '(135 -13) 1 1 0 )
(command "insert" "Center" '(121 -38) 1 1 0 )
(command "insert" "Center" '(144 -27) 1 1 0 )
(command "insert" "Center" '(134 -34) 1 1 0 )
(command "insert" "Center" '(120 -13) 1 1 0 )
(command "insert" "Center" '(138 -33) 1 1 0 )
(command "insert" "Center" '(123 -40) 1 1 0 )
(command "insert" "Center" '(126 -39) 1 1 0 )
(command "insert" "Center" '(109 -21) 1 1 0 )
(command "insert" "Center" '(137 -12) 1 1 0 )
(command "insert" "Center" '(122 -15) 1 1 0 )
(command "insert" "Center" '(125 -18) 1 1 0 )
(command "insert" "Center" '(136 -23) 1 1 0 )
(command "insert" "Center" '(127 -12) 1 1 0 )
(command "insert" "Center" '(138 -21) 1 1 0 )
(command "insert" "Center" '(126 -19) 1 1 0 )
(command "insert" "Center" '(136 -13) 1 1 0 )
(command "insert" "Center" '(131 -14) 1 1 0 )
(command "insert" "Center" '(116 -13) 1 1 0 )
(command "insert" "Center" '(119 -16) 1 1 0 )
(command "insert" "Center" '(133 -12) 1 1 0 )
(command "insert" "Center" '(118 -15) 1 1 0 )
(command "insert" "Center" '(119 -14) 1 1 0 )
(command "insert" "Center" '(129 -36) 1 1 0 )
(command "insert" "Center" '(132 -23) 1 1 0 )
(command "insert" "Center" '(111 -36) 1 1 0 )
(command "insert" "Center" '(144 -18) 1 1 0 )
(command "insert" "Center" '(134 -37) 1 1 0 )
(command "insert" "Center" '(120 -20) 1 1 0 )
(command "insert" "Center" '(119 -36) 1 1 0 )
(command "insert" "Center" '(138 -40) 1 1 0 )
(command "insert" "Center" '(123 -33) 1 1 0 )
(command "insert" "Center" '(146 -24) 1 1 0 )
(command "insert" "Center" '(122 -22) 1 1 0 )
(command "insert" "Center" '(140 -38) 1 1 0 )
(command "insert" "Center" '(136 -30) 1 1 0 )
(command "insert" "Center" '(142 -20) 1 1 0 )
(command "insert" "Center" '(138 -28) 1 1 0 )
(command "insert" "Center" '(126 -26) 1 1 0 )
(command "insert" "Center" '(128 -26) 1 1 0 )
(command "insert" "Center" '(140 -26) 1 1 0 )
(command "insert" "Center" '(116 -20) 1 1 0 )
(command "insert" "Center" '(112 -28) 1 1 0 )
(command "insert" "Center" '(142 -32) 1 1 0 )
(command "insert" "Center" '(132 -30) 1 1 0 )
(command "insert" "Center" '(148 -25) 1 1 0 )
(command "insert" "Center" '(131 -35) 1 1 0 )
(command "insert" "Center" '(134 -28) 1 1 0 )
(command "insert" "Center" '(120 -27) 1 1 0 )
(command "insert" "Center" '(110 -18) 1 1 0 )
(command "insert" "Center" '(123 -38) 1 1 0 )
(command "insert" "Center" '(146 -19) 1 1 0 )
(command "insert" "Center" '(122 -17) 1 1 0 )
(command "insert" "Center" '(125 -36) 1 1 0 )
(command "insert" "Center" '(108 -28) 1 1 0 )
(command "insert" "Center" '(124 -31) 1 1 0 )
(command "insert" "Center" '(142 -31) 1 1 0 )
(command "insert" "Center" '(114 -37) 1 1 0 )
(command "insert" "Center" '(126 -29) 1 1 0 )
(command "insert" "Center" '(128 -17) 1 1 0 )
(command "insert" "Center" '(140 -17) 1 1 0 )
(command "insert" "Center" '(116 -19) 1 1 0 )
(command "insert" "Center" '(112 -19) 1 1 0 )
(command "insert" "Center" '(130 -27) 1 1 0 )
(command "insert" "Center" '(118 -25) 1 1 0 )
(command "insert" "Center" '(114 -25) 1 1 0 )
(command "insert" "Center" '(148 -32) 1 1 0 )
(command "insert" "Center" '(131 -40) 1 1 0 )
(command "insert" "Center" '(134 -23) 1 1 0 )
(command "insert" "Center" '(120 -34) 1 1 0 )
(command "insert" "Center" '(110 -21) 1 1 0 )
(command "insert" "Center" '(133 -34) 1 1 0 )
(command "insert" "Center" '(137 -39) 1 1 0 )
(command "insert" "Center" '(122 -24) 1 1 0 )
(command "insert" "Center" '(108 -27) 1 1 0 )
(command "insert" "Center" '(136 -12) 1 1 0 )
(command "insert" "Center" '(139 -41) 1 1 0 )
(command "insert" "Center" '(124 -22) 1 1 0 )
(command "insert" "Center" '(138 -14) 1 1 0 )
(command "insert" "Center" '(137 -19) 1 1 0 )
(command "insert" "Center" '(116 -26) 1 1 0 )
(command "insert" "Center" '(130 -18) 1 1 0 )
(command "insert" "Center" '(118 -16) 1 1 0 )
(command "insert" "Center" '(129 -15) 1 1 0 )
(command "insert" "Center" '(114 -16) 1 1 0 )
(command "insert" "Center" '(132 -12) 1 1 0 )
(command "insert" "Center" '(128 -36) 1 1 0 )
(command "insert" "Center" '(131 -17) 1 1 0 )
(command "insert" "Center" '(134 -14) 1 1 0 )
(command "insert" "Center" '(120 -41) 1 1 0 )
(command "insert" "Center" '(110 -28) 1 1 0 )
(command "insert" "Center" '(130 -38) 1 1 0 )
(command "insert" "Center" '(137 -40) 1 1 0 )
(command "insert" "Center" '(122 -35) 1 1 0 )
(command "insert" "Center" '(108 -18) 1 1 0 )
(command "insert" "Center" '(145 -24) 1 1 0 )
(command "insert" "Center" '(135 -37) 1 1 0 )
(command "insert" "Center" '(121 -14) 1 1 0 )
(command "insert" "Center" '(127 -32) 1 1 0 )
(command "insert" "Center" '(126 -15) 1 1 0 )
(command "insert" "Center" '(137 -20) 1 1 0 )
(command "insert" "Center" '(139 -26) 1 1 0 )
(command "insert" "Center" '(115 -12) 1 1 0 )
(command "insert" "Center" '(127 -20) 1 1 0 )
(command "insert" "Center" '(117 -14) 1 1 0 )
(command "insert" "Center" '(131 -22) 1 1 0 )
(command "insert" "Center" '(147 -27) 1 1 0 )
(command "insert" "Center" '(130 -33) 1 1 0 )
(command "insert" "Center" '(133 -20) 1 1 0 )
(command "insert" "Center" '(118 -39) 1 1 0 )
(command "insert" "Center" '(135 -34) 1 1 0 )
(command "insert" "Center" '(121 -23) 1 1 0 )
(command "insert" "Center" '(139 -39) 1 1 0 )
(command "insert" "Center" '(124 -36) 1 1 0 )
(command "insert" "Center" '(127 -41) 1 1 0 )
(command "insert" "Center" '(123 -25) 1 1 0 )
(command "insert" "Center" '(141 -37) 1 1 0 )
(command "insert" "Center" '(137 -29) 1 1 0 )
(command "insert" "Center" '(113 -35) 1 1 0 )
(command "insert" "Center" '(143 -19) 1 1 0 )
(command "insert" "Center" '(139 -19) 1 1 0 )
(command "insert" "Center" '(115 -21) 1 1 0 )
(command "insert" "Center" '(127 -29) 1 1 0 )
(command "insert" "Center" '(129 -25) 1 1 0 )
(command "insert" "Center" '(141 -25) 1 1 0 )
(command "insert" "Center" '(117 -23) 1 1 0 )
(command "insert" "Center" '(131 -31) 1 1 0 )
(command "insert" "Center" '(147 -32) 1 1 0 )
(command "insert" "Center" '(115 -33) 1 1 0 )
(command "insert" "Center" '(133 -29) 1 1 0 )
(command "insert" "Center" '(149 -26) 1 1 0 )
(command "insert" "Center" '(132 -38) 1 1 0 )
(command "insert" "Center" '(136 -33) 1 1 0 )
(command "insert" "Center" '(135 -27) 1 1 0 )
(command "insert" "Center" '(121 -24) 1 1 0 )
(command "insert" "Center" '(111 -21) 1 1 0 )
(command "insert" "Center" '(124 -35) 1 1 0 )
(command "insert" "Center" '(144 -33) 1 1 0 )
(command "insert" "Center" '(123 -30) 1 1 0 )
(command "insert" "Center" '(113 -36) 1 1 0 )
(command "insert" "Center" '(125 -28) 1 1 0 )
(command "insert" "Center" '(143 -24) 1 1 0 )
(command "insert" "Center" '(115 -26) 1 1 0 )
(command "insert" "Center" '(127 -26) 1 1 0 )
(command "insert" "Center" '(129 -18) 1 1 0 )
(command "insert" "Center" '(141 -18) 1 1 0 )
(command "insert" "Center" '(117 -16) 1 1 0 )
(command "insert" "Center" '(113 -16) 1 1 0 )
(command "insert" "Center" '(119 -30) 1 1 0 )
(command "insert" "Center" '(115 -38) 1 1 0 )
(command "insert" "Center" '(149 -35) 1 1 0 )
(command "insert" "Center" '(117 -36) 1 1 0 )
(command "insert" "Center" '(136 -40) 1 1 0 )
(command "insert" "Center" '(135 -16) 1 1 0 )
(command "insert" "Center" '(121 -33) 1 1 0 )
(command "insert" "Center" '(111 -18) 1 1 0 )
(command "insert" "Center" '(144 -24) 1 1 0 )
(command "insert" "Center" '(120 -10) 1 1 0 )
(command "insert" "Center" '(138 -34) 1 1 0 )
(command "insert" "Center" '(123 -23) 1 1 0 )
(command "insert" "Center" '(126 -32) 1 1 0 )
(command "insert" "Center" '(109 -24) 1 1 0 )
(command "insert" "Center" '(146 -34) 1 1 0 )
(command "insert" "Center" '(125 -21) 1 1 0 )
(command "insert" "Center" '(136 -20) 1 1 0 )
(command "insert" "Center" '(124 -14) 1 1 0 )
(command "insert" "Center" '(138 -22) 1 1 0 )
(command "insert" "Center" '(117 -25) 1 1 0 )
(command "insert" "Center" '(131 -13) 1 1 0 )
(command "insert" "Center" '(119 -23) 1 1 0 )
(command "insert" "Center" '(133 -15) 1 1 0 )
(command "insert" "Center" '(129 -39) 1 1 0 )
(command "insert" "Center" '(132 -20) 1 1 0 )
(command "insert" "Center" '(111 -27) 1 1 0 )
(command "insert" "Center" '(148 -23) 1 1 0 )
(command "insert" "Center" '(144 -31) 1 1 0 )
(command "insert" "Center" '(134 -38) 1 1 0 )
(command "insert" "Center" '(120 -17) 1 1 0 )
(command "insert" "Center" '(126 -43) 1 1 0 )
(command "insert" "Center" '(146 -29) 1 1 0 )
(command "insert" "Center" '(122 -11) 1 1 0 )
(command "insert" "Center" '(136 -27) 1 1 0 )
(command "insert" "Center" '(138 -17) 1 1 0 )
(command "insert" "Center" '(126 -23) 1 1 0 )
(command "insert" "Center" '(140 -31) 1 1 0 )
(command "insert" "Center" '(112 -25) 1 1 0 )
(command "insert" "Center" '(132 -19) 1 1 0 )
(command "insert" "Center" '(148 -30) 1 1 0 )
(command "insert" "Center" '(144 -22) 1 1 0 )
(command "insert" "Center" '(134 -25) 1 1 0 )
(command "insert" "Center" '(120 -24) 1 1 0 )
(command "insert" "Center" '(119 -32) 1 1 0 )
(command "insert" "Center" '(123 -37) 1 1 0 )
(command "insert" "Center" '(146 -20) 1 1 0 )
(command "insert" "Center" '(122 -18) 1 1 0 )
(command "insert" "Center" '(140 -34) 1 1 0 )
(command "insert" "Center" '(125 -39) 1 1 0 )
(command "insert" "Center" '(108 -33) 1 1 0 )
(command "insert" "Center" '(112 -36) 1 1 0 )
(command "insert" "Center" '(124 -28) 1 1 0 )
(command "insert" "Center" '(142 -24) 1 1 0 )
(command "insert" "Center" '(138 -24) 1 1 0 )
(command "insert" "Center" '(114 -38) 1 1 0 )
(command "insert" "Center" '(126 -30) 1 1 0 )
(command "insert" "Center" '(128 -30) 1 1 0 )
(command "insert" "Center" '(140 -22) 1 1 0 )
(command "insert" "Center" '(116 -16) 1 1 0 )
(command "insert" "Center" '(112 -16) 1 1 0 )
(command "insert" "Center" '(130 -28) 1 1 0 )
(command "insert" "Center" '(142 -36) 1 1 0 )
(command "insert" "Center" '(118 -26) 1 1 0 )
(command "insert" "Center" '(114 -26) 1 1 0 )
(command "insert" "Center" '(132 -26) 1 1 0 )
(command "insert" "Center" '(128 -42) 1 1 0 )
(command "insert" "Center" '(131 -39) 1 1 0 )
(command "insert" "Center" '(116 -36) 1 1 0 )
(command "insert" "Center" '(134 -16) 1 1 0 )
(command "insert" "Center" '(120 -31) 1 1 0 )
(command "insert" "Center" '(110 -22) 1 1 0 )
(command "insert" "Center" '(133 -37) 1 1 0 )
(command "insert" "Center" '(137 -34) 1 1 0 )
(command "insert" "Center" '(122 -29) 1 1 0 )
(command "insert" "Center" '(125 -32) 1 1 0 )
(command "insert" "Center" '(108 -24) 1 1 0 )
(command "insert" "Center" '(145 -34) 1 1 0 )
(command "insert" "Center" '(124 -27) 1 1 0 )
(command "insert" "Center" '(114 -33) 1 1 0 )
(command "insert" "Center" '(128 -21) 1 1 0 )
(command "insert" "Center" '(140 -13) 1 1 0 )
(command "insert" "Center" '(112 -23) 1 1 0 )
(command "insert" "Center" '(130 -23) 1 1 0 )
(command "insert" "Center" '(118 -29) 1 1 0 )
(command "insert" "Center" '(114 -21) 1 1 0 )
(command "insert" "Center" '(128 -33) 1 1 0 )
(command "insert" "Center" '(116 -35) 1 1 0 )
(command "insert" "Center" '(146 -32) 1 1 0 )
(command "insert" "Center" '(120 -38) 1 1 0 )
(command "insert" "Center" '(110 -25) 1 1 0 )
(command "insert" "Center" '(118 -41) 1 1 0 )
(command "insert" "Center" '(122 -36) 1 1 0 )
(command "insert" "Center" '(108 -23) 1 1 0 )
(command "insert" "Center" '(145 -27) 1 1 0 )
(command "insert" "Center" '(135 -40) 1 1 0 )
(command "insert" "Center" '(121 -9) 1 1 0 )
(command "insert" "Center" '(124 -18) 1 1 0 )
(command "insert" "Center" '(127 -39) 1 1 0 )
(command "insert" "Center" '(123 -15) 1 1 0 )
(command "insert" "Center" '(137 -23) 1 1 0 )
(command "insert" "Center" '(125 -13) 1 1 0 )
(command "insert" "Center" '(139 -25) 1 1 0 )
(command "insert" "Center" '(118 -20) 1 1 0 )
(command "insert" "Center" '(114 -12) 1 1 0 )
(command "insert" "Center" '(131 -21) 1 1 0 )
(command "insert" "Center" '(119 -15) 1 1 0 )
(command "insert" "Center" '(147 -22) 1 1 0 )
(command "insert" "Center" '(130 -34) 1 1 0 )
(command "insert" "Center" '(133 -23) 1 1 0 )
(command "insert" "Center" '(118 -32) 1 1 0 )
(command "insert" "Center" '(145 -28) 1 1 0 )
(command "insert" "Center" '(135 -33) 1 1 0 )
(command "insert" "Center" '(121 -18) 1 1 0 )
(command "insert" "Center" '(139 -34) 1 1 0 )
(command "insert" "Center" '(124 -41) 1 1 0 )
(command "insert" "Center" '(127 -44) 1 1 0 )
(command "insert" "Center" '(137 -24) 1 1 0 )
(command "insert" "Center" '(143 -22) 1 1 0 )
(command "insert" "Center" '(139 -30) 1 1 0 )
(command "insert" "Center" '(115 -16) 1 1 0 )
(command "insert" "Center" '(127 -16) 1 1 0 )
(command "insert" "Center" '(141 -28) 1 1 0 )
(command "insert" "Center" '(117 -10) 1 1 0 )
(command "insert" "Center" '(113 -26) 1 1 0 )
(command "insert" "Center" '(131 -26) 1 1 0 )
(command "insert" "Center" '(147 -31) 1 1 0 )
(command "insert" "Center" '(133 -16) 1 1 0 )
(command "insert" "Center" '(149 -29) 1 1 0 )
(command "insert" "Center" '(145 -21) 1 1 0 )
(command "insert" "Center" '(135 -30) 1 1 0 )
(command "insert" "Center" '(121 -27) 1 1 0 )
(command "insert" "Center" '(124 -32) 1 1 0 )
(command "insert" "Center" '(123 -29) 1 1 0 )
(command "insert" "Center" '(141 -33) 1 1 0 )
(command "insert" "Center" '(109 -34) 1 1 0 )
(command "insert" "Center" '(125 -31) 1 1 0 )
(command "insert" "Center" '(143 -31) 1 1 0 )
(command "insert" "Center" '(139 -23) 1 1 0 )
(command "insert" "Center" '(115 -25) 1 1 0 )
(command "insert" "Center" '(127 -25) 1 1 0 )
(command "insert" "Center" '(129 -29) 1 1 0 )
(command "insert" "Center" '(141 -21) 1 1 0 )
(command "insert" "Center" '(117 -19) 1 1 0 )
(command "insert" "Center" '(113 -19) 1 1 0 )
(command "insert" "Center" '(143 -35) 1 1 0 )
(command "insert" "Center" '(119 -29) 1 1 0 )
(command "insert" "Center" '(115 -37) 1 1 0 )
(command "insert" "Center" '(133 -25) 1 1 0 )
(command "insert" "Center" '(129 -41) 1 1 0 )
(command "insert" "Center" '(132 -34) 1 1 0 )
(command "insert" "Center" '(117 -39) 1 1 0 )
(command "insert" "Center" '(136 -37) 1 1 0 )
(command "insert" "Center" '(135 -23) 1 1 0 )
(command "insert" "Center" '(121 -28) 1 1 0 )
(command "insert" "Center" '(111 -17) 1 1 0 )
(command "insert" "Center" '(144 -37) 1 1 0 )
(command "insert" "Center" '(134 -40) 1 1 0 )
(command "insert" "Center" '(138 -39) 1 1 0 )
(command "insert" "Center" '(123 -18) 1 1 0 )
(command "insert" "Center" '(109 -27) 1 1 0 )
(command "insert" "Center" '(125 -24) 1 1 0 )
(command "insert" "Center" '(136 -17) 1 1 0 )
(command "insert" "Center" '(139 -12) 1 1 0 )
(command "insert" "Center" '(129 -22) 1 1 0 )
(command "insert" "Center" '(117 -28) 1 1 0 )
(command "insert" "Center" '(128 -13) 1 1 0 )
(command "insert" "Center" '(113 -20) 1 1 0 )
(command "insert" "Center" '(119 -26) 1 1 0 )
(command "insert" "Center" '(130 -15) 1 1 0 )
(command "insert" "Center" '(129 -34) 1 1 0 )
(command "insert" "Center" '(132 -41) 1 1 0 )
(command "insert" "Center" '(117 -32) 1 1 0 )
(command "insert" "Center" '(135 -12) 1 1 0 )
(command "insert" "Center" '(121 -37) 1 1 0 )
(command "insert" "Center" '(144 -28) 1 1 0 )
(command "insert" "Center" '(134 -35) 1 1 0 )
(command "insert" "Center" '(120 -14) 1 1 0 )
(command "insert" "Center" '(126 -36) 1 1 0 )
(command "insert" "Center" '(109 -20) 1 1 0 )
(command "insert" "Center" '(146 -30) 1 1 0 )
(command "insert" "Center" '(122 -12) 1 1 0 )
(command "insert" "Center" '(140 -40) 1 1 0 )
(command "insert" "Center" '(125 -17) 1 1 0 )
(command "insert" "Center" '(136 -24) 1 1 0 )
(command "insert" "Center" '(142 -18) 1 1 0 )
(command "insert" "Center" '(127 -15) 1 1 0 )
(command "insert" "Center" '(138 -18) 1 1 0 )
(command "insert" "Center" '(126 -16) 1 1 0 )
(command "insert" "Center" '(140 -28) 1 1 0 )
(command "insert" "Center" '(116 -14) 1 1 0 )
(command "insert" "Center" '(119 -19) 1 1 0 )
(command "insert" "Center" '(118 -12) 1 1 0 )
(command "insert" "Center" '(132 -16) 1 1 0 )
(command "insert" "Center" '(117 -41) 1 1 0 )
(command "insert" "Center" '(144 -19) 1 1 0 )
(command "insert" "Center" '(134 -26) 1 1 0 )
(command "insert" "Center" '(120 -21) 1 1 0 )
(command "insert" "Center" '(119 -39) 1 1 0 )
(command "insert" "Center" '(138 -41) 1 1 0 )
(command "insert" "Center" '(123 -32) 1 1 0 )
(command "insert" "Center" '(146 -25) 1 1 0 )
(command "insert" "Center" '(122 -23) 1 1 0 )
(command "insert" "Center" '(140 -39) 1 1 0 )
(command "insert" "Center" '(136 -31) 1 1 0 )
(command "insert" "Center" '(112 -33) 1 1 0 )
(command "insert" "Center" '(142 -21) 1 1 0 )
(command "insert" "Center" '(138 -29) 1 1 0 )
(command "insert" "Center" '(126 -27) 1 1 0 )
(command "insert" "Center" '(128 -27) 1 1 0 )
(command "insert" "Center" '(140 -27) 1 1 0 )
(command "insert" "Center" '(116 -21) 1 1 0 )
(command "insert" "Center" '(112 -29) 1 1 0 )
(command "insert" "Center" '(142 -33) 1 1 0 )
(command "insert" "Center" '(132 -31) 1 1 0 )
(command "insert" "Center" '(148 -26) 1 1 0 )
(command "insert" "Center" '(131 -34) 1 1 0 )
(command "insert" "Center" '(134 -29) 1 1 0 )
(command "insert" "Center" '(120 -28) 1 1 0 )
(command "insert" "Center" '(110 -19) 1 1 0 )
(command "insert" "Center" '(122 -30) 1 1 0 )
(command "insert" "Center" '(125 -35) 1 1 0 )
(command "insert" "Center" '(108 -29) 1 1 0 )
(command "insert" "Center" '(124 -24) 1 1 0 )
(command "insert" "Center" '(142 -28) 1 1 0 )
(command "insert" "Center" '(114 -34) 1 1 0 )
(command "insert" "Center" '(128 -18) 1 1 0 )
(command "insert" "Center" '(140 -18) 1 1 0 )
(command "insert" "Center" '(116 -28) 1 1 0 )
(command "insert" "Center" '(112 -20) 1 1 0 )
(command "insert" "Center" '(130 -24) 1 1 0 )
(command "insert" "Center" '(118 -30) 1 1 0 )
(command "insert" "Center" '(114 -22) 1 1 0 )
(command "insert" "Center" '(148 -33) 1 1 0 )
(command "insert" "Center" '(134 -20) 1 1 0 )
(command "insert" "Center" '(120 -35) 1 1 0 )
(command "insert" "Center" '(110 -26) 1 1 0 )
(command "insert" "Center" '(133 -33) 1 1 0 )
(command "insert" "Center" '(137 -38) 1 1 0 )
(command "insert" "Center" '(122 -25) 1 1 0 )
(command "insert" "Center" '(108 -20) 1 1 0 )
(command "insert" "Center" '(145 -38) 1 1 0 )
(command "insert" "Center" '(139 -40) 1 1 0 )
(command "insert" "Center" '(124 -23) 1 1 0 )
(command "insert" "Center" '(138 -15) 1 1 0 )
(command "insert" "Center" '(137 -18) 1 1 0 )
(command "insert" "Center" '(116 -27) 1 1 0 )
(command "insert" "Center" '(130 -19) 1 1 0 )
(command "insert" "Center" '(118 -17) 1 1 0 )
(command "insert" "Center" '(129 -14) 1 1 0 )
(command "insert" "Center" '(114 -17) 1 1 0 )
(command "insert" "Center" '(132 -13) 1 1 0 )
(command "insert" "Center" '(128 -37) 1 1 0 )
(command "insert" "Center" '(131 -16) 1 1 0 )
(command "insert" "Center" '(134 -15) 1 1 0 )
(command "insert" "Center" '(110 -29) 1 1 0 )
(command "insert" "Center" '(147 -21) 1 1 0 )
(command "insert" "Center" '(130 -39) 1 1 0 )
(command "insert" "Center" '(122 -32) 1 1 0 )
(command "insert" "Center" '(149 -23) 1 1 0 )
(command "insert" "Center" '(108 -19) 1 1 0 )
(command "insert" "Center" '(145 -31) 1 1 0 )
(command "insert" "Center" '(135 -36) 1 1 0 )
(command "insert" "Center" '(121 -13) 1 1 0 )
(command "insert" "Center" '(139 -33) 1 1 0 )
(command "insert" "Center" '(127 -35) 1 1 0 )
(command "insert" "Center" '(126 -12) 1 1 0 )
(command "insert" "Center" '(137 -27) 1 1 0 )
(command "insert" "Center" '(143 -21) 1 1 0 )
(command "insert" "Center" '(139 -29) 1 1 0 )
(command "insert" "Center" '(115 -15) 1 1 0 )
(command "insert" "Center" '(127 -23) 1 1 0 )
(command "insert" "Center" '(141 -31) 1 1 0 )
(command "insert" "Center" '(117 -13) 1 1 0 )
(command "insert" "Center" '(131 -25) 1 1 0 )
(command "insert" "Center" '(119 -11) 1 1 0 )
(command "insert" "Center" '(147 -26) 1 1 0 )
(command "insert" "Center" '(133 -19) 1 1 0 )
(command "insert" "Center" '(118 -36) 1 1 0 )
(command "insert" "Center" '(135 -29) 1 1 0 )
(command "insert" "Center" '(121 -22) 1 1 0 )
(command "insert" "Center" '(111 -15) 1 1 0 )
(command "insert" "Center" '(139 -38) 1 1 0 )
(command "insert" "Center" '(124 -37) 1 1 0 )
(command "insert" "Center" '(127 -40) 1 1 0 )
(command "insert" "Center" '(123 -24) 1 1 0 )
(command "insert" "Center" '(141 -36) 1 1 0 )
(command "insert" "Center" '(137 -28) 1 1 0 )
(command "insert" "Center" '(113 -34) 1 1 0 )
(command "insert" "Center" '(143 -18) 1 1 0 )
(command "insert" "Center" '(139 -18) 1 1 0 )
(command "insert" "Center" '(115 -20) 1 1 0 )
(command "insert" "Center" '(127 -28) 1 1 0 )
(command "insert" "Center" '(129 -24) 1 1 0 )
(command "insert" "Center" '(141 -24) 1 1 0 )
(command "insert" "Center" '(117 -22) 1 1 0 )
(command "insert" "Center" '(131 -30) 1 1 0 )
(command "insert" "Center" '(143 -38) 1 1 0 )
(command "insert" "Center" '(147 -35) 1 1 0 )
(command "insert" "Center" '(133 -28) 1 1 0 )
(command "insert" "Center" '(149 -25) 1 1 0 )
(command "insert" "Center" '(132 -39) 1 1 0 )
(command "insert" "Center" '(136 -34) 1 1 0 )
(command "insert" "Center" '(135 -26) 1 1 0 )
(command "insert" "Center" '(121 -31) 1 1 0 )
(command "insert" "Center" '(111 -20) 1 1 0 )
(command "insert" "Center" '(144 -34) 1 1 0 )
(command "insert" "Center" '(123 -17) 1 1 0 )
(command "insert" "Center" '(125 -27) 1 1 0 )
(command "insert" "Center" '(143 -27) 1 1 0 )
(command "insert" "Center" '(115 -29) 1 1 0 )
(command "insert" "Center" '(129 -17) 1 1 0 )
(command "insert" "Center" '(117 -31) 1 1 0 )
(command "insert" "Center" '(113 -23) 1 1 0 )
(command "insert" "Center" '(119 -25) 1 1 0 )
(command "insert" "Center" '(149 -34) 1 1 0 )
(command "insert" "Center" '(117 -35) 1 1 0 )
(command "insert" "Center" '(136 -41) 1 1 0 )
(command "insert" "Center" '(135 -19) 1 1 0 )
(command "insert" "Center" '(121 -32) 1 1 0 )
(command "insert" "Center" '(111 -29) 1 1 0 )
(command "insert" "Center" '(144 -25) 1 1 0 )
(command "insert" "Center" '(120 -11) 1 1 0 )
(command "insert" "Center" '(138 -35) 1 1 0 )
(command "insert" "Center" '(123 -22) 1 1 0 )
(command "insert" "Center" '(126 -33) 1 1 0 )
(command "insert" "Center" '(109 -23) 1 1 0 )
(command "insert" "Center" '(146 -35) 1 1 0 )
(command "insert" "Center" '(125 -20) 1 1 0 )
(command "insert" "Center" '(136 -21) 1 1 0 )
(command "insert" "Center" '(124 -15) 1 1 0 )
(command "insert" "Center" '(138 -23) 1 1 0 )
(command "insert" "Center" '(117 -24) 1 1 0 )
(command "insert" "Center" '(131 -12) 1 1 0 )
(command "insert" "Center" '(119 -22) 1 1 0 )
(command "insert" "Center" '(133 -14) 1 1 0 )
(command "insert" "Center" '(118 -9) 1 1 0 )
(command "insert" "Center" '(129 -38) 1 1 0 )
(command "insert" "Center" '(132 -21) 1 1 0 )
(command "insert" "Center" '(121 -41) 1 1 0 )
(command "insert" "Center" '(111 -26) 1 1 0 )
(command "insert" "Center" '(134 -39) 1 1 0 )
(command "insert" "Center" '(120 -18) 1 1 0 )
(command "insert" "Center" '(126 -40) 1 1 0 )
(command "insert" "Center" '(146 -26) 1 1 0 )
(command "insert" "Center" '(140 -36) 1 1 0 )
(command "insert" "Center" '(136 -28) 1 1 0 )
(command "insert" "Center" '(142 -22) 1 1 0 )
(command "insert" "Center" '(138 -30) 1 1 0 )
(command "insert" "Center" '(126 -20) 1 1 0 )
(command "insert" "Center" '(128 -24) 1 1 0 )
(command "insert" "Center" '(140 -24) 1 1 0 )
(command "insert" "Center" '(112 -26) 1 1 0 )
(command "insert" "Center" '(142 -34) 1 1 0 )
(command "insert" "Center" '(132 -28) 1 1 0 )
(command "insert" "Center" '(111 -35) 1 1 0 )
(command "insert" "Center" '(148 -31) 1 1 0 )
(command "insert" "Center" '(131 -33) 1 1 0 )
(command "insert" "Center" '(144 -23) 1 1 0 )
(command "insert" "Center" '(134 -30) 1 1 0 )
(command "insert" "Center" '(120 -25) 1 1 0 )
(command "insert" "Center" '(119 -35) 1 1 0 )
(command "insert" "Center" '(123 -36) 1 1 0 )
(command "insert" "Center" '(146 -21) 1 1 0 )
(command "insert" "Center" '(122 -19) 1 1 0 )
(command "insert" "Center" '(140 -35) 1 1 0 )
(command "insert" "Center" '(125 -38) 1 1 0 )
(command "insert" "Center" '(108 -34) 1 1 0 )
(command "insert" "Center" '(112 -37) 1 1 0 )
(command "insert" "Center" '(124 -29) 1 1 0 )
(command "insert" "Center" '(142 -25) 1 1 0 )
(command "insert" "Center" '(138 -25) 1 1 0 )
(command "insert" "Center" '(126 -31) 1 1 0 )
(command "insert" "Center" '(136 -15) 1 1 0 )
(command "insert" "Center" '(128 -31) 1 1 0 )
(command "insert" "Center" '(140 -23) 1 1 0 )
(command "insert" "Center" '(116 -17) 1 1 0 )
(command "insert" "Center" '(112 -17) 1 1 0 )
(command "insert" "Center" '(130 -29) 1 1 0 )
(command "insert" "Center" '(142 -37) 1 1 0 )
(command "insert" "Center" '(118 -27) 1 1 0 )
(command "insert" "Center" '(114 -27) 1 1 0 )
(command "insert" "Center" '(132 -27) 1 1 0 )
(command "insert" "Center" '(128 -43) 1 1 0 )
(command "insert" "Center" '(131 -38) 1 1 0 )
(command "insert" "Center" '(116 -37) 1 1 0 )
(command "insert" "Center" '(137 -14) 1 1 0 )
(command "insert" "Center" '(134 -17) 1 1 0 )
(command "insert" "Center" '(120 -32) 1 1 0 )
(command "insert" "Center" '(110 -23) 1 1 0 )
(command "insert" "Center" '(133 -36) 1 1 0 )
(command "insert" "Center" '(137 -33) 1 1 0 )
(command "insert" "Center" '(122 -26) 1 1 0 )
(command "insert" "Center" '(108 -25) 1 1 0 )
(command "insert" "Center" '(145 -33) 1 1 0 )
(command "insert" "Center" '(124 -20) 1 1 0 )
(command "insert" "Center" '(128 -22) 1 1 0 )
(command "insert" "Center" '(140 -14) 1 1 0 )
(command "insert" "Center" '(116 -24) 1 1 0 )
(command "insert" "Center" '(130 -20) 1 1 0 )
(command "insert" "Center" '(118 -18) 1 1 0 )
(command "insert" "Center" '(114 -18) 1 1 0 )
(command "insert" "Center" '(128 -34) 1 1 0 )
(command "insert" "Center" '(120 -39) 1 1 0 )
(command "insert" "Center" '(130 -40) 1 1 0 )
(command "insert" "Center" '(122 -37) 1 1 0 )
(command "insert" "Center" '(145 -26) 1 1 0 )
(command "insert" "Center" '(124 -19) 1 1 0 )
(command "insert" "Center" '(127 -38) 1 1 0 )
(command "insert" "Center" '(123 -14) 1 1 0 )
(command "insert" "Center" '(137 -22) 1 1 0 )
(command "insert" "Center" '(125 -12) 1 1 0 )
(command "insert" "Center" '(112 -15) 1 1 0 )
(command "insert" "Center" '(139 -24) 1 1 0 )
(command "insert" "Center" '(118 -21) 1 1 0 )
(command "insert" "Center" '(114 -13) 1 1 0 )
(command "insert" "Center" '(131 -20) 1 1 0 )
(command "insert" "Center" '(110 -33) 1 1 0 )
(command "insert" "Center" '(147 -25) 1 1 0 )
(command "insert" "Center" '(130 -35) 1 1 0 )
(command "insert" "Center" '(133 -22) 1 1 0 )
(command "insert" "Center" '(118 -33) 1 1 0 )
(command "insert" "Center" '(145 -19) 1 1 0 )
(command "insert" "Center" '(135 -32) 1 1 0 )
(command "insert" "Center" '(121 -17) 1 1 0 )
(command "insert" "Center" '(139 -37) 1 1 0 )
(command "insert" "Center" '(137 -31) 1 1 0 )
(command "insert" "Center" '(139 -17) 1 1 0 )
(command "insert" "Center" '(115 -19) 1 1 0 )
(command "insert" "Center" '(127 -19) 1 1 0 )
(command "insert" "Center" '(129 -27) 1 1 0 )
(command "insert" "Center" '(141 -27) 1 1 0 )
(command "insert" "Center" '(117 -9) 1 1 0 )
(command "insert" "Center" '(113 -25) 1 1 0 )
(command "insert" "Center" '(131 -29) 1 1 0 )
(command "insert" "Center" '(143 -37) 1 1 0 )
(command "insert" "Center" '(147 -30) 1 1 0 )
(command "insert" "Center" '(133 -31) 1 1 0 )
(command "insert" "Center" '(149 -28) 1 1 0 )
(command "insert" "Center" '(132 -36) 1 1 0 )
(command "insert" "Center" '(145 -20) 1 1 0 )
(command "insert" "Center" '(135 -25) 1 1 0 )
(command "insert" "Center" '(121 -26) 1 1 0 )
(command "insert" "Center" '(124 -33) 1 1 0 )
(command "insert" "Center" '(123 -28) 1 1 0 )
(command "insert" "Center" '(141 -32) 1 1 0 )
(command "insert" "Center" '(109 -33) 1 1 0 )
(command "insert" "Center" '(113 -38) 1 1 0 )
(command "insert" "Center" '(125 -30) 1 1 0 )
(command "insert" "Center" '(143 -30) 1 1 0 )
(command "insert" "Center" '(139 -22) 1 1 0 )
(command "insert" "Center" '(115 -24) 1 1 0 )
(command "insert" "Center" '(127 -24) 1 1 0 )
(command "insert" "Center" '(129 -28) 1 1 0 )
(command "insert" "Center" '(141 -20) 1 1 0 )
(command "insert" "Center" '(117 -18) 1 1 0 )
(command "insert" "Center" '(113 -18) 1 1 0 )
(command "insert" "Center" '(143 -34) 1 1 0 )
(command "insert" "Center" '(119 -28) 1 1 0 )
(command "insert" "Center" '(115 -36) 1 1 0 )
(command "insert" "Center" '(133 -24) 1 1 0 )
(command "insert" "Center" '(110 -35) 1 1 0 )
(command "insert" "Center" '(129 -40) 1 1 0 )
(command "insert" "Center" '(132 -35) 1 1 0 )
(command "insert" "Center" '(117 -38) 1 1 0 )
(command "insert" "Center" '(136 -38) 1 1 0 )
(command "insert" "Center" '(135 -22) 1 1 0 )
(command "insert" "Center" '(121 -35) 1 1 0 )
(command "insert" "Center" '(111 -16) 1 1 0 )
(command "insert" "Center" '(144 -38) 1 1 0 )
(command "insert" "Center" '(134 -41) 1 1 0 )
(command "insert" "Center" '(138 -36) 1 1 0 )
(command "insert" "Center" '(123 -21) 1 1 0 )
(command "insert" "Center" '(126 -34) 1 1 0 )
(command "insert" "Center" '(109 -26) 1 1 0 )
(command "insert" "Center" '(146 -36) 1 1 0 )
(command "insert" "Center" '(125 -23) 1 1 0 )
(command "insert" "Center" '(136 -18) 1 1 0 )
(command "insert" "Center" '(139 -15) 1 1 0 )
(command "insert" "Center" '(124 -12) 1 1 0 )
(command "insert" "Center" '(129 -21) 1 1 0 )
(command "insert" "Center" '(117 -27) 1 1 0 )
(command "insert" "Center" '(128 -14) 1 1 0 )
(command "insert" "Center" '(119 -21) 1 1 0 )
(command "insert" "Center" '(130 -12) 1 1 0 )
(command "insert" "Center" '(118 -10) 1 1 0 )
(command "insert" "Center" '(129 -33) 1 1 0 )
(command "insert" "Center" '(135 -15) 1 1 0 )
(command "insert" "Center" '(121 -36) 1 1 0 )
(command "insert" "Center" '(111 -25) 1 1 0 )
(command "insert" "Center" '(148 -21) 1 1 0 )
(command "insert" "Center" '(144 -29) 1 1 0 )
(command "insert" "Center" '(134 -32) 1 1 0 )
(command "insert" "Center" '(120 -15) 1 1 0 )
(command "insert" "Center" '(119 -41) 1 1 0 )
(command "insert" "Center" '(126 -37) 1 1 0 )
(command "insert" "Center" '(109 -19) 1 1 0 )
(command "insert" "Center" '(146 -31) 1 1 0 )
(command "insert" "Center" '(122 -13) 1 1 0 )
(command "insert" "Center" '(140 -41) 1 1 0 )
(command "insert" "Center" '(125 -16) 1 1 0 )
(command "insert" "Center" '(136 -25) 1 1 0 )
(command "insert" "Center" '(142 -19) 1 1 0 )
(command "insert" "Center" '(127 -14) 1 1 0 )
(command "insert" "Center" '(138 -19) 1 1 0 )
(command "insert" "Center" '(126 -17) 1 1 0 )
(command "insert" "Center" '(140 -29) 1 1 0 )
(command "insert" "Center" '(116 -15) 1 1 0 )
(command "insert" "Center" '(119 -18) 1 1 0 )
(command "insert" "Center" '(118 -13) 1 1 0 )
(command "insert" "Center" '(132 -17) 1 1 0 )
(command "insert" "Center" '(117 -40) 1 1 0 )
(command "insert" "Center" '(111 -38) 1 1 0 )
(command "insert" "Center" '(148 -28) 1 1 0 )
(command "insert" "Center" '(144 -20) 1 1 0 )
(command "insert" "Center" '(134 -27) 1 1 0 )
(command "insert" "Center" '(120 -22) 1 1 0 )
(command "insert" "Center" '(119 -38) 1 1 0 )
(command "insert" "Center" '(123 -35) 1 1 0 )
(command "insert" "Center" '(126 -44) 1 1 0 )
(command "insert" "Center" '(146 -22) 1 1 0 )
(command "insert" "Center" '(122 -20) 1 1 0 )
(command "insert" "Center" '(140 -32) 1 1 0 )
(command "insert" "Center" '(125 -41) 1 1 0 )
(command "insert" "Center" '(112 -34) 1 1 0 )
(command "insert" "Center" '(142 -26) 1 1 0 )
(command "insert" "Center" '(138 -26) 1 1 0 )
(command "insert" "Center" '(126 -24) 1 1 0 )
(command "insert" "Center" '(128 -28) 1 1 0 )
(command "insert" "Center" '(140 -20) 1 1 0 )
(command "insert" "Center" '(116 -22) 1 1 0 )
(command "insert" "Center" '(130 -30) 1 1 0 )
(command "insert" "Center" '(142 -38) 1 1 0 )
(command "insert" "Center" '(114 -28) 1 1 0 )
(command "insert" "Center" '(132 -24) 1 1 0 )
(command "insert" "Center" '(128 -40) 1 1 0 )
(command "insert" "Center" '(148 -27) 1 1 0 )
(command "insert" "Center" '(131 -37) 1 1 0 )
(command "insert" "Center" '(134 -18) 1 1 0 )
(command "insert" "Center" '(120 -29) 1 1 0 )
(command "insert" "Center" '(133 -39) 1 1 0 )
(command "insert" "Center" '(122 -31) 1 1 0 )
(command "insert" "Center" '(125 -34) 1 1 0 )
(command "insert" "Center" '(124 -25) 1 1 0 )
(command "insert" "Center" '(142 -29) 1 1 0 )
(command "insert" "Center" '(114 -35) 1 1 0 )
(command "insert" "Center" '(128 -19) 1 1 0 )
(command "insert" "Center" '(140 -19) 1 1 0 )
(command "insert" "Center" '(116 -29) 1 1 0 )
(command "insert" "Center" '(112 -21) 1 1 0 )
(command "insert" "Center" '(130 -25) 1 1 0 )
(command "insert" "Center" '(118 -31) 1 1 0 )
(command "insert" "Center" '(114 -23) 1 1 0 )
(command "insert" "Center" '(148 -34) 1 1 0 )
(command "insert" "Center" '(116 -33) 1 1 0 )
(command "insert" "Center" '(134 -21) 1 1 0 )
(command "insert" "Center" '(120 -36) 1 1 0 )
(command "insert" "Center" '(110 -27) 1 1 0 )
(command "insert" "Center" '(133 -32) 1 1 0 )
(command "insert" "Center" '(137 -37) 1 1 0 )
(command "insert" "Center" '(122 -38) 1 1 0 )
(command "insert" "Center" '(108 -21) 1 1 0 )
(command "insert" "Center" '(145 -37) 1 1 0 )
(command "insert" "Center" '(121 -11) 1 1 0 )
(command "insert" "Center" '(124 -16) 1 1 0 )
(command "insert" "Center" '(127 -37) 1 1 0 )
(command "insert" "Center" '(138 -12) 1 1 0 )
(command "insert" "Center" '(123 -13) 1 1 0 )
(command "insert" "Center" '(137 -17) 1 1 0 )
(command "insert" "Center" '(125 -15) 1 1 0 )
(command "insert" "Center" '(130 -16) 1 1 0 )
(command "insert" "Center" '(118 -22) 1 1 0 )
(command "insert" "Center" '(129 -13) 1 1 0 )
(command "insert" "Center" '(114 -14) 1 1 0 )
(command "insert" "Center" '(132 -14) 1 1 0 )
(command "insert" "Center" '(128 -38) 1 1 0 )
(command "insert" "Center" '(131 -19) 1 1 0 )
(command "insert" "Center" '(134 -12) 1 1 0 )
(command "insert" "Center" '(110 -34) 1 1 0 )
(command "insert" "Center" '(130 -36) 1 1 0 )
(command "insert" "Center" '(133 -41) 1 1 0 )
(command "insert" "Center" '(118 -34) 1 1 0 )
(command "insert" "Center" '(122 -33) 1 1 0 )
(command "insert" "Center" '(149 -22) 1 1 0 )
(command "insert" "Center" '(145 -30) 1 1 0 )
(command "insert" "Center" '(135 -39) 1 1 0 )
(command "insert" "Center" '(121 -12) 1 1 0 )
(command "insert" "Center" '(139 -32) 1 1 0 )
(command "insert" "Center" '(127 -34) 1 1 0 )
(command "insert" "Center" '(126 -13) 1 1 0 )
(command "insert" "Center" '(137 -26) 1 1 0 )
(command "insert" "Center" '(143 -20) 1 1 0 )
(command "insert" "Center" '(139 -28) 1 1 0 )
(command "insert" "Center" '(115 -14) 1 1 0 )
(command "insert" "Center" '(127 -22) 1 1 0 )
(command "insert" "Center" '(141 -30) 1 1 0 )
(command "insert" "Center" '(117 -12) 1 1 0 )
(command "insert" "Center" '(131 -24) 1 1 0 )
(command "insert" "Center" '(119 -10) 1 1 0 )
(command "insert" "Center" '(147 -29) 1 1 0 )
(command "insert" "Center" '(133 -18) 1 1 0 )
(command "insert" "Center" '(118 -37) 1 1 0 )
(command "insert" "Center" '(122 -40) 1 1 0 )
(command "insert" "Center" '(149 -31) 1 1 0 )
(command "insert" "Center" '(145 -23) 1 1 0 )
(command "insert" "Center" '(135 -28) 1 1 0 )
(command "insert" "Center" '(121 -21) 1 1 0 )
(command "insert" "Center" '(124 -38) 1 1 0 )
(command "insert" "Center" '(127 -43) 1 1 0 )
(command "insert" "Center" '(123 -27) 1 1 0 )
(command "insert" "Center" '(141 -35) 1 1 0 )
(command "insert" "Center" '(113 -33) 1 1 0 )
(command "insert" "Center" '(143 -29) 1 1 0 )
(command "insert" "Center" '(139 -21) 1 1 0 )
(command "insert" "Center" '(115 -23) 1 1 0 )
(command "insert" "Center" '(127 -31) 1 1 0 )
(command "insert" "Center" '(129 -31) 1 1 0 )
(command "insert" "Center" '(141 -23) 1 1 0 )
(command "insert" "Center" '(117 -21) 1 1 0 )
(command "insert" "Center" '(113 -29) 1 1 0 )
(command "insert" "Center" '(143 -33) 1 1 0 )
(command "insert" "Center" '(147 -34) 1 1 0 )
(command "insert" "Center" '(115 -35) 1 1 0 )
(command "insert" "Center" '(133 -27) 1 1 0 )
(command "insert" "Center" '(149 -24) 1 1 0 )
(command "insert" "Center" '(132 -32) 1 1 0 )
(command "insert" "Center" '(136 -35) 1 1 0 )
(command "insert" "Center" '(135 -21) 1 1 0 )
(command "insert" "Center" '(121 -30) 1 1 0 )
(command "insert" "Center" '(111 -23) 1 1 0 )
(command "insert" "Center" '(144 -35) 1 1 0 )
(command "insert" "Center" '(123 -16) 1 1 0 )
(command "insert" "Center" '(109 -29) 1 1 0 )
(command "insert" "Center" '(125 -26) 1 1 0 )
(command "insert" "Center" '(143 -26) 1 1 0 )
(command "insert" "Center" '(115 -28) 1 1 0 )
(command "insert" "Center" '(129 -16) 1 1 0 )
(command "insert" "Center" '(117 -30) 1 1 0 )
(command "insert" "Center" '(113 -22) 1 1 0 )
(command "insert" "Center" '(119 -24) 1 1 0 )
(command "insert" "Center" '(149 -33) 1 1 0 )
(command "insert" "Center" '(117 -34) 1 1 0 )
(command "insert" "Center" '(135 -18) 1 1 0 )
(command "insert" "Center" '(121 -39) 1 1 0 )
(command "insert" "Center" '(111 -28) 1 1 0 )
(command "insert" "Center" '(144 -26) 1 1 0 )
(command "insert" "Center" '(120 -12) 1 1 0 )
(command "insert" "Center" '(138 -32) 1 1 0 )
(command "insert" "Center" '(123 -41) 1 1 0 )
(command "insert" "Center" '(126 -38) 1 1 0 )
(command "insert" "Center" '(109 -22) 1 1 0 )
(command "insert" "Center" '(137 -13) 1 1 0 )
(command "insert" "Center" '(122 -14) 1 1 0 )
(command "insert" "Center" '(125 -19) 1 1 0 )
(command "insert" "Center" '(136 -22) 1 1 0 )
(command "insert" "Center" '(127 -13) 1 1 0 )
(command "insert" "Center" '(138 -20) 1 1 0 )
(command "insert" "Center" '(126 -18) 1 1 0 )
(command "insert" "Center" '(113 -15) 1 1 0 )
(command "insert" "Center" '(131 -15) 1 1 0 )
(command "insert" "Center" '(116 -12) 1 1 0 )
(command "insert" "Center" '(119 -17) 1 1 0 )
(command "insert" "Center" '(133 -13) 1 1 0 )
(command "insert" "Center" '(118 -14) 1 1 0 )
(command "insert" "Center" '(129 -37) 1 1 0 )
(command "insert" "Center" '(132 -22) 1 1 0 )
(command "insert" "Center" '(121 -40) 1 1 0 )
(command "insert" "Center" '(111 -37) 1 1 0 )
(command "insert" "Center" '(134 -36) 1 1 0 )
(command "insert" "Center" '(120 -19) 1 1 0 )
(command "insert" "Center" '(119 -37) 1 1 0 )
(command "insert" "Center" '(126 -41) 1 1 0 )
(command "insert" "Center" '(146 -27) 1 1 0 )
(command "insert" "Center" '(122 -9) 1 1 0 )
(command "insert" "Center" '(140 -37) 1 1 0 )
(command "insert" "Center" '(136 -29) 1 1 0 )
(command "insert" "Center" '(142 -23) 1 1 0 )
(command "insert" "Center" '(138 -31) 1 1 0 )
(command "insert" "Center" '(126 -21) 1 1 0 )
(command "insert" "Center" '(136 -14) 1 1 0 )
(command "insert" "Center" '(128 -25) 1 1 0 )
(command "insert" "Center" '(140 -25) 1 1 0 )
(command "insert" "Center" '(112 -27) 1 1 0 )
(command "insert" "Center" '(142 -35) 1 1 0 )
(command "insert" "Center" '(132 -29) 1 1 0 )
(command "insert" "Center" '(111 -34) 1 1 0 )
(command "insert" "Center" '(148 -24) 1 1 0 )
(command "insert" "Center" '(131 -32) 1 1 0 )
(command "insert" "Center" '(137 -15) 1 1 0 )
(command "insert" "Center" '(134 -31) 1 1 0 )
(command "insert" "Center" '(120 -26) 1 1 0 )
(command "insert" "Center" '(119 -34) 1 1 0 )
(command "insert" "Center" '(123 -39) 1 1 0 )
(command "insert" "Center" '(146 -18) 1 1 0 )
(command "insert" "Center" '(122 -16) 1 1 0 )
(command "insert" "Center" '(125 -37) 1 1 0 )
(command "insert" "Center" '(108 -35) 1 1 0 )
(command "insert" "Center" '(112 -38) 1 1 0 )
(command "insert" "Center" '(124 -30) 1 1 0 )
(command "insert" "Center" '(142 -30) 1 1 0 )
(command "insert" "Center" '(114 -36) 1 1 0 )
(command "insert" "Center" '(126 -28) 1 1 0 )
(command "insert" "Center" '(128 -16) 1 1 0 )
(command "insert" "Center" '(140 -16) 1 1 0 )
(command "insert" "Center" '(116 -18) 1 1 0 )
(command "insert" "Center" '(112 -18) 1 1 0 )
(command "insert" "Center" '(130 -26) 1 1 0 )
(command "insert" "Center" '(118 -24) 1 1 0 )
(command "insert" "Center" '(114 -24) 1 1 0 )
(command "insert" "Center" '(128 -44) 1 1 0 )
(command "insert" "Center" '(131 -41) 1 1 0 )
(command "insert" "Center" '(116 -38) 1 1 0 )
(command "insert" "Center" '(134 -22) 1 1 0 )
(command "insert" "Center" '(120 -33) 1 1 0 )
(command "insert" "Center" '(110 -20) 1 1 0 )
(command "insert" "Center" '(133 -35) 1 1 0 )
(command "insert" "Center" '(137 -32) 1 1 0 )
(command "insert" "Center" '(122 -27) 1 1 0 )
(command "insert" "Center" '(108 -26) 1 1 0 )
(command "insert" "Center" '(145 -32) 1 1 0 )
(command "insert" "Center" '(124 -21) 1 1 0 )
(command "insert" "Center" '(128 -23) 1 1 0 )
(command "insert" "Center" '(140 -15) 1 1 0 )
(command "insert" "Center" '(116 -25) 1 1 0 )
(command "insert" "Center" '(130 -21) 1 1 0 )
(command "insert" "Center" '(118 -19) 1 1 0 )
(command "insert" "Center" '(114 -19) 1 1 0 )
(command "insert" "Center" '(128 -35) 1 1 0 )
(command "insert" "Center" '(120 -40) 1 1 0 )
(command "insert" "Center" '(130 -41) 1 1 0 )
(command "insert" "Center" '(137 -41) 1 1 0 )
(command "insert" "Center" '(122 -34) 1 1 0 )
(command "insert" "Center" '(145 -25) 1 1 0 )
(command "insert" "Center" '(121 -15) 1 1 0 )
(command "insert" "Center" '(127 -33) 1 1 0 )
(command "insert" "Center" '(126 -14) 1 1 0 )
(command "insert" "Center" '(137 -21) 1 1 0 )
(command "insert" "Center" '(139 -27) 1 1 0 )
(command "insert" "Center" '(115 -13) 1 1 0 )
(command "insert" "Center" '(127 -21) 1 1 0 )
(command "insert" "Center" '(117 -15) 1 1 0 )
(command "insert" "Center" '(131 -23) 1 1 0 )
(command "insert" "Center" '(119 -9) 1 1 0 )
(command "insert" "Center" '(147 -24) 1 1 0 )
(command "insert" "Center" '(130 -32) 1 1 0 )
(command "insert" "Center" '(133 -21) 1 1 0 )
(command "insert" "Center" '(118 -38) 1 1 0 )
(command "insert" "Center" '(145 -18) 1 1 0 )
(command "insert" "Center" '(135 -35) 1 1 0 )
(command "insert" "Center" '(121 -16) 1 1 0 )
(command "insert" "Center" '(139 -36) 1 1 0 )
(command "insert" "Center" '(141 -38) 1 1 0 )
(command "insert" "Center" '(137 -30) 1 1 0 )
(command "layer" "m" "Res" "" )
(command "insert" "Res" '(12 -2) 1 1 0 )
(command "insert" "Res" '(12 -1) 1 1 0 )
(command "insert" "Res" '(9 -1) 1 1 0 )
(command "insert" "Res" '(13 -1) 1 1 0 )
(command "insert" "Res" '(9 -2) 1 1 0 )
(command "insert" "Res" '(11 -2) 1 1 0 )
(command "insert" "Res" '(14 -1) 1 1 0 )
(command "insert" "Res" '(11 -1) 1 1 0 )
(command "insert" "Res" '(10 -1) 1 1 0 )
(command "insert" "Res" '(13 -2) 1 1 0 )
(command "insert" "Res" '(14 -2) 1 1 0 )
(command "insert" "Res" '(10 -2) 1 1 0 )
(command "layer" "m" "Commmer" "" )
(command "insert" "Commmer" '(247 -83) 1 1 0 )
(command "insert" "Commmer" '(236 -79) 1 1 0 )
(command "insert" "Commmer" '(245 -79) 1 1 0 )
(command "insert" "Commmer" '(250 -86) 1 1 0 )
(command "insert" "Commmer" '(235 -79) 1 1 0 )
(command "insert" "Commmer" '(233 -83) 1 1 0 )
(command "insert" "Commmer" '(235 -80) 1 1 0 )
(command "insert" "Commmer" '(241 -72) 1 1 0 )
(command "insert" "Commmer" '(245 -85) 1 1 0 )
(command "insert" "Commmer" '(234 -81) 1 1 0 )
(command "insert" "Commmer" '(251 -85) 1 1 0 )
(command "insert" "Commmer" '(248 -81) 1 1 0 )
(command "insert" "Commmer" '(249 -86) 1 1 0 )
(command "insert" "Commmer" '(244 -84) 1 1 0 )
(command "insert" "Commmer" '(246 -83) 1 1 0 )
(command "insert" "Commmer" '(247 -76) 1 1 0 )
(command "insert" "Commmer" '(242 -78) 1 1 0 )
(command "insert" "Commmer" '(235 -78) 1 1 0 )
(command "insert" "Commmer" '(241 -75) 1 1 0 )
(command "insert" "Commmer" '(248 -83) 1 1 0 )
(command "insert" "Commmer" '(234 -82) 1 1 0 )
(command "insert" "Commmer" '(231 -83) 1 1 0 )
(command "insert" "Commmer" '(236 -81) 1 1 0 )
(command "insert" "Commmer" '(242 -73) 1 1 0 )
(command "insert" "Commmer" '(236 -78) 1 1 0 )
(command "insert" "Commmer" '(233 -84) 1 1 0 )
(command "insert" "Commmer" '(238 -83) 1 1 0 )
(command "insert" "Commmer" '(232 -85) 1 1 0 )
(command "insert" "Commmer" '(237 -83) 1 1 0 )
(command "insert" "Commmer" '(248 -75) 1 1 0 )
(command "insert" "Commmer" '(244 -78) 1 1 0 )
(command "insert" "Commmer" '(242 -74) 1 1 0 )
(command "insert" "Commmer" '(233 -77) 1 1 0 )
(command "insert" "Commmer" '(232 -76) 1 1 0 )
(command "insert" "Commmer" '(246 -76) 1 1 0 )
(command "insert" "Commmer" '(231 -81) 1 1 0 )
(command "insert" "Commmer" '(245 -84) 1 1 0 )
(command "insert" "Commmer" '(238 -76) 1 1 0 )
(command "insert" "Commmer" '(234 -78) 1 1 0 )
(command "insert" "Commmer" '(235 -84) 1 1 0 )
(command "insert" "Commmer" '(232 -82) 1 1 0 )
(command "insert" "Commmer" '(241 -76) 1 1 0 )
(command "insert" "Commmer" '(240 -77) 1 1 0 )
(command "insert" "Commmer" '(247 -82) 1 1 0 )
(command "insert" "Commmer" '(244 -80) 1 1 0 )
(command "insert" "Commmer" '(245 -78) 1 1 0 )
(command "insert" "Commmer" '(231 -85) 1 1 0 )
(command "insert" "Commmer" '(242 -79) 1 1 0 )
(command "insert" "Commmer" '(243 -86) 1 1 0 )
(command "insert" "Commmer" '(233 -82) 1 1 0 )
(command "insert" "Commmer" '(235 -83) 1 1 0 )
(command "insert" "Commmer" '(241 -79) 1 1 0 )
(command "insert" "Commmer" '(237 -76) 1 1 0 )
(command "insert" "Commmer" '(251 -84) 1 1 0 )
(command "insert" "Commmer" '(248 -82) 1 1 0 )
(command "insert" "Commmer" '(247 -81) 1 1 0 )
(command "insert" "Commmer" '(244 -85) 1 1 0 )
(command "insert" "Commmer" '(246 -80) 1 1 0 )
(command "insert" "Commmer" '(242 -80) 1 1 0 )
(command "insert" "Commmer" '(233 -75) 1 1 0 )
(command "insert" "Commmer" '(247 -79) 1 1 0 )
(command "insert" "Commmer" '(248 -78) 1 1 0 )
(command "insert" "Commmer" '(231 -86) 1 1 0 )
(command "insert" "Commmer" '(237 -77) 1 1 0 )
(command "insert" "Commmer" '(241 -74) 1 1 0 )
(command "insert" "Commmer" '(234 -83) 1 1 0 )
(command "insert" "Commmer" '(248 -79) 1 1 0 )
(command "insert" "Commmer" '(236 -86) 1 1 0 )
(command "insert" "Commmer" '(240 -73) 1 1 0 )
(command "insert" "Commmer" '(240 -79) 1 1 0 )
(command "insert" "Commmer" '(243 -80) 1 1 0 )
(command "insert" "Commmer" '(232 -86) 1 1 0 )
(command "insert" "Commmer" '(237 -82) 1 1 0 )
(command "insert" "Commmer" '(234 -84) 1 1 0 )
(command "insert" "Commmer" '(248 -76) 1 1 0 )
(command "insert" "Commmer" '(244 -79) 1 1 0 )
(command "insert" "Commmer" '(242 -75) 1 1 0 )
(command "insert" "Commmer" '(233 -76) 1 1 0 )
(command "insert" "Commmer" '(241 -73) 1 1 0 )
(command "insert" "Commmer" '(232 -77) 1 1 0 )
(command "insert" "Commmer" '(246 -77) 1 1 0 )
(command "insert" "Commmer" '(233 -86) 1 1 0 )
(command "insert" "Commmer" '(238 -77) 1 1 0 )
(command "insert" "Commmer" '(234 -79) 1 1 0 )
(command "insert" "Commmer" '(243 -79) 1 1 0 )
(command "insert" "Commmer" '(232 -83) 1 1 0 )
(command "insert" "Commmer" '(245 -80) 1 1 0 )
(command "insert" "Commmer" '(243 -78) 1 1 0 )
(command "insert" "Commmer" '(239 -83) 1 1 0 )
(command "insert" "Commmer" '(241 -80) 1 1 0 )
(command "insert" "Commmer" '(243 -85) 1 1 0 )
(command "insert" "Commmer" '(239 -76) 1 1 0 )
(command "insert" "Commmer" '(231 -77) 1 1 0 )
(command "insert" "Commmer" '(250 -84) 1 1 0 )
(command "insert" "Commmer" '(247 -75) 1 1 0 )
(command "insert" "Commmer" '(250 -85) 1 1 0 )
(command "insert" "Commmer" '(246 -78) 1 1 0 )
(command "insert" "Commmer" '(240 -74) 1 1 0 )
(command "insert" "Commmer" '(233 -81) 1 1 0 )
(command "insert" "Commmer" '(231 -75) 1 1 0 )
(command "insert" "Commmer" '(235 -82) 1 1 0 )
(command "insert" "Commmer" '(241 -78) 1 1 0 )
(command "insert" "Commmer" '(237 -75) 1 1 0 )
(command "insert" "Commmer" '(240 -75) 1 1 0 )
(command "insert" "Commmer" '(247 -80) 1 1 0 )
(command "insert" "Commmer" '(244 -86) 1 1 0 )
(command "insert" "Commmer" '(246 -81) 1 1 0 )
(command "insert" "Commmer" '(247 -78) 1 1 0 )
(command "insert" "Commmer" '(246 -75) 1 1 0 )
(command "insert" "Commmer" '(243 -84) 1 1 0 )
(command "insert" "Commmer" '(240 -78) 1 1 0 )
(command "insert" "Commmer" '(238 -75) 1 1 0 )
(command "insert" "Commmer" '(231 -84) 1 1 0 )
(command "insert" "Commmer" '(235 -81) 1 1 0 )
(command "insert" "Commmer" '(249 -84) 1 1 0 )
(command "insert" "Commmer" '(245 -86) 1 1 0 )
(command "insert" "Commmer" '(234 -80) 1 1 0 )
(command "insert" "Commmer" '(240 -72) 1 1 0 )
(command "insert" "Commmer" '(236 -83) 1 1 0 )
(command "insert" "Commmer" '(246 -82) 1 1 0 )
(command "insert" "Commmer" '(231 -82) 1 1 0 )
(command "insert" "Commmer" '(247 -77) 1 1 0 )
(command "insert" "Commmer" '(242 -76) 1 1 0 )
(command "insert" "Commmer" '(238 -81) 1 1 0 )
(command "insert" "Commmer" '(236 -82) 1 1 0 )
(command "insert" "Commmer" '(248 -80) 1 1 0 )
(command "insert" "Commmer" '(237 -81) 1 1 0 )
(command "insert" "Commmer" '(234 -85) 1 1 0 )
(command "insert" "Commmer" '(248 -77) 1 1 0 )
(command "insert" "Commmer" '(236 -80) 1 1 0 )
(command "insert" "Commmer" '(242 -72) 1 1 0 )
(command "insert" "Commmer" '(236 -84) 1 1 0 )
(command "insert" "Commmer" '(233 -85) 1 1 0 )
(command "insert" "Commmer" '(238 -82) 1 1 0 )
(command "insert" "Commmer" '(235 -86) 1 1 0 )
(command "insert" "Commmer" '(232 -84) 1 1 0 )
(command "insert" "Commmer" '(239 -77) 1 1 0 )
(command "insert" "Commmer" '(239 -82) 1 1 0 )
(command "insert" "Commmer" '(249 -85) 1 1 0 )
(command "insert" "Commmer" '(234 -86) 1 1 0 )
(command "insert" "Commmer" '(236 -85) 1 1 0 )
(command "insert" "Commmer" '(242 -77) 1 1 0 )
(command "insert" "Commmer" '(240 -80) 1 1 0 )
(command "insert" "Commmer" '(231 -76) 1 1 0 )
(command "insert" "Commmer" '(232 -75) 1 1 0 )
(command "insert" "Commmer" '(246 -79) 1 1 0 )
(command "insert" "Commmer" '(239 -75) 1 1 0 )
(command "insert" "Commmer" '(235 -85) 1 1 0 )
(command "insert" "Commmer" '(232 -81) 1 1 0 )
(command "insert" "Commmer" '(241 -77) 1 1 0 )
(command "insert" "Commmer" '(240 -76) 1 1 0 )
(command "insert" "Commmer" '(251 -86) 1 1 0 )
(command "insert" "Commmer" '(239 -81) 1 1 0 )
(command "layer" "m" "Res" "" )
(command "insert" "Res" '(205 -97) 1 1 0 )
(command "insert" "Res" '(221 -83) 1 1 0 )
(command "insert" "Res" '(207 -95) 1 1 0 )
(command "insert" "Res" '(220 -98) 1 1 0 )
(command "insert" "Res" '(206 -90) 1 1 0 )
(command "insert" "Res" '(220 -83) 1 1 0 )
(command "insert" "Res" '(217 -87) 1 1 0 )
(command "insert" "Res" '(214 -84) 1 1 0 )
(command "insert" "Res" '(215 -94) 1 1 0 )
(command "insert" "Res" '(219 -84) 1 1 0 )
(command "insert" "Res" '(220 -94) 1 1 0 )
(command "insert" "Res" '(202 -96) 1 1 0 )
(command "insert" "Res" '(210 -98) 1 1 0 )
(command "insert" "Res" '(214 -91) 1 1 0 )
(command "insert" "Res" '(204 -96) 1 1 0 )
(command "insert" "Res" '(209 -97) 1 1 0 )
(command "insert" "Res" '(221 -86) 1 1 0 )
(command "insert" "Res" '(222 -92) 1 1 0 )
(command "insert" "Res" '(216 -87) 1 1 0 )
(command "insert" "Res" '(219 -96) 1 1 0 )
(command "insert" "Res" '(217 -93) 1 1 0 )
(command "insert" "Res" '(218 -85) 1 1 0 )
(command "insert" "Res" '(215 -93) 1 1 0 )
(command "insert" "Res" '(219 -83) 1 1 0 )
(command "insert" "Res" '(220 -84) 1 1 0 )
(command "insert" "Res" '(209 -95) 1 1 0 )
(command "insert" "Res" '(201 -95) 1 1 0 )
(command "insert" "Res" '(206 -93) 1 1 0 )
(command "insert" "Res" '(216 -84) 1 1 0 )
(command "insert" "Res" '(208 -95) 1 1 0 )
(command "insert" "Res" '(213 -86) 1 1 0 )
(command "insert" "Res" '(217 -88) 1 1 0 )
(command "insert" "Res" '(218 -86) 1 1 0 )
(command "insert" "Res" '(208 -98) 1 1 0 )
(command "insert" "Res" '(221 -96) 1 1 0 )
(command "insert" "Res" '(205 -91) 1 1 0 )
(command "insert" "Res" '(220 -85) 1 1 0 )
(command "insert" "Res" '(204 -94) 1 1 0 )
(command "insert" "Res" '(219 -94) 1 1 0 )
(command "insert" "Res" '(216 -94) 1 1 0 )
(command "insert" "Res" '(222 -90) 1 1 0 )
(command "insert" "Res" '(206 -94) 1 1 0 )
(command "insert" "Res" '(212 -98) 1 1 0 )
(command "insert" "Res" '(213 -92) 1 1 0 )
(command "insert" "Res" '(223 -90) 1 1 0 )
(command "insert" "Res" '(215 -90) 1 1 0 )
(command "insert" "Res" '(205 -94) 1 1 0 )
(command "insert" "Res" '(214 -95) 1 1 0 )
(command "insert" "Res" '(205 -96) 1 1 0 )
(command "insert" "Res" '(219 -93) 1 1 0 )
(command "insert" "Res" '(203 -96) 1 1 0 )
(command "insert" "Res" '(204 -97) 1 1 0 )
(command "insert" "Res" '(207 -94) 1 1 0 )
(command "insert" "Res" '(221 -95) 1 1 0 )
(command "insert" "Res" '(206 -91) 1 1 0 )
(command "insert" "Res" '(213 -95) 1 1 0 )
(command "insert" "Res" '(217 -86) 1 1 0 )
(command "insert" "Res" '(214 -85) 1 1 0 )
(command "insert" "Res" '(224 -92) 1 1 0 )
(command "insert" "Res" '(220 -95) 1 1 0 )
(command "insert" "Res" '(202 -97) 1 1 0 )
(command "insert" "Res" '(207 -98) 1 1 0 )
(command "insert" "Res" '(209 -96) 1 1 0 )
(command "insert" "Res" '(224 -91) 1 1 0 )
(command "insert" "Res" '(221 -85) 1 1 0 )
(command "insert" "Res" '(207 -93) 1 1 0 )
(command "insert" "Res" '(220 -96) 1 1 0 )
(command "insert" "Res" '(219 -98) 1 1 0 )
(command "insert" "Res" '(223 -92) 1 1 0 )
(command "insert" "Res" '(208 -97) 1 1 0 )
(command "insert" "Res" '(220 -81) 1 1 0 )
(command "insert" "Res" '(214 -86) 1 1 0 )
(command "insert" "Res" '(215 -92) 1 1 0 )
(command "insert" "Res" '(204 -90) 1 1 0 )
(command "insert" "Res" '(219 -82) 1 1 0 )
(command "insert" "Res" '(209 -94) 1 1 0 )
(command "insert" "Res" '(207 -97) 1 1 0 )
(command "insert" "Res" '(211 -98) 1 1 0 )
(command "insert" "Res" '(216 -88) 1 1 0 )
(command "insert" "Res" '(201 -94) 1 1 0 )
(command "insert" "Res" '(206 -96) 1 1 0 )
(command "insert" "Res" '(216 -85) 1 1 0 )
(command "insert" "Res" '(218 -88) 1 1 0 )
(command "insert" "Res" '(213 -85) 1 1 0 )
(command "insert" "Res" '(217 -95) 1 1 0 )
(command "insert" "Res" '(201 -98) 1 1 0 )
(command "insert" "Res" '(215 -86) 1 1 0 )
(command "insert" "Res" '(205 -90) 1 1 0 )
(command "insert" "Res" '(220 -86) 1 1 0 )
(command "insert" "Res" '(204 -95) 1 1 0 )
(command "insert" "Res" '(219 -81) 1 1 0 )
(command "insert" "Res" '(219 -95) 1 1 0 )
(command "insert" "Res" '(211 -97) 1 1 0 )
(command "insert" "Res" '(216 -95) 1 1 0 )
(command "insert" "Res" '(224 -90) 1 1 0 )
(command "insert" "Res" '(222 -91) 1 1 0 )
(command "insert" "Res" '(206 -95) 1 1 0 )
(command "insert" "Res" '(213 -91) 1 1 0 )
(command "insert" "Res" '(203 -95) 1 1 0 )
(command "insert" "Res" '(218 -93) 1 1 0 )
(command "insert" "Res" '(208 -93) 1 1 0 )
(command "insert" "Res" '(208 -96) 1 1 0 )
(command "insert" "Res" '(221 -98) 1 1 0 )
(command "insert" "Res" '(205 -93) 1 1 0 )
(command "insert" "Res" '(214 -92) 1 1 0 )
(command "insert" "Res" '(204 -92) 1 1 0 )
(command "insert" "Res" '(215 -85) 1 1 0 )
(command "insert" "Res" '(204 -98) 1 1 0 )
(command "insert" "Res" '(221 -94) 1 1 0 )
(command "insert" "Res" '(212 -96) 1 1 0 )
(command "insert" "Res" '(213 -94) 1 1 0 )
(command "insert" "Res" '(218 -94) 1 1 0 )
(command "insert" "Res" '(217 -85) 1 1 0 )
(command "insert" "Res" '(219 -86) 1 1 0 )
(command "insert" "Res" '(210 -96) 1 1 0 )
(command "insert" "Res" '(205 -98) 1 1 0 )
(command "insert" "Res" '(221 -84) 1 1 0 )
(command "insert" "Res" '(218 -87) 1 1 0 )
(command "insert" "Res" '(216 -89) 1 1 0 )
(command "insert" "Res" '(220 -97) 1 1 0 )
(command "insert" "Res" '(202 -93) 1 1 0 )
(command "insert" "Res" '(202 -95) 1 1 0 )
(command "insert" "Res" '(215 -95) 1 1 0 )
(command "insert" "Res" '(204 -91) 1 1 0 )
(command "insert" "Res" '(219 -85) 1 1 0 )
(command "insert" "Res" '(220 -93) 1 1 0 )
(command "insert" "Res" '(209 -93) 1 1 0 )
(command "insert" "Res" '(214 -90) 1 1 0 )
(command "insert" "Res" '(207 -96) 1 1 0 )
(command "insert" "Res" '(201 -96) 1 1 0 )
(command "insert" "Res" '(221 -81) 1 1 0 )
(command "insert" "Res" '(220 -82) 1 1 0 )
(command "insert" "Res" '(201 -93) 1 1 0 )
(command "insert" "Res" '(206 -97) 1 1 0 )
(command "insert" "Res" '(216 -86) 1 1 0 )
(command "insert" "Res" '(218 -89) 1 1 0 )
(command "insert" "Res" '(209 -98) 1 1 0 )
(command "insert" "Res" '(219 -97) 1 1 0 )
(command "insert" "Res" '(217 -94) 1 1 0 )
(command "insert" "Res" '(218 -84) 1 1 0 )
(command "insert" "Res" '(203 -98) 1 1 0 )
(command "insert" "Res" '(211 -96) 1 1 0 )
(command "insert" "Res" '(206 -98) 1 1 0 )
(command "insert" "Res" '(206 -92) 1 1 0 )
(command "insert" "Res" '(213 -90) 1 1 0 )
(command "insert" "Res" '(203 -94) 1 1 0 )
(command "insert" "Res" '(208 -94) 1 1 0 )
(command "insert" "Res" '(217 -89) 1 1 0 )
(command "insert" "Res" '(213 -84) 1 1 0 )
(command "insert" "Res" '(215 -84) 1 1 0 )
(command "insert" "Res" '(221 -97) 1 1 0 )
(command "insert" "Res" '(205 -92) 1 1 0 )
(command "insert" "Res" '(203 -97) 1 1 0 )
(command "insert" "Res" '(214 -93) 1 1 0 )
(command "insert" "Res" '(204 -93) 1 1 0 )
(command "insert" "Res" '(221 -82) 1 1 0 )
(command "insert" "Res" '(202 -98) 1 1 0 )
(command "insert" "Res" '(201 -97) 1 1 0 )
(command "insert" "Res" '(216 -93) 1 1 0 )
(command "insert" "Res" '(221 -93) 1 1 0 )
(command "insert" "Res" '(212 -97) 1 1 0 )
(command "insert" "Res" '(213 -93) 1 1 0 )
(command "insert" "Res" '(203 -93) 1 1 0 )
(command "insert" "Res" '(218 -95) 1 1 0 )
(command "insert" "Res" '(223 -91) 1 1 0 )
(command "insert" "Res" '(217 -84) 1 1 0 )
(command "insert" "Res" '(215 -91) 1 1 0 )
(command "insert" "Res" '(205 -95) 1 1 0 )
(command "insert" "Res" '(202 -94) 1 1 0 )
(command "insert" "Res" '(210 -97) 1 1 0 )
(command "insert" "Res" '(214 -94) 1 1 0 )
(command "layer" "m" "Idust" "" )
(command "insert" "Idust" '(41 -13) 1 1 0 )
(command "insert" "Idust" '(31 -6) 1 1 0 )
(command "insert" "Idust" '(55 -5) 1 1 0 )
(command "insert" "Idust" '(8 -7) 1 1 0 )
(command "insert" "Idust" '(42 -10) 1 1 0 )
(command "insert" "Idust" '(16 -9) 1 1 0 )
(command "insert" "Idust" '(24 -5) 1 1 0 )
(command "insert" "Idust" '(19 -4) 1 1 0 )
(command "insert" "Idust" '(43 -3) 1 1 0 )
(command "insert" "Idust" '(46 -12) 1 1 0 )
(command "insert" "Idust" '(20 -7) 1 1 0 )
(command "insert" "Idust" '(44 -4) 1 1 0 )
(command "insert" "Idust" '(57 -20) 1 1 0 )
(command "insert" "Idust" '(47 -9) 1 1 0 )
(command "insert" "Idust" '(21 -6) 1 1 0 )
(command "insert" "Idust" '(45 -9) 1 1 0 )
(command "insert" "Idust" '(58 -19) 1 1 0 )
(command "insert" "Idust" '(33 -3) 1 1 0 )
(command "insert" "Idust" '(36 -8) 1 1 0 )
(command "insert" "Idust" '(10 -7) 1 1 0 )
(command "insert" "Idust" '(34 -8) 1 1 0 )
(command "insert" "Idust" '(17 -7) 1 1 0 )
(command "insert" "Idust" '(37 -13) 1 1 0 )
(command "insert" "Idust" '(24 -14) 1 1 0 )
(command "insert" "Idust" '(15 -4) 1 1 0 )
(command "insert" "Idust" '(39 -11) 1 1 0 )
(command "insert" "Idust" '(52 -17) 1 1 0 )
(command "insert" "Idust" '(26 -12) 1 1 0 )
(command "insert" "Idust" '(53 -16) 1 1 0 )
(command "insert" "Idust" '(64 -20) 1 1 0 )
(command "insert" "Idust" '(4 -5) 1 1 0 )
(command "insert" "Idust" '(28 -10) 1 1 0 )
(command "insert" "Idust" '(65 -17) 1 1 0 )
(command "insert" "Idust" '(29 -11) 1 1 0 )
(command "insert" "Idust" '(64 -10) 1 1 0 )
(command "insert" "Idust" '(19 -13) 1 1 0 )
(command "insert" "Idust" '(67 -7) 1 1 0 )
(command "insert" "Idust" '(65 -11) 1 1 0 )
(command "insert" "Idust" '(20 -14) 1 1 0 )
(command "insert" "Idust" '(44 -3) 1 1 0 )
(command "insert" "Idust" '(18 -10) 1 1 0 )
(command "insert" "Idust" '(69 -5) 1 1 0 )
(command "insert" "Idust" '(8 -12) 1 1 0 )
(command "insert" "Idust" '(56 -6) 1 1 0 )
(command "insert" "Idust" '(70 -10) 1 1 0 )
(command "insert" "Idust" '(59 -19) 1 1 0 )
(command "insert" "Idust" '(33 -4) 1 1 0 )
(command "insert" "Idust" '(57 -7) 1 1 0 )
(command "insert" "Idust" '(60 -20) 1 1 0 )
(command "insert" "Idust" '(34 -3) 1 1 0 )
(command "insert" "Idust" '(58 -4) 1 1 0 )
(command "insert" "Idust" '(59 -9) 1 1 0 )
(command "insert" "Idust" '(14 -8) 1 1 0 )
(command "insert" "Idust" '(38 -5) 1 1 0 )
(command "insert" "Idust" '(62 -6) 1 1 0 )
(command "insert" "Idust" '(15 -13) 1 1 0 )
(command "insert" "Idust" '(63 -7) 1 1 0 )
(command "insert" "Idust" '(40 -14) 1 1 0 )
(command "insert" "Idust" '(48 -8) 1 1 0 )
(command "insert" "Idust" '(3 -11) 1 1 0 )
(command "insert" "Idust" '(27 -6) 1 1 0 )
(command "insert" "Idust" '(51 -5) 1 1 0 )
(command "insert" "Idust" '(54 -18) 1 1 0 )
(command "insert" "Idust" '(52 -6) 1 1 0 )
(command "insert" "Idust" '(29 -4) 1 1 0 )
(command "insert" "Idust" '(53 -7) 1 1 0 )
(command "insert" "Idust" '(66 -17) 1 1 0 )
(command "insert" "Idust" '(40 -4) 1 1 0 )
(command "insert" "Idust" '(67 -12) 1 1 0 )
(command "insert" "Idust" '(65 -12) 1 1 0 )
(command "insert" "Idust" '(8 -5) 1 1 0 )
(command "insert" "Idust" '(68 -15) 1 1 0 )
(command "insert" "Idust" '(42 -6) 1 1 0 )
(command "insert" "Idust" '(66 -11) 1 1 0 )
(command "insert" "Idust" '(21 -8) 1 1 0 )
(command "insert" "Idust" '(57 -9) 1 1 0 )
(command "insert" "Idust" '(69 -14) 1 1 0 )
(command "insert" "Idust" '(56 -13) 1 1 0 )
(command "insert" "Idust" '(70 -13) 1 1 0 )
(command "insert" "Idust" '(57 -8) 1 1 0 )
(command "insert" "Idust" '(47 -5) 1 1 0 )
(command "insert" "Idust" '(71 -8) 1 1 0 )
(command "insert" "Idust" '(60 -19) 1 1 0 )
(command "insert" "Idust" '(58 -15) 1 1 0 )
(command "insert" "Idust" '(61 -18) 1 1 0 )
(command "insert" "Idust" '(35 -3) 1 1 0 )
(command "insert" "Idust" '(59 -14) 1 1 0 )
(command "insert" "Idust" '(60 -18) 1 1 0 )
(command "insert" "Idust" '(62 -9) 1 1 0 )
(command "insert" "Idust" '(36 -4) 1 1 0 )
(command "insert" "Idust" '(60 -9) 1 1 0 )
(command "insert" "Idust" '(15 -10) 1 1 0 )
(command "insert" "Idust" '(63 -12) 1 1 0 )
(command "insert" "Idust" '(61 -12) 1 1 0 )
(command "insert" "Idust" '(62 -19) 1 1 0 )
(command "insert" "Idust" '(51 -10) 1 1 0 )
(command "insert" "Idust" '(25 -3) 1 1 0 )
(command "insert" "Idust" '(49 -14) 1 1 0 )
(command "insert" "Idust" '(4 -11) 1 1 0 )
(command "insert" "Idust" '(52 -13) 1 1 0 )
(command "insert" "Idust" '(50 -13) 1 1 0 )
(command "insert" "Idust" '(5 -10) 1 1 0 )
(command "insert" "Idust" '(40 -11) 1 1 0 )
(command "insert" "Idust" '(11 -5) 1 1 0 )
(command "insert" "Idust" '(54 -15) 1 1 0 )
(command "insert" "Idust" '(41 -10) 1 1 0 )
(command "insert" "Idust" '(65 -5) 1 1 0 )
(command "insert" "Idust" '(55 -14) 1 1 0 )
(command "insert" "Idust" '(18 -6) 1 1 0 )
(command "insert" "Idust" '(43 -12) 1 1 0 )
(command "insert" "Idust" '(56 -20) 1 1 0 )
(command "insert" "Idust" '(46 -11) 1 1 0 )
(command "insert" "Idust" '(70 -4) 1 1 0 )
(command "insert" "Idust" '(57 -17) 1 1 0 )
(command "insert" "Idust" '(55 -19) 1 1 0 )
(command "insert" "Idust" '(45 -14) 1 1 0 )
(command "insert" "Idust" '(32 -13) 1 1 0 )
(command "insert" "Idust" '(12 -6) 1 1 0 )
(command "insert" "Idust" '(35 -8) 1 1 0 )
(command "insert" "Idust" '(59 -7) 1 1 0 )
(command "insert" "Idust" '(33 -8) 1 1 0 )
(command "insert" "Idust" '(36 -3) 1 1 0 )
(command "insert" "Idust" '(61 -5) 1 1 0 )
(command "insert" "Idust" '(24 -9) 1 1 0 )
(command "insert" "Idust" '(48 -6) 1 1 0 )
(command "insert" "Idust" '(38 -9) 1 1 0 )
(command "insert" "Idust" '(25 -4) 1 1 0 )
(command "insert" "Idust" '(49 -7) 1 1 0 )
(command "insert" "Idust" '(39 -12) 1 1 0 )
(command "insert" "Idust" '(63 -19) 1 1 0 )
(command "insert" "Idust" '(40 -12) 1 1 0 )
(command "insert" "Idust" '(26 -3) 1 1 0 )
(command "insert" "Idust" '(50 -4) 1 1 0 )
(command "insert" "Idust" '(53 -9) 1 1 0 )
(command "insert" "Idust" '(27 -10) 1 1 0 )
(command "insert" "Idust" '(63 -13) 1 1 0 )
(command "insert" "Idust" '(30 -5) 1 1 0 )
(command "insert" "Idust" '(54 -6) 1 1 0 )
(command "insert" "Idust" '(28 -13) 1 1 0 )
(command "insert" "Idust" '(55 -7) 1 1 0 )
(command "insert" "Idust" '(42 -8) 1 1 0 )
(command "insert" "Idust" '(16 -11) 1 1 0 )
(command "insert" "Idust" '(19 -6) 1 1 0 )
(command "insert" "Idust" '(43 -5) 1 1 0 )
(command "insert" "Idust" '(17 -10) 1 1 0 )
(command "insert" "Idust" '(44 -6) 1 1 0 )
(command "insert" "Idust" '(41 -9) 1 1 0 )
(command "insert" "Idust" '(47 -11) 1 1 0 )
(command "insert" "Idust" '(21 -4) 1 1 0 )
(command "insert" "Idust" '(45 -7) 1 1 0 )
(command "insert" "Idust" '(58 -17) 1 1 0 )
(command "insert" "Idust" '(32 -4) 1 1 0 )
(command "insert" "Idust" '(22 -11) 1 1 0 )
(command "insert" "Idust" '(62 -12) 1 1 0 )
(command "insert" "Idust" '(9 -6) 1 1 0 )
(command "insert" "Idust" '(36 -10) 1 1 0 )
(command "insert" "Idust" '(10 -5) 1 1 0 )
(command "insert" "Idust" '(34 -6) 1 1 0 )
(command "insert" "Idust" '(37 -11) 1 1 0 )
(command "insert" "Idust" '(11 -8) 1 1 0 )
(command "insert" "Idust" '(60 -16) 1 1 0 )
(command "insert" "Idust" '(14 -7) 1 1 0 )
(command "insert" "Idust" '(51 -11) 1 1 0 )
(command "insert" "Idust" '(25 -13) 1 1 0 )
(command "insert" "Idust" '(15 -6) 1 1 0 )
(command "insert" "Idust" '(39 -5) 1 1 0 )
(command "insert" "Idust" '(26 -10) 1 1 0 )
(command "insert" "Idust" '(3 -4) 1 1 0 )
(command "insert" "Idust" '(27 -3) 1 1 0 )
(command "insert" "Idust" '(30 -12) 1 1 0 )
(command "insert" "Idust" '(4 -7) 1 1 0 )
(command "insert" "Idust" '(28 -4) 1 1 0 )
(command "insert" "Idust" '(66 -16) 1 1 0 )
(command "insert" "Idust" '(31 -9) 1 1 0 )
(command "insert" "Idust" '(5 -6) 1 1 0 )
(command "insert" "Idust" '(29 -9) 1 1 0 )
(command "insert" "Idust" '(64 -12) 1 1 0 )
(command "insert" "Idust" '(67 -9) 1 1 0 )
(command "insert" "Idust" '(65 -9) 1 1 0 )
(command "insert" "Idust" '(20 -8) 1 1 0 )
(command "insert" "Idust" '(18 -8) 1 1 0 )
(command "insert" "Idust" '(66 -14) 1 1 0 )
(command "insert" "Idust" '(21 -13) 1 1 0 )
(command "insert" "Idust" '(69 -3) 1 1 0 )
(command "insert" "Idust" '(8 -14) 1 1 0 )
(command "insert" "Idust" '(56 -8) 1 1 0 )
(command "insert" "Idust" '(70 -8) 1 1 0 )
(command "insert" "Idust" '(57 -5) 1 1 0 )
(command "insert" "Idust" '(30 -14) 1 1 0 )
(command "insert" "Idust" '(10 -12) 1 1 0 )
(command "insert" "Idust" '(24 -12) 1 1 0 )
(command "insert" "Idust" '(12 -4) 1 1 0 )
(command "insert" "Idust" '(59 -11) 1 1 0 )
(command "insert" "Idust" '(14 -14) 1 1 0 )
(command "insert" "Idust" '(62 -4) 1 1 0 )
(command "insert" "Idust" '(60 -12) 1 1 0 )
(command "insert" "Idust" '(13 -11) 1 1 0 )
(command "insert" "Idust" '(48 -10) 1 1 0 )
(command "insert" "Idust" '(3 -13) 1 1 0 )
(command "insert" "Idust" '(51 -7) 1 1 0 )
(command "insert" "Idust" '(12 -9) 1 1 0 )
(command "insert" "Idust" '(49 -11) 1 1 0 )
(command "insert" "Idust" '(54 -16) 1 1 0 )
(command "insert" "Idust" '(28 -3) 1 1 0 )
(command "insert" "Idust" '(53 -5) 1 1 0 )
(command "insert" "Idust" '(63 -3) 1 1 0 )
(command "insert" "Idust" '(40 -6) 1 1 0 )
(command "insert" "Idust" '(64 -3) 1 1 0 )
(command "insert" "Idust" '(54 -10) 1 1 0 )
(command "insert" "Idust" '(67 -14) 1 1 0 )
(command "insert" "Idust" '(41 -7) 1 1 0 )
(command "insert" "Idust" '(68 -9) 1 1 0 )
(command "insert" "Idust" '(42 -4) 1 1 0 )
(command "insert" "Idust" '(66 -9) 1 1 0 )
(command "insert" "Idust" '(69 -12) 1 1 0 )
(command "insert" "Idust" '(43 -9) 1 1 0 )
(command "insert" "Idust" '(56 -15) 1 1 0 )
(command "insert" "Idust" '(46 -6) 1 1 0 )
(command "insert" "Idust" '(70 -3) 1 1 0 )
(command "insert" "Idust" '(59 -20) 1 1 0 )
(command "insert" "Idust" '(7 -5) 1 1 0 )
(command "insert" "Idust" '(57 -14) 1 1 0 )
(command "insert" "Idust" '(47 -7) 1 1 0 )
(command "insert" "Idust" '(71 -10) 1 1 0 )
(command "insert" "Idust" '(23 -11) 1 1 0 )
(command "insert" "Idust" '(7 -11) 1 1 0 )
(command "insert" "Idust" '(58 -13) 1 1 0 )
(command "insert" "Idust" '(32 -8) 1 1 0 )
(command "insert" "Idust" '(61 -16) 1 1 0 )
(command "insert" "Idust" '(35 -5) 1 1 0 )
(command "insert" "Idust" '(71 -13) 1 1 0 )
(command "insert" "Idust" '(62 -15) 1 1 0 )
(command "insert" "Idust" '(36 -6) 1 1 0 )
(command "insert" "Idust" '(60 -11) 1 1 0 )
(command "insert" "Idust" '(63 -14) 1 1 0 )
(command "insert" "Idust" '(37 -7) 1 1 0 )
(command "insert" "Idust" '(61 -10) 1 1 0 )
(command "insert" "Idust" '(24 -4) 1 1 0 )
(command "insert" "Idust" '(5 -8) 1 1 0 )
(command "insert" "Idust" '(62 -17) 1 1 0 )
(command "insert" "Idust" '(51 -12) 1 1 0 )
(command "insert" "Idust" '(49 -12) 1 1 0 )
(command "insert" "Idust" '(17 -13) 1 1 0 )
(command "insert" "Idust" '(63 -20) 1 1 0 )
(command "insert" "Idust" '(52 -15) 1 1 0 )
(command "insert" "Idust" '(26 -6) 1 1 0 )
(command "insert" "Idust" '(50 -11) 1 1 0 )
(command "insert" "Idust" '(55 -18) 1 1 0 )
(command "insert" "Idust" '(53 -14) 1 1 0 )
(command "insert" "Idust" '(40 -13) 1 1 0 )
(command "insert" "Idust" '(54 -13) 1 1 0 )
(command "insert" "Idust" '(41 -8) 1 1 0 )
(command "insert" "Idust" '(31 -5) 1 1 0 )
(command "insert" "Idust" '(55 -8) 1 1 0 )
(command "insert" "Idust" '(19 -3) 1 1 0 )
(command "insert" "Idust" '(43 -14) 1 1 0 )
(command "insert" "Idust" '(46 -9) 1 1 0 )
(command "insert" "Idust" '(20 -4) 1 1 0 )
(command "insert" "Idust" '(44 -9) 1 1 0 )
(command "insert" "Idust" '(47 -12) 1 1 0 )
(command "insert" "Idust" '(71 -3) 1 1 0 )
(command "insert" "Idust" '(45 -12) 1 1 0 )
(command "insert" "Idust" '(58 -20) 1 1 0 )
(command "insert" "Idust" '(35 -10) 1 1 0 )
(command "insert" "Idust" '(9 -3) 1 1 0 )
(command "insert" "Idust" '(33 -14) 1 1 0 )
(command "insert" "Idust" '(30 -8) 1 1 0 )
(command "insert" "Idust" '(36 -13) 1 1 0 )
(command "insert" "Idust" '(34 -13) 1 1 0 )
(command "insert" "Idust" '(18 -12) 1 1 0 )
(command "insert" "Idust" '(61 -3) 1 1 0 )
(command "insert" "Idust" '(24 -11) 1 1 0 )
(command "insert" "Idust" '(25 -10) 1 1 0 )
(command "insert" "Idust" '(49 -5) 1 1 0 )
(command "insert" "Idust" '(39 -14) 1 1 0 )
(command "insert" "Idust" '(62 -5) 1 1 0 )
(command "insert" "Idust" '(27 -12) 1 1 0 )
(command "insert" "Idust" '(30 -11) 1 1 0 )
(command "insert" "Idust" '(54 -4) 1 1 0 )
(command "insert" "Idust" '(31 -13) 1 1 0 )
(command "insert" "Idust" '(22 -12) 1 1 0 )
(command "insert" "Idust" '(29 -14) 1 1 0 )
(command "insert" "Idust" '(16 -13) 1 1 0 )
(command "insert" "Idust" '(19 -8) 1 1 0 )
(command "insert" "Idust" '(43 -7) 1 1 0 )
(command "insert" "Idust" '(17 -8) 1 1 0 )
(command "insert" "Idust" '(11 -4) 1 1 0 )
(command "insert" "Idust" '(20 -3) 1 1 0 )
(command "insert" "Idust" '(68 -5) 1 1 0 )
(command "insert" "Idust" '(45 -5) 1 1 0 )
(command "insert" "Idust" '(9 -9) 1 1 0 )
(command "insert" "Idust" '(8 -9) 1 1 0 )
(command "insert" "Idust" '(32 -6) 1 1 0 )
(command "insert" "Idust" '(56 -3) 1 1 0 )
(command "insert" "Idust" '(9 -4) 1 1 0 )
(command "insert" "Idust" '(33 -7) 1 1 0 )
(command "insert" "Idust" '(23 -12) 1 1 0 )
(command "insert" "Idust" '(23 -9) 1 1 0 )
(command "insert" "Idust" '(10 -3) 1 1 0 )
(command "insert" "Idust" '(34 -4) 1 1 0 )
(command "insert" "Idust" '(37 -9) 1 1 0 )
(command "insert" "Idust" '(11 -10) 1 1 0 )
(command "insert" "Idust" '(14 -5) 1 1 0 )
(command "insert" "Idust" '(38 -6) 1 1 0 )
(command "insert" "Idust" '(62 -3) 1 1 0 )
(command "insert" "Idust" '(39 -7) 1 1 0 )
(command "insert" "Idust" '(26 -8) 1 1 0 )
(command "insert" "Idust" '(10 -14) 1 1 0 )
(command "insert" "Idust" '(3 -6) 1 1 0 )
(command "insert" "Idust" '(27 -5) 1 1 0 )
(command "insert" "Idust" '(28 -6) 1 1 0 )
(command "insert" "Idust" '(31 -11) 1 1 0 )
(command "insert" "Idust" '(5 -4) 1 1 0 )
(command "insert" "Idust" '(29 -7) 1 1 0 )
(command "insert" "Idust" '(16 -4) 1 1 0 )
(command "insert" "Idust" '(6 -11) 1 1 0 )
(command "insert" "Idust" '(64 -14) 1 1 0 )
(command "insert" "Idust" '(67 -11) 1 1 0 )
(command "insert" "Idust" '(65 -15) 1 1 0 )
(command "insert" "Idust" '(20 -10) 1 1 0 )
(command "insert" "Idust" '(68 -12) 1 1 0 )
(command "insert" "Idust" '(66 -12) 1 1 0 )
(command "insert" "Idust" '(21 -11) 1 1 0 )
(command "insert" "Idust" '(67 -17) 1 1 0 )
(command "insert" "Idust" '(56 -10) 1 1 0 )
(command "insert" "Idust" '(70 -14) 1 1 0 )
(command "insert" "Idust" '(9 -13) 1 1 0 )
(command "insert" "Idust" '(12 -5) 1 1 0 )
(command "insert" "Idust" '(57 -11) 1 1 0 )
(command "insert" "Idust" '(10 -10) 1 1 0 )
(command "insert" "Idust" '(11 -3) 1 1 0 )
(command "insert" "Idust" '(59 -13) 1 1 0 )
(command "insert" "Idust" '(14 -12) 1 1 0 )
(command "insert" "Idust" '(62 -10) 1 1 0 )
(command "insert" "Idust" '(60 -14) 1 1 0 )
(command "insert" "Idust" '(15 -9) 1 1 0 )
(command "insert" "Idust" '(22 -3) 1 1 0 )
(command "insert" "Idust" '(13 -9) 1 1 0 )
(command "insert" "Idust" '(61 -15) 1 1 0 )
(command "insert" "Idust" '(48 -12) 1 1 0 )
(command "insert" "Idust" '(51 -9) 1 1 0 )
(command "insert" "Idust" '(49 -9) 1 1 0 )
(command "insert" "Idust" '(4 -8) 1 1 0 )
(command "insert" "Idust" '(50 -14) 1 1 0 )
(command "insert" "Idust" '(5 -13) 1 1 0 )
(command "insert" "Idust" '(53 -3) 1 1 0 )
(command "insert" "Idust" '(40 -8) 1 1 0 )
(command "insert" "Idust" '(64 -5) 1 1 0 )
(command "insert" "Idust" '(54 -8) 1 1 0 )
(command "insert" "Idust" '(6 -12) 1 1 0 )
(command "insert" "Idust" '(41 -5) 1 1 0 )
(command "insert" "Idust" '(55 -13) 1 1 0 )
(command "insert" "Idust" '(68 -11) 1 1 0 )
(command "insert" "Idust" '(13 -13) 1 1 0 )
(command "insert" "Idust" '(66 -7) 1 1 0 )
(command "insert" "Idust" '(69 -10) 1 1 0 )
(command "insert" "Idust" '(43 -11) 1 1 0 )
(command "insert" "Idust" '(56 -17) 1 1 0 )
(command "insert" "Idust" '(46 -4) 1 1 0 )
(command "insert" "Idust" '(44 -12) 1 1 0 )
(command "insert" "Idust" '(68 -17) 1 1 0 )
(command "insert" "Idust" '(57 -12) 1 1 0 )
(command "insert" "Idust" '(71 -4) 1 1 0 )
(command "insert" "Idust" '(9 -11) 1 1 0 )
(command "insert" "Idust" '(58 -11) 1 1 0 )
(command "insert" "Idust" '(32 -10) 1 1 0 )
(command "insert" "Idust" '(35 -7) 1 1 0 )
(command "insert" "Idust" '(33 -11) 1 1 0 )
(command "insert" "Idust" '(12 -3) 1 1 0 )
(command "insert" "Idust" '(60 -5) 1 1 0 )
(command "insert" "Idust" '(63 -8) 1 1 0 )
(command "insert" "Idust" '(37 -5) 1 1 0 )
(command "insert" "Idust" '(61 -8) 1 1 0 )
(command "insert" "Idust" '(24 -6) 1 1 0 )
(command "insert" "Idust" '(48 -3) 1 1 0 )
(command "insert" "Idust" '(38 -10) 1 1 0 )
(command "insert" "Idust" '(51 -14) 1 1 0 )
(command "insert" "Idust" '(25 -7) 1 1 0 )
(command "insert" "Idust" '(52 -9) 1 1 0 )
(command "insert" "Idust" '(26 -4) 1 1 0 )
(command "insert" "Idust" '(50 -9) 1 1 0 )
(command "insert" "Idust" '(18 -3) 1 1 0 )
(command "insert" "Idust" '(53 -12) 1 1 0 )
(command "insert" "Idust" '(27 -9) 1 1 0 )
(command "insert" "Idust" '(6 -5) 1 1 0 )
(command "insert" "Idust" '(30 -6) 1 1 0 )
(command "insert" "Idust" '(54 -3) 1 1 0 )
(command "insert" "Idust" '(40 -9) 1 1 0 )
(command "insert" "Idust" '(41 -14) 1 1 0 )
(command "insert" "Idust" '(31 -7) 1 1 0 )
(command "insert" "Idust" '(55 -10) 1 1 0 )
(command "insert" "Idust" '(42 -13) 1 1 0 )
(command "insert" "Idust" '(16 -8) 1 1 0 )
(command "insert" "Idust" '(19 -5) 1 1 0 )
(command "insert" "Idust" '(4 -12) 1 1 0 )
(command "insert" "Idust" '(62 -13) 1 1 0 )
(command "insert" "Idust" '(44 -11) 1 1 0 )
(command "insert" "Idust" '(47 -14) 1 1 0 )
(command "insert" "Idust" '(21 -7) 1 1 0 )
(command "insert" "Idust" '(45 -10) 1 1 0 )
(command "insert" "Idust" '(58 -18) 1 1 0 )
(command "insert" "Idust" '(18 -14) 1 1 0 )
(command "insert" "Idust" '(35 -12) 1 1 0 )
(command "insert" "Idust" '(33 -12) 1 1 0 )
(command "insert" "Idust" '(7 -3) 1 1 0 )
(command "insert" "Idust" '(10 -6) 1 1 0 )
(command "insert" "Idust" '(34 -11) 1 1 0 )
(command "insert" "Idust" '(37 -14) 1 1 0 )
(command "insert" "Idust" '(24 -13) 1 1 0 )
(command "insert" "Idust" '(22 -5) 1 1 0 )
(command "insert" "Idust" '(38 -13) 1 1 0 )
(command "insert" "Idust" '(25 -8) 1 1 0 )
(command "insert" "Idust" '(15 -5) 1 1 0 )
(command "insert" "Idust" '(39 -8) 1 1 0 )
(command "insert" "Idust" '(52 -16) 1 1 0 )
(command "insert" "Idust" '(3 -3) 1 1 0 )
(command "insert" "Idust" '(27 -14) 1 1 0 )
(command "insert" "Idust" '(64 -19) 1 1 0 )
(command "insert" "Idust" '(4 -4) 1 1 0 )
(command "insert" "Idust" '(28 -9) 1 1 0 )
(command "insert" "Idust" '(22 -4) 1 1 0 )
(command "insert" "Idust" '(65 -18) 1 1 0 )
(command "insert" "Idust" '(55 -3) 1 1 0 )
(command "insert" "Idust" '(29 -12) 1 1 0 )
(command "insert" "Idust" '(16 -7) 1 1 0 )
(command "insert" "Idust" '(64 -9) 1 1 0 )
(command "insert" "Idust" '(64 -17) 1 1 0 )
(command "insert" "Idust" '(19 -10) 1 1 0 )
(command "insert" "Idust" '(6 -14) 1 1 0 )
(command "insert" "Idust" '(67 -4) 1 1 0 )
(command "insert" "Idust" '(20 -13) 1 1 0 )
(command "insert" "Idust" '(68 -7) 1 1 0 )
(command "insert" "Idust" '(63 -5) 1 1 0 )
(command "insert" "Idust" '(45 -3) 1 1 0 )
(command "insert" "Idust" '(69 -6) 1 1 0 )
(command "insert" "Idust" '(8 -11) 1 1 0 )
(command "insert" "Idust" '(56 -5) 1 1 0 )
(command "insert" "Idust" '(59 -16) 1 1 0 )
(command "insert" "Idust" '(33 -5) 1 1 0 )
(command "insert" "Idust" '(23 -14) 1 1 0 )
(command "insert" "Idust" '(58 -7) 1 1 0 )
(command "insert" "Idust" '(17 -6) 1 1 0 )
(command "insert" "Idust" '(11 -12) 1 1 0 )
(command "insert" "Idust" '(14 -11) 1 1 0 )
(command "insert" "Idust" '(38 -4) 1 1 0 )
(command "insert" "Idust" '(57 -3) 1 1 0 )
(command "insert" "Idust" '(63 -4) 1 1 0 )
(command "insert" "Idust" '(3 -8) 1 1 0 )
(command "insert" "Idust" '(27 -7) 1 1 0 )
(command "insert" "Idust" '(11 -6) 1 1 0 )
(command "insert" "Idust" '(4 -3) 1 1 0 )
(command "insert" "Idust" '(52 -5) 1 1 0 )
(command "insert" "Idust" '(29 -5) 1 1 0 )
(command "insert" "Idust" '(16 -6) 1 1 0 )
(command "insert" "Idust" '(40 -3) 1 1 0 )
(command "insert" "Idust" '(67 -13) 1 1 0 )
(command "insert" "Idust" '(7 -12) 1 1 0 )
(command "insert" "Idust" '(65 -13) 1 1 0 )
(command "insert" "Idust" '(68 -14) 1 1 0 )
(command "insert" "Idust" '(66 -10) 1 1 0 )
(command "insert" "Idust" '(21 -9) 1 1 0 )
(command "insert" "Idust" '(22 -6) 1 1 0 )
(command "insert" "Idust" '(46 -3) 1 1 0 )
(command "insert" "Idust" '(70 -12) 1 1 0 )
(command "insert" "Idust" '(23 -7) 1 1 0 )
(command "insert" "Idust" '(71 -9) 1 1 0 )
(command "insert" "Idust" '(10 -8) 1 1 0 )
(command "insert" "Idust" '(58 -14) 1 1 0 )
(command "insert" "Idust" '(61 -19) 1 1 0 )
(command "insert" "Idust" '(59 -15) 1 1 0 )
(command "insert" "Idust" '(62 -8) 1 1 0 )
(command "insert" "Idust" '(60 -8) 1 1 0 )
(command "insert" "Idust" '(15 -11) 1 1 0 )
(command "insert" "Idust" '(13 -7) 1 1 0 )
(command "insert" "Idust" '(61 -13) 1 1 0 )
(command "insert" "Idust" '(48 -14) 1 1 0 )
(command "insert" "Idust" '(62 -18) 1 1 0 )
(command "insert" "Idust" '(13 -4) 1 1 0 )
(command "insert" "Idust" '(54 -20) 1 1 0 )
(command "insert" "Idust" '(52 -12) 1 1 0 )
(command "insert" "Idust" '(50 -12) 1 1 0 )
(command "insert" "Idust" '(55 -17) 1 1 0 )
(command "insert" "Idust" '(40 -10) 1 1 0 )
(command "insert" "Idust" '(64 -7) 1 1 0 )
(command "insert" "Idust" '(54 -14) 1 1 0 )
(command "insert" "Idust" '(41 -11) 1 1 0 )
(command "insert" "Idust" '(65 -6) 1 1 0 )
(command "insert" "Idust" '(55 -15) 1 1 0 )
(command "insert" "Idust" '(8 -6) 1 1 0 )
(command "insert" "Idust" '(56 -12) 1 1 0 )
(command "insert" "Idust" '(66 -5) 1 1 0 )
(command "insert" "Idust" '(23 -6) 1 1 0 )
(command "insert" "Idust" '(69 -8) 1 1 0 )
(command "insert" "Idust" '(43 -13) 1 1 0 )
(command "insert" "Idust" '(56 -19) 1 1 0 )
(command "insert" "Idust" '(46 -10) 1 1 0 )
(command "insert" "Idust" '(70 -7) 1 1 0 )
(command "insert" "Idust" '(44 -14) 1 1 0 )
(command "insert" "Idust" '(57 -18) 1 1 0 )
(command "insert" "Idust" '(47 -3) 1 1 0 )
(command "insert" "Idust" '(71 -6) 1 1 0 )
(command "insert" "Idust" '(58 -9) 1 1 0 )
(command "insert" "Idust" '(32 -12) 1 1 0 )
(command "insert" "Idust" '(35 -9) 1 1 0 )
(command "insert" "Idust" '(59 -4) 1 1 0 )
(command "insert" "Idust" '(33 -9) 1 1 0 )
(command "insert" "Idust" '(60 -7) 1 1 0 )
(command "insert" "Idust" '(34 -14) 1 1 0 )
(command "insert" "Idust" '(63 -10) 1 1 0 )
(command "insert" "Idust" '(37 -3) 1 1 0 )
(command "insert" "Idust" '(61 -6) 1 1 0 )
(command "insert" "Idust" '(24 -8) 1 1 0 )
(command "insert" "Idust" '(48 -5) 1 1 0 )
(command "insert" "Idust" '(38 -8) 1 1 0 )
(command "insert" "Idust" '(51 -16) 1 1 0 )
(command "insert" "Idust" '(25 -5) 1 1 0 )
(command "insert" "Idust" '(39 -13) 1 1 0 )
(command "insert" "Idust" '(63 -16) 1 1 0 )
(command "insert" "Idust" '(52 -11) 1 1 0 )
(command "insert" "Idust" '(50 -7) 1 1 0 )
(command "insert" "Idust" '(53 -10) 1 1 0 )
(command "insert" "Idust" '(27 -11) 1 1 0 )
(command "insert" "Idust" '(53 -17) 1 1 0 )
(command "insert" "Idust" '(30 -4) 1 1 0 )
(command "insert" "Idust" '(28 -12) 1 1 0 )
(command "insert" "Idust" '(41 -12) 1 1 0 )
(command "insert" "Idust" '(55 -4) 1 1 0 )
(command "insert" "Idust" '(18 -7) 1 1 0 )
(command "insert" "Idust" '(42 -11) 1 1 0 )
(command "insert" "Idust" '(16 -10) 1 1 0 )
(command "insert" "Idust" '(19 -7) 1 1 0 )
(command "insert" "Idust" '(17 -11) 1 1 0 )
(command "insert" "Idust" '(46 -13) 1 1 0 )
(command "insert" "Idust" '(44 -5) 1 1 0 )
(command "insert" "Idust" '(47 -8) 1 1 0 )
(command "insert" "Idust" '(21 -5) 1 1 0 )
(command "insert" "Idust" '(45 -8) 1 1 0 )
(command "insert" "Idust" '(58 -16) 1 1 0 )
(command "insert" "Idust" '(32 -3) 1 1 0 )
(command "insert" "Idust" '(22 -10) 1 1 0 )
(command "insert" "Idust" '(12 -7) 1 1 0 )
(command "insert" "Idust" '(35 -14) 1 1 0 )
(command "insert" "Idust" '(9 -7) 1 1 0 )
(command "insert" "Idust" '(36 -9) 1 1 0 )
(command "insert" "Idust" '(10 -4) 1 1 0 )
(command "insert" "Idust" '(34 -9) 1 1 0 )
(command "insert" "Idust" '(37 -12) 1 1 0 )
(command "insert" "Idust" '(11 -9) 1 1 0 )
(command "insert" "Idust" '(14 -6) 1 1 0 )
(command "insert" "Idust" '(38 -3) 1 1 0 )
(command "insert" "Idust" '(25 -14) 1 1 0 )
(command "insert" "Idust" '(15 -7) 1 1 0 )
(command "insert" "Idust" '(39 -10) 1 1 0 )
(command "insert" "Idust" '(17 -4) 1 1 0 )
(command "insert" "Idust" '(6 -7) 1 1 0 )
(command "insert" "Idust" '(26 -13) 1 1 0 )
(command "insert" "Idust" '(3 -5) 1 1 0 )
(command "insert" "Idust" '(13 -6) 1 1 0 )
(command "insert" "Idust" '(4 -6) 1 1 0 )
(command "insert" "Idust" '(28 -11) 1 1 0 )
(command "insert" "Idust" '(65 -16) 1 1 0 )
(command "insert" "Idust" '(5 -7) 1 1 0 )
(command "insert" "Idust" '(29 -10) 1 1 0 )
(command "insert" "Idust" '(64 -11) 1 1 0 )
(command "insert" "Idust" '(19 -12) 1 1 0 )
(command "insert" "Idust" '(67 -6) 1 1 0 )
(command "insert" "Idust" '(65 -10) 1 1 0 )
(command "insert" "Idust" '(8 -4) 1 1 0 )
(command "insert" "Idust" '(18 -11) 1 1 0 )
(command "insert" "Idust" '(7 -6) 1 1 0 )
(command "insert" "Idust" '(21 -14) 1 1 0 )
(command "insert" "Idust" '(57 -10) 1 1 0 )
(command "insert" "Idust" '(69 -4) 1 1 0 )
(command "insert" "Idust" '(8 -13) 1 1 0 )
(command "insert" "Idust" '(56 -7) 1 1 0 )
(command "insert" "Idust" '(70 -11) 1 1 0 )
(command "insert" "Idust" '(59 -18) 1 1 0 )
(command "insert" "Idust" '(57 -6) 1 1 0 )
(command "insert" "Idust" '(10 -9) 1 1 0 )
(command "insert" "Idust" '(58 -5) 1 1 0 )
(command "insert" "Idust" '(11 -14) 1 1 0 )
(command "insert" "Idust" '(59 -8) 1 1 0 )
(command "insert" "Idust" '(60 -17) 1 1 0 )
(command "insert" "Idust" '(14 -9) 1 1 0 )
(command "insert" "Idust" '(62 -7) 1 1 0 )
(command "insert" "Idust" '(15 -12) 1 1 0 )
(command "insert" "Idust" '(39 -3) 1 1 0 )
(command "insert" "Idust" '(63 -6) 1 1 0 )
(command "insert" "Idust" '(22 -7) 1 1 0 )
(command "insert" "Idust" '(20 -11) 1 1 0 )
(command "insert" "Idust" '(13 -12) 1 1 0 )
(command "insert" "Idust" '(48 -9) 1 1 0 )
(command "insert" "Idust" '(3 -10) 1 1 0 )
(command "insert" "Idust" '(51 -4) 1 1 0 )
(command "insert" "Idust" '(54 -19) 1 1 0 )
(command "insert" "Idust" '(52 -7) 1 1 0 )
(command "insert" "Idust" '(18 -5) 1 1 0 )
(command "insert" "Idust" '(53 -6) 1 1 0 )
(command "insert" "Idust" '(40 -5) 1 1 0 )
(command "insert" "Idust" '(67 -15) 1 1 0 )
(command "insert" "Idust" '(7 -14) 1 1 0 )
(command "insert" "Idust" '(65 -3) 1 1 0 )
(command "insert" "Idust" '(18 -9) 1 1 0 )
(command "insert" "Idust" '(68 -8) 1 1 0 )
(command "insert" "Idust" '(42 -7) 1 1 0 )
(command "insert" "Idust" '(66 -8) 1 1 0 )
(command "insert" "Idust" '(7 -13) 1 1 0 )
(command "insert" "Idust" '(69 -13) 1 1 0 )
(command "insert" "Idust" '(56 -14) 1 1 0 )
(command "insert" "Idust" '(57 -15) 1 1 0 )
(command "insert" "Idust" '(47 -4) 1 1 0 )
(command "insert" "Idust" '(71 -11) 1 1 0 )
(command "insert" "Idust" '(58 -12) 1 1 0 )
(command "insert" "Idust" '(61 -17) 1 1 0 )
(command "insert" "Idust" '(62 -14) 1 1 0 )
(command "insert" "Idust" '(36 -5) 1 1 0 )
(command "insert" "Idust" '(60 -10) 1 1 0 )
(command "insert" "Idust" '(13 -5) 1 1 0 )
(command "insert" "Idust" '(61 -11) 1 1 0 )
(command "insert" "Idust" '(24 -3) 1 1 0 )
(command "insert" "Idust" '(62 -16) 1 1 0 )
(command "insert" "Idust" '(51 -13) 1 1 0 )
(command "insert" "Idust" '(49 -13) 1 1 0 )
(command "insert" "Idust" '(52 -14) 1 1 0 )
(command "insert" "Idust" '(50 -10) 1 1 0 )
(command "insert" "Idust" '(5 -9) 1 1 0 )
(command "insert" "Idust" '(53 -15) 1 1 0 )
(command "insert" "Idust" '(6 -6) 1 1 0 )
(command "insert" "Idust" '(30 -3) 1 1 0 )
(command "insert" "Idust" '(54 -12) 1 1 0 )
(command "insert" "Idust" '(7 -7) 1 1 0 )
(command "insert" "Idust" '(65 -4) 1 1 0 )
(command "insert" "Idust" '(55 -9) 1 1 0 )
(command "insert" "Idust" '(42 -14) 1 1 0 )
(command "insert" "Idust" '(66 -3) 1 1 0 )
(command "insert" "Idust" '(31 -14) 1 1 0 )
(command "insert" "Idust" '(6 -9) 1 1 0 )
(command "insert" "Idust" '(46 -8) 1 1 0 )
(command "insert" "Idust" '(70 -5) 1 1 0 )
(command "insert" "Idust" '(44 -8) 1 1 0 )
(command "insert" "Idust" '(7 -4) 1 1 0 )
(command "insert" "Idust" '(57 -16) 1 1 0 )
(command "insert" "Idust" '(47 -13) 1 1 0 )
(command "insert" "Idust" '(45 -13) 1 1 0 )
(command "insert" "Idust" '(32 -14) 1 1 0 )
(command "insert" "Idust" '(35 -11) 1 1 0 )
(command "insert" "Idust" '(59 -6) 1 1 0 )
(command "insert" "Idust" '(36 -12) 1 1 0 )
(command "insert" "Idust" '(34 -12) 1 1 0 )
(command "insert" "Idust" '(61 -4) 1 1 0 )
(command "insert" "Idust" '(24 -10) 1 1 0 )
(command "insert" "Idust" '(48 -7) 1 1 0 )
(command "insert" "Idust" '(38 -14) 1 1 0 )
(command "insert" "Idust" '(25 -11) 1 1 0 )
(command "insert" "Idust" '(49 -6) 1 1 0 )
(command "insert" "Idust" '(17 -12) 1 1 0 )
(command "insert" "Idust" '(63 -18) 1 1 0 )
(command "insert" "Idust" '(50 -5) 1 1 0 )
(command "insert" "Idust" '(12 -8) 1 1 0 )
(command "insert" "Idust" '(53 -8) 1 1 0 )
(command "insert" "Idust" '(27 -13) 1 1 0 )
(command "insert" "Idust" '(64 -16) 1 1 0 )
(command "insert" "Idust" '(54 -7) 1 1 0 )
(command "insert" "Idust" '(28 -14) 1 1 0 )
(command "insert" "Idust" '(31 -3) 1 1 0 )
(command "insert" "Idust" '(55 -6) 1 1 0 )
(command "insert" "Idust" '(56 -4) 1 1 0 )
(command "insert" "Idust" '(42 -9) 1 1 0 )
(command "insert" "Idust" '(16 -12) 1 1 0 )
(command "insert" "Idust" '(22 -13) 1 1 0 )
(command "insert" "Idust" '(19 -9) 1 1 0 )
(command "insert" "Idust" '(43 -4) 1 1 0 )
(command "insert" "Idust" '(67 -3) 1 1 0 )
(command "insert" "Idust" '(44 -7) 1 1 0 )
(command "insert" "Idust" '(68 -4) 1 1 0 )
(command "insert" "Idust" '(47 -10) 1 1 0 )
(command "insert" "Idust" '(21 -3) 1 1 0 )
(command "insert" "Idust" '(45 -6) 1 1 0 )
(command "insert" "Idust" '(8 -8) 1 1 0 )
(command "insert" "Idust" '(32 -5) 1 1 0 )
(command "insert" "Idust" '(22 -8) 1 1 0 )
(command "insert" "Idust" '(9 -5) 1 1 0 )
(command "insert" "Idust" '(23 -13) 1 1 0 )
(command "insert" "Idust" '(30 -9) 1 1 0 )
(command "insert" "Idust" '(36 -11) 1 1 0 )
(command "insert" "Idust" '(34 -7) 1 1 0 )
(command "insert" "Idust" '(7 -8) 1 1 0 )
(command "insert" "Idust" '(37 -10) 1 1 0 )
(command "insert" "Idust" '(11 -11) 1 1 0 )
(command "insert" "Idust" '(14 -4) 1 1 0 )
(command "insert" "Idust" '(12 -12) 1 1 0 )
(command "insert" "Idust" '(25 -12) 1 1 0 )
(command "insert" "Idust" '(39 -4) 1 1 0 )
(command "insert" "Idust" '(26 -11) 1 1 0 )
(command "insert" "Idust" '(3 -7) 1 1 0 )
(command "insert" "Idust" '(30 -13) 1 1 0 )
(command "insert" "Idust" '(28 -5) 1 1 0 )
(command "insert" "Idust" '(31 -12) 1 1 0 )
(command "insert" "Idust" '(31 -8) 1 1 0 )
(command "insert" "Idust" '(5 -5) 1 1 0 )
(command "insert" "Idust" '(29 -8) 1 1 0 )
(command "insert" "Idust" '(16 -3) 1 1 0 )
(command "insert" "Idust" '(6 -10) 1 1 0 )
(command "insert" "Idust" '(64 -13) 1 1 0 )
(command "insert" "Idust" '(19 -14) 1 1 0 )
(command "insert" "Idust" '(67 -8) 1 1 0 )
(command "insert" "Idust" '(65 -8) 1 1 0 )
(command "insert" "Idust" '(20 -9) 1 1 0 )
(command "insert" "Idust" '(68 -3) 1 1 0 )
(command "insert" "Idust" '(66 -15) 1 1 0 )
(command "insert" "Idust" '(21 -12) 1 1 0 )
(command "insert" "Idust" '(9 -8) 1 1 0 )
(command "insert" "Idust" '(56 -9) 1 1 0 )
(command "insert" "Idust" '(70 -9) 1 1 0 )
(command "insert" "Idust" '(9 -14) 1 1 0 )
(command "insert" "Idust" '(7 -10) 1 1 0 )
(command "insert" "Idust" '(23 -10) 1 1 0 )
(command "insert" "Idust" '(71 -12) 1 1 0 )
(command "insert" "Idust" '(23 -8) 1 1 0 )
(command "insert" "Idust" '(10 -13) 1 1 0 )
(command "insert" "Idust" '(58 -3) 1 1 0 )
(command "insert" "Idust" '(59 -10) 1 1 0 )
(command "insert" "Idust" '(12 -11) 1 1 0 )
(command "insert" "Idust" '(60 -13) 1 1 0 )
(command "insert" "Idust" '(15 -14) 1 1 0 )
(command "insert" "Idust" '(13 -10) 1 1 0 )
(command "insert" "Idust" '(48 -11) 1 1 0 )
(command "insert" "Idust" '(3 -12) 1 1 0 )
(command "insert" "Idust" '(51 -6) 1 1 0 )
(command "insert" "Idust" '(49 -10) 1 1 0 )
(command "insert" "Idust" '(17 -14) 1 1 0 )
(command "insert" "Idust" '(54 -17) 1 1 0 )
(command "insert" "Idust" '(5 -14) 1 1 0 )
(command "insert" "Idust" '(53 -4) 1 1 0 )
(command "insert" "Idust" '(40 -7) 1 1 0 )
(command "insert" "Idust" '(64 -4) 1 1 0 )
(command "insert" "Idust" '(54 -11) 1 1 0 )
(command "insert" "Idust" '(41 -6) 1 1 0 )
(command "insert" "Idust" '(68 -10) 1 1 0 )
(command "insert" "Idust" '(42 -5) 1 1 0 )
(command "insert" "Idust" '(66 -6) 1 1 0 )
(command "insert" "Idust" '(69 -11) 1 1 0 )
(command "insert" "Idust" '(43 -8) 1 1 0 )
(command "insert" "Idust" '(56 -16) 1 1 0 )
(command "insert" "Idust" '(46 -7) 1 1 0 )
(command "insert" "Idust" '(18 -13) 1 1 0 )
(command "insert" "Idust" '(68 -16) 1 1 0 )
(command "insert" "Idust" '(57 -13) 1 1 0 )
(command "insert" "Idust" '(47 -6) 1 1 0 )
(command "insert" "Idust" '(71 -5) 1 1 0 )
(command "insert" "Idust" '(58 -10) 1 1 0 )
(command "insert" "Idust" '(32 -9) 1 1 0 )
(command "insert" "Idust" '(35 -4) 1 1 0 )
(command "insert" "Idust" '(59 -3) 1 1 0 )
(command "insert" "Idust" '(55 -20) 1 1 0 )
(command "insert" "Idust" '(36 -7) 1 1 0 )
(command "insert" "Idust" '(60 -4) 1 1 0 )
(command "insert" "Idust" '(13 -3) 1 1 0 )
(command "insert" "Idust" '(37 -6) 1 1 0 )
(command "insert" "Idust" '(61 -9) 1 1 0 )
(command "insert" "Idust" '(18 -4) 1 1 0 )
(command "insert" "Idust" '(51 -15) 1 1 0 )
(command "insert" "Idust" '(49 -3) 1 1 0 )
(command "insert" "Idust" '(52 -8) 1 1 0 )
(command "insert" "Idust" '(26 -7) 1 1 0 )
(command "insert" "Idust" '(50 -8) 1 1 0 )
(command "insert" "Idust" '(5 -11) 1 1 0 )
(command "insert" "Idust" '(53 -13) 1 1 0 )
(command "insert" "Idust" '(6 -4) 1 1 0 )
(command "insert" "Idust" '(6 -13) 1 1 0 )
(command "insert" "Idust" '(31 -4) 1 1 0 )
(command "insert" "Idust" '(55 -11) 1 1 0 )
(command "insert" "Idust" '(63 -15) 1 1 0 )
(command "insert" "Idust" '(42 -12) 1 1 0 )
(command "insert" "Idust" '(46 -14) 1 1 0 )
(command "insert" "Idust" '(20 -5) 1 1 0 )
(command "insert" "Idust" '(44 -10) 1 1 0 )
(command "insert" "Idust" '(45 -11) 1 1 0 )
(command "insert" "Idust" '(9 -10) 1 1 0 )
(command "insert" "Idust" '(8 -3) 1 1 0 )
(command "insert" "Idust" '(35 -13) 1 1 0 )
(command "insert" "Idust" '(33 -13) 1 1 0 )
(command "insert" "Idust" '(36 -14) 1 1 0 )
(command "insert" "Idust" '(60 -3) 1 1 0 )
(command "insert" "Idust" '(34 -10) 1 1 0 )
(command "insert" "Idust" '(20 -6) 1 1 0 )
(command "insert" "Idust" '(23 -5) 1 1 0 )
(command "insert" "Idust" '(14 -3) 1 1 0 )
(command "insert" "Idust" '(38 -12) 1 1 0 )
(command "insert" "Idust" '(25 -9) 1 1 0 )
(command "insert" "Idust" '(49 -4) 1 1 0 )
(command "insert" "Idust" '(39 -9) 1 1 0 )
(command "insert" "Idust" '(26 -14) 1 1 0 )
(command "insert" "Idust" '(50 -3) 1 1 0 )
(command "insert" "Idust" '(17 -3) 1 1 0 )
(command "insert" "Idust" '(64 -18) 1 1 0 )
(command "insert" "Idust" '(54 -5) 1 1 0 )
(command "insert" "Idust" '(28 -8) 1 1 0 )
(command "insert" "Idust" '(65 -19) 1 1 0 )
(command "insert" "Idust" '(29 -13) 1 1 0 )
(command "insert" "Idust" '(16 -14) 1 1 0 )
(command "insert" "Idust" '(4 -14) 1 1 0 )
(command "insert" "Idust" '(64 -8) 1 1 0 )
(command "insert" "Idust" '(55 -16) 1 1 0 )
(command "insert" "Idust" '(19 -11) 1 1 0 )
(command "insert" "Idust" '(43 -6) 1 1 0 )
(command "insert" "Idust" '(67 -5) 1 1 0 )
(command "insert" "Idust" '(4 -13) 1 1 0 )
(command "insert" "Idust" '(20 -12) 1 1 0 )
(command "insert" "Idust" '(68 -6) 1 1 0 )
(command "insert" "Idust" '(45 -4) 1 1 0 )
(command "insert" "Idust" '(69 -7) 1 1 0 )
(command "insert" "Idust" '(4 -10) 1 1 0 )
(command "insert" "Idust" '(8 -10) 1 1 0 )
(command "insert" "Idust" '(32 -7) 1 1 0 )
(command "insert" "Idust" '(22 -14) 1 1 0 )
(command "insert" "Idust" '(59 -17) 1 1 0 )
(command "insert" "Idust" '(33 -6) 1 1 0 )
(command "insert" "Idust" '(34 -5) 1 1 0 )
(command "insert" "Idust" '(58 -6) 1 1 0 )
(command "insert" "Idust" '(37 -8) 1 1 0 )
(command "insert" "Idust" '(11 -13) 1 1 0 )
(command "insert" "Idust" '(12 -10) 1 1 0 )
(command "insert" "Idust" '(14 -10) 1 1 0 )
(command "insert" "Idust" '(38 -7) 1 1 0 )
(command "insert" "Idust" '(12 -14) 1 1 0 )
(command "insert" "Idust" '(15 -3) 1 1 0 )
(command "insert" "Idust" '(39 -6) 1 1 0 )
(command "insert" "Idust" '(29 -3) 1 1 0 )
(command "insert" "Idust" '(26 -9) 1 1 0 )
(command "insert" "Idust" '(3 -9) 1 1 0 )
(command "insert" "Idust" '(27 -4) 1 1 0 )
(command "insert" "Idust" '(51 -3) 1 1 0 )
(command "insert" "Idust" '(28 -7) 1 1 0 )
(command "insert" "Idust" '(52 -4) 1 1 0 )
(command "insert" "Idust" '(65 -20) 1 1 0 )
(command "insert" "Idust" '(5 -3) 1 1 0 )
(command "insert" "Idust" '(29 -6) 1 1 0 )
(command "insert" "Idust" '(16 -5) 1 1 0 )
(command "insert" "Idust" '(6 -8) 1 1 0 )
(command "insert" "Idust" '(64 -15) 1 1 0 )
(command "insert" "Idust" '(23 -3) 1 1 0 )
(command "insert" "Idust" '(67 -10) 1 1 0 )
(command "insert" "Idust" '(41 -3) 1 1 0 )
(command "insert" "Idust" '(65 -14) 1 1 0 )
(command "insert" "Idust" '(22 -9) 1 1 0 )
(command "insert" "Idust" '(30 -10) 1 1 0 )
(command "insert" "Idust" '(68 -13) 1 1 0 )
(command "insert" "Idust" '(13 -14) 1 1 0 )
(command "insert" "Idust" '(66 -13) 1 1 0 )
(command "insert" "Idust" '(21 -10) 1 1 0 )
(command "insert" "Idust" '(7 -9) 1 1 0 )
(command "insert" "Idust" '(67 -16) 1 1 0 )
(command "insert" "Idust" '(56 -11) 1 1 0 )
(command "insert" "Idust" '(9 -12) 1 1 0 )
(command "insert" "Idust" '(23 -4) 1 1 0 )
(command "insert" "Idust" '(71 -14) 1 1 0 )
(command "insert" "Idust" '(51 -17) 1 1 0 )
(command "insert" "Idust" '(10 -11) 1 1 0 )
(command "insert" "Idust" '(17 -5) 1 1 0 )
(command "insert" "Idust" '(11 -7) 1 1 0 )
(command "insert" "Idust" '(61 -20) 1 1 0 )
(command "insert" "Idust" '(59 -12) 1 1 0 )
(command "insert" "Idust" '(14 -13) 1 1 0 )
(command "insert" "Idust" '(62 -11) 1 1 0 )
(command "insert" "Idust" '(60 -15) 1 1 0 )
(command "insert" "Idust" '(15 -8) 1 1 0 )
(command "insert" "Idust" '(13 -8) 1 1 0 )
(command "insert" "Idust" '(61 -14) 1 1 0 )
(command "insert" "Idust" '(63 -17) 1 1 0 )
(command "insert" "Idust" '(48 -13) 1 1 0 )
(command "insert" "Idust" '(3 -14) 1 1 0 )
(command "insert" "Idust" '(51 -8) 1 1 0 )
(command "insert" "Idust" '(49 -8) 1 1 0 )
(command "insert" "Idust" '(4 -9) 1 1 0 )
(command "insert" "Idust" '(52 -3) 1 1 0 )
(command "insert" "Idust" '(52 -10) 1 1 0 )
(command "insert" "Idust" '(5 -12) 1 1 0 )
(command "insert" "Idust" '(57 -4) 1 1 0 )
(command "insert" "Idust" '(6 -3) 1 1 0 )
(command "insert" "Idust" '(64 -6) 1 1 0 )
(command "insert" "Idust" '(54 -9) 1 1 0 )
(command "insert" "Idust" '(41 -4) 1 1 0 )
(command "insert" "Idust" '(65 -7) 1 1 0 )
(command "insert" "Idust" '(55 -12) 1 1 0 )
(command "insert" "Idust" '(42 -3) 1 1 0 )
(command "insert" "Idust" '(66 -4) 1 1 0 )
(command "insert" "Idust" '(69 -9) 1 1 0 )
(command "insert" "Idust" '(43 -10) 1 1 0 )
(command "insert" "Idust" '(31 -10) 1 1 0 )
(command "insert" "Idust" '(56 -18) 1 1 0 )
(command "insert" "Idust" '(46 -5) 1 1 0 )
(command "insert" "Idust" '(70 -6) 1 1 0 )
(command "insert" "Idust" '(44 -13) 1 1 0 )
(command "insert" "Idust" '(57 -19) 1 1 0 )
(command "insert" "Idust" '(71 -7) 1 1 0 )
(command "insert" "Idust" '(58 -8) 1 1 0 )
(command "insert" "Idust" '(32 -11) 1 1 0 )
(command "insert" "Idust" '(35 -6) 1 1 0 )
(command "insert" "Idust" '(59 -5) 1 1 0 )
(command "insert" "Idust" '(33 -10) 1 1 0 )
(command "insert" "Idust" '(60 -6) 1 1 0 )
(command "insert" "Idust" '(63 -11) 1 1 0 )
(command "insert" "Idust" '(37 -4) 1 1 0 )
(command "insert" "Idust" '(61 -7) 1 1 0 )
(command "insert" "Idust" '(24 -7) 1 1 0 )
(command "insert" "Idust" '(48 -4) 1 1 0 )
(command "insert" "Idust" '(38 -11) 1 1 0 )
(command "insert" "Idust" '(62 -20) 1 1 0 )
(command "insert" "Idust" '(63 -9) 1 1 0 )
(command "insert" "Idust" '(25 -6) 1 1 0 )
(command "insert" "Idust" '(17 -9) 1 1 0 )
(command "insert" "Idust" '(12 -13) 1 1 0 )
(command "insert" "Idust" '(26 -5) 1 1 0 )
(command "insert" "Idust" '(50 -6) 1 1 0 )
(command "insert" "Idust" '(53 -11) 1 1 0 )
(command "insert" "Idust" '(27 -8) 1 1 0 )
(command "insert" "Idust" '(30 -7) 1 1 0 )
(command "layer" "m" "Center" "" )
(command "insert" "Center" '(232 -57) 1 1 0 )
(command "insert" "Center" '(261 -62) 1 1 0 )
(command "insert" "Center" '(265 -59) 1 1 0 )
(command "insert" "Center" '(233 -52) 1 1 0 )
(command "insert" "Center" '(260 -69) 1 1 0 )
(command "insert" "Center" '(244 -66) 1 1 0 )
(command "insert" "Center" '(234 -51) 1 1 0 )
(command "insert" "Center" '(230 -53) 1 1 0 )
(command "insert" "Center" '(254 -54) 1 1 0 )
(command "insert" "Center" '(235 -58) 1 1 0 )
(command "insert" "Center" '(232 -72) 1 1 0 )
(command "insert" "Center" '(246 -72) 1 1 0 )
(command "insert" "Center" '(236 -61) 1 1 0 )
(command "insert" "Center" '(240 -56) 1 1 0 )
(command "insert" "Center" '(237 -64) 1 1 0 )
(command "insert" "Center" '(234 -66) 1 1 0 )
(command "insert" "Center" '(262 -61) 1 1 0 )
(command "insert" "Center" '(249 -69) 1 1 0 )
(command "insert" "Center" '(243 -59) 1 1 0 )
(command "insert" "Center" '(226 -65) 1 1 0 )
(command "insert" "Center" '(239 -65) 1 1 0 )
(command "insert" "Center" '(244 -60) 1 1 0 )
(command "insert" "Center" '(250 -75) 1 1 0 )
(command "insert" "Center" '(251 -75) 1 1 0 )
(command "insert" "Center" '(248 -55) 1 1 0 )
(command "insert" "Center" '(257 -77) 1 1 0 )
(command "insert" "Center" '(249 -54) 1 1 0 )
(command "insert" "Center" '(254 -77) 1 1 0 )
(command "insert" "Center" '(246 -62) 1 1 0 )
(command "insert" "Center" '(252 -69) 1 1 0 )
(command "insert" "Center" '(226 -48) 1 1 0 )
(command "insert" "Center" '(247 -63) 1 1 0 )
(command "insert" "Center" '(251 -56) 1 1 0 )
(command "insert" "Center" '(243 -71) 1 1 0 )
(command "insert" "Center" '(240 -67) 1 1 0 )
(command "insert" "Center" '(222 -55) 1 1 0 )
(command "insert" "Center" '(265 -60) 1 1 0 )
(command "insert" "Center" '(233 -73) 1 1 0 )
(command "insert" "Center" '(233 -61) 1 1 0 )
(command "insert" "Center" '(223 -54) 1 1 0 )
(command "insert" "Center" '(257 -70) 1 1 0 )
(command "insert" "Center" '(245 -69) 1 1 0 )
(command "insert" "Center" '(234 -58) 1 1 0 )
(command "insert" "Center" '(254 -57) 1 1 0 )
(command "insert" "Center" '(228 -52) 1 1 0 )
(command "insert" "Center" '(235 -51) 1 1 0 )
(command "insert" "Center" '(261 -72) 1 1 0 )
(command "insert" "Center" '(233 -71) 1 1 0 )
(command "insert" "Center" '(246 -67) 1 1 0 )
(command "insert" "Center" '(236 -52) 1 1 0 )
(command "insert" "Center" '(240 -63) 1 1 0 )
(command "insert" "Center" '(237 -57) 1 1 0 )
(command "insert" "Center" '(263 -70) 1 1 0 )
(command "insert" "Center" '(235 -73) 1 1 0 )
(command "insert" "Center" '(241 -62) 1 1 0 )
(command "insert" "Center" '(238 -70) 1 1 0 )
(command "insert" "Center" '(242 -61) 1 1 0 )
(command "insert" "Center" '(244 -59) 1 1 0 )
(command "insert" "Center" '(251 -64) 1 1 0 )
(command "insert" "Center" '(248 -62) 1 1 0 )
(command "insert" "Center" '(245 -58) 1 1 0 )
(command "insert" "Center" '(249 -63) 1 1 0 )
(command "insert" "Center" '(239 -52) 1 1 0 )
(command "insert" "Center" '(268 -71) 1 1 0 )
(command "insert" "Center" '(265 -67) 1 1 0 )
(command "insert" "Center" '(253 -74) 1 1 0 )
(command "insert" "Center" '(250 -60) 1 1 0 )
(command "insert" "Center" '(256 -69) 1 1 0 )
(command "insert" "Center" '(222 -62) 1 1 0 )
(command "insert" "Center" '(252 -58) 1 1 0 )
(command "insert" "Center" '(231 -72) 1 1 0 )
(command "insert" "Center" '(223 -63) 1 1 0 )
(command "insert" "Center" '(253 -59) 1 1 0 )
(command "insert" "Center" '(227 -56) 1 1 0 )
(command "insert" "Center" '(242 -64) 1 1 0 )
(command "insert" "Center" '(222 -64) 1 1 0 )
(command "insert" "Center" '(228 -51) 1 1 0 )
(command "insert" "Center" '(233 -72) 1 1 0 )
(command "insert" "Center" '(259 -65) 1 1 0 )
(command "insert" "Center" '(247 -72) 1 1 0 )
(command "insert" "Center" '(236 -51) 1 1 0 )
(command "insert" "Center" '(240 -54) 1 1 0 )
(command "insert" "Center" '(230 -57) 1 1 0 )
(command "insert" "Center" '(241 -55) 1 1 0 )
(command "insert" "Center" '(231 -60) 1 1 0 )
(command "insert" "Center" '(263 -73) 1 1 0 )
(command "insert" "Center" '(242 -52) 1 1 0 )
(command "insert" "Center" '(236 -66) 1 1 0 )
(command "insert" "Center" '(262 -63) 1 1 0 )
(command "insert" "Center" '(264 -64) 1 1 0 )
(command "insert" "Center" '(248 -69) 1 1 0 )
(command "insert" "Center" '(238 -56) 1 1 0 )
(command "insert" "Center" '(239 -61) 1 1 0 )
(command "insert" "Center" '(247 -66) 1 1 0 )
(command "insert" "Center" '(265 -68) 1 1 0 )
(command "insert" "Center" '(253 -67) 1 1 0 )
(command "insert" "Center" '(250 -71) 1 1 0 )
(command "insert" "Center" '(224 -62) 1 1 0 )
(command "insert" "Center" '(261 -60) 1 1 0 )
(command "insert" "Center" '(251 -54) 1 1 0 )
(command "insert" "Center" '(225 -63) 1 1 0 )
(command "insert" "Center" '(257 -64) 1 1 0 )
(command "insert" "Center" '(241 -69) 1 1 0 )
(command "insert" "Center" '(254 -65) 1 1 0 )
(command "insert" "Center" '(259 -57) 1 1 0 )
(command "insert" "Center" '(226 -60) 1 1 0 )
(command "insert" "Center" '(231 -65) 1 1 0 )
(command "insert" "Center" '(234 -53) 1 1 0 )
(command "insert" "Center" '(232 -52) 1 1 0 )
(command "insert" "Center" '(228 -58) 1 1 0 )
(command "insert" "Center" '(255 -64) 1 1 0 )
(command "insert" "Center" '(259 -70) 1 1 0 )
(command "insert" "Center" '(229 -59) 1 1 0 )
(command "insert" "Center" '(244 -69) 1 1 0 )
(command "insert" "Center" '(234 -54) 1 1 0 )
(command "insert" "Center" '(230 -48) 1 1 0 )
(command "insert" "Center" '(252 -66) 1 1 0 )
(command "insert" "Center" '(235 -71) 1 1 0 )
(command "insert" "Center" '(232 -67) 1 1 0 )
(command "insert" "Center" '(231 -53) 1 1 0 )
(command "insert" "Center" '(237 -69) 1 1 0 )
(command "insert" "Center" '(248 -60) 1 1 0 )
(command "insert" "Center" '(264 -71) 1 1 0 )
(command "insert" "Center" '(261 -65) 1 1 0 )
(command "insert" "Center" '(249 -66) 1 1 0 )
(command "insert" "Center" '(256 -61) 1 1 0 )
(command "insert" "Center" '(239 -58) 1 1 0 )
(command "insert" "Center" '(244 -55) 1 1 0 )
(command "insert" "Center" '(224 -53) 1 1 0 )
(command "insert" "Center" '(221 -51) 1 1 0 )
(command "insert" "Center" '(245 -54) 1 1 0 )
(command "insert" "Center" '(225 -48) 1 1 0 )
(command "insert" "Center" '(254 -72) 1 1 0 )
(command "insert" "Center" '(259 -62) 1 1 0 )
(command "insert" "Center" '(252 -72) 1 1 0 )
(command "insert" "Center" '(226 -55) 1 1 0 )
(command "insert" "Center" '(260 -57) 1 1 0 )
(command "insert" "Center" '(263 -66) 1 1 0 )
(command "insert" "Center" '(264 -60) 1 1 0 )
(command "insert" "Center" '(243 -64) 1 1 0 )
(command "insert" "Center" '(269 -73) 1 1 0 )
(command "insert" "Center" '(232 -59) 1 1 0 )
(command "insert" "Center" '(222 -50) 1 1 0 )
(command "insert" "Center" '(265 -57) 1 1 0 )
(command "insert" "Center" '(233 -58) 1 1 0 )
(command "insert" "Center" '(260 -71) 1 1 0 )
(command "insert" "Center" '(257 -67) 1 1 0 )
(command "insert" "Center" '(240 -65) 1 1 0 )
(command "insert" "Center" '(227 -61) 1 1 0 )
(command "insert" "Center" '(263 -58) 1 1 0 )
(command "insert" "Center" '(235 -60) 1 1 0 )
(command "insert" "Center" '(232 -74) 1 1 0 )
(command "insert" "Center" '(236 -63) 1 1 0 )
(command "insert" "Center" '(240 -58) 1 1 0 )
(command "insert" "Center" '(237 -62) 1 1 0 )
(command "insert" "Center" '(234 -64) 1 1 0 )
(command "insert" "Center" '(241 -59) 1 1 0 )
(command "insert" "Center" '(249 -75) 1 1 0 )
(command "insert" "Center" '(243 -61) 1 1 0 )
(command "insert" "Center" '(239 -67) 1 1 0 )
(command "insert" "Center" '(244 -62) 1 1 0 )
(command "insert" "Center" '(250 -73) 1 1 0 )
(command "insert" "Center" '(251 -77) 1 1 0 )
(command "insert" "Center" '(248 -57) 1 1 0 )
(command "insert" "Center" '(245 -63) 1 1 0 )
(command "insert" "Center" '(267 -70) 1 1 0 )
(command "insert" "Center" '(255 -67) 1 1 0 )
(command "insert" "Center" '(252 -71) 1 1 0 )
(command "insert" "Center" '(268 -72) 1 1 0 )
(command "insert" "Center" '(247 -57) 1 1 0 )
(command "insert" "Center" '(251 -58) 1 1 0 )
(command "insert" "Center" '(256 -64) 1 1 0 )
(command "insert" "Center" '(240 -69) 1 1 0 )
(command "insert" "Center" '(222 -53) 1 1 0 )
(command "insert" "Center" '(252 -61) 1 1 0 )
(command "insert" "Center" '(223 -48) 1 1 0 )
(command "insert" "Center" '(266 -57) 1 1 0 )
(command "insert" "Center" '(258 -74) 1 1 0 )
(command "insert" "Center" '(242 -71) 1 1 0 )
(command "insert" "Center" '(234 -56) 1 1 0 )
(command "insert" "Center" '(254 -63) 1 1 0 )
(command "insert" "Center" '(228 -54) 1 1 0 )
(command "insert" "Center" '(235 -53) 1 1 0 )
(command "insert" "Center" '(233 -69) 1 1 0 )
(command "insert" "Center" '(246 -65) 1 1 0 )
(command "insert" "Center" '(229 -55) 1 1 0 )
(command "insert" "Center" '(236 -54) 1 1 0 )
(command "insert" "Center" '(229 -57) 1 1 0 )
(command "insert" "Center" '(223 -65) 1 1 0 )
(command "insert" "Center" '(237 -55) 1 1 0 )
(command "insert" "Center" '(263 -64) 1 1 0 )
(command "insert" "Center" '(241 -60) 1 1 0 )
(command "insert" "Center" '(238 -68) 1 1 0 )
(command "insert" "Center" '(242 -59) 1 1 0 )
(command "insert" "Center" '(249 -76) 1 1 0 )
(command "insert" "Center" '(236 -69) 1 1 0 )
(command "insert" "Center" '(232 -62) 1 1 0 )
(command "insert" "Center" '(251 -66) 1 1 0 )
(command "insert" "Center" '(248 -64) 1 1 0 )
(command "insert" "Center" '(238 -55) 1 1 0 )
(command "insert" "Center" '(245 -56) 1 1 0 )
(command "insert" "Center" '(228 -64) 1 1 0 )
(command "insert" "Center" '(249 -61) 1 1 0 )
(command "insert" "Center" '(239 -54) 1 1 0 )
(command "insert" "Center" '(246 -55) 1 1 0 )
(command "insert" "Center" '(265 -65) 1 1 0 )
(command "insert" "Center" '(253 -72) 1 1 0 )
(command "insert" "Center" '(250 -58) 1 1 0 )
(command "insert" "Center" '(224 -57) 1 1 0 )
(command "insert" "Center" '(247 -54) 1 1 0 )
(command "insert" "Center" '(256 -71) 1 1 0 )
(command "insert" "Center" '(241 -66) 1 1 0 )
(command "insert" "Center" '(222 -60) 1 1 0 )
(command "insert" "Center" '(227 -62) 1 1 0 )
(command "insert" "Center" '(231 -74) 1 1 0 )
(command "insert" "Center" '(223 -57) 1 1 0 )
(command "insert" "Center" '(253 -57) 1 1 0 )
(command "insert" "Center" '(227 -58) 1 1 0 )
(command "insert" "Center" '(228 -61) 1 1 0 )
(command "insert" "Center" '(262 -71) 1 1 0 )
(command "insert" "Center" '(259 -67) 1 1 0 )
(command "insert" "Center" '(247 -74) 1 1 0 )
(command "insert" "Center" '(230 -63) 1 1 0 )
(command "insert" "Center" '(235 -64) 1 1 0 )
(command "insert" "Center" '(241 -53) 1 1 0 )
(command "insert" "Center" '(231 -62) 1 1 0 )
(command "insert" "Center" '(266 -59) 1 1 0 )
(command "insert" "Center" '(227 -51) 1 1 0 )
(command "insert" "Center" '(224 -65) 1 1 0 )
(command "insert" "Center" '(264 -66) 1 1 0 )
(command "insert" "Center" '(248 -71) 1 1 0 )
(command "insert" "Center" '(238 -62) 1 1 0 )
(command "insert" "Center" '(239 -63) 1 1 0 )
(command "insert" "Center" '(220 -53) 1 1 0 )
(command "insert" "Center" '(253 -65) 1 1 0 )
(command "insert" "Center" '(250 -69) 1 1 0 )
(command "insert" "Center" '(224 -48) 1 1 0 )
(command "insert" "Center" '(225 -61) 1 1 0 )
(command "insert" "Center" '(254 -71) 1 1 0 )
(command "insert" "Center" '(259 -59) 1 1 0 )
(command "insert" "Center" '(226 -58) 1 1 0 )
(command "insert" "Center" '(231 -67) 1 1 0 )
(command "insert" "Center" '(260 -60) 1 1 0 )
(command "insert" "Center" '(232 -54) 1 1 0 )
(command "insert" "Center" '(233 -55) 1 1 0 )
(command "insert" "Center" '(259 -72) 1 1 0 )
(command "insert" "Center" '(247 -67) 1 1 0 )
(command "insert" "Center" '(257 -72) 1 1 0 )
(command "insert" "Center" '(234 -52) 1 1 0 )
(command "insert" "Center" '(230 -54) 1 1 0 )
(command "insert" "Center" '(235 -57) 1 1 0 )
(command "insert" "Center" '(232 -69) 1 1 0 )
(command "insert" "Center" '(231 -55) 1 1 0 )
(command "insert" "Center" '(255 -60) 1 1 0 )
(command "insert" "Center" '(254 -66) 1 1 0 )
(command "insert" "Center" '(237 -67) 1 1 0 )
(command "insert" "Center" '(234 -71) 1 1 0 )
(command "insert" "Center" '(247 -64) 1 1 0 )
(command "insert" "Center" '(264 -73) 1 1 0 )
(command "insert" "Center" '(249 -64) 1 1 0 )
(command "insert" "Center" '(245 -67) 1 1 0 )
(command "insert" "Center" '(243 -54) 1 1 0 )
(command "insert" "Center" '(256 -62) 1 1 0 )
(command "insert" "Center" '(239 -68) 1 1 0 )
(command "insert" "Center" '(256 -76) 1 1 0 )
(command "insert" "Center" '(257 -62) 1 1 0 )
(command "insert" "Center" '(250 -76) 1 1 0 )
(command "insert" "Center" '(224 -55) 1 1 0 )
(command "insert" "Center" '(232 -66) 1 1 0 )
(command "insert" "Center" '(230 -68) 1 1 0 )
(command "insert" "Center" '(258 -61) 1 1 0 )
(command "insert" "Center" '(225 -54) 1 1 0 )
(command "insert" "Center" '(267 -69) 1 1 0 )
(command "insert" "Center" '(246 -59) 1 1 0 )
(command "insert" "Center" '(255 -65) 1 1 0 )
(command "insert" "Center" '(226 -53) 1 1 0 )
(command "insert" "Center" '(250 -54) 1 1 0 )
(command "insert" "Center" '(260 -59) 1 1 0 )
(command "insert" "Center" '(264 -62) 1 1 0 )
(command "insert" "Center" '(243 -66) 1 1 0 )
(command "insert" "Center" '(240 -64) 1 1 0 )
(command "insert" "Center" '(232 -61) 1 1 0 )
(command "insert" "Center" '(222 -48) 1 1 0 )
(command "insert" "Center" '(265 -63) 1 1 0 )
(command "insert" "Center" '(227 -60) 1 1 0 )
(command "insert" "Center" '(233 -56) 1 1 0 )
(command "insert" "Center" '(223 -53) 1 1 0 )
(command "insert" "Center" '(260 -65) 1 1 0 )
(command "insert" "Center" '(257 -65) 1 1 0 )
(command "insert" "Center" '(234 -63) 1 1 0 )
(command "insert" "Center" '(254 -58) 1 1 0 )
(command "insert" "Center" '(235 -62) 1 1 0 )
(command "insert" "Center" '(233 -66) 1 1 0 )
(command "insert" "Center" '(236 -57) 1 1 0 )
(command "insert" "Center" '(240 -60) 1 1 0 )
(command "insert" "Center" '(261 -61) 1 1 0 )
(command "insert" "Center" '(237 -60) 1 1 0 )
(command "insert" "Center" '(263 -69) 1 1 0 )
(command "insert" "Center" '(241 -57) 1 1 0 )
(command "insert" "Center" '(238 -67) 1 1 0 )
(command "insert" "Center" '(255 -72) 1 1 0 )
(command "insert" "Center" '(242 -62) 1 1 0 )
(command "insert" "Center" '(249 -73) 1 1 0 )
(command "insert" "Center" '(236 -72) 1 1 0 )
(command "insert" "Center" '(243 -63) 1 1 0 )
(command "insert" "Center" '(245 -71) 1 1 0 )
(command "insert" "Center" '(244 -56) 1 1 0 )
(command "insert" "Center" '(248 -59) 1 1 0 )
(command "insert" "Center" '(245 -61) 1 1 0 )
(command "insert" "Center" '(255 -66) 1 1 0 )
(command "insert" "Center" '(249 -58) 1 1 0 )
(command "insert" "Center" '(255 -77) 1 1 0 )
(command "insert" "Center" '(252 -65) 1 1 0 )
(command "insert" "Center" '(253 -77) 1 1 0 )
(command "insert" "Center" '(247 -59) 1 1 0 )
(command "insert" "Center" '(251 -60) 1 1 0 )
(command "insert" "Center" '(256 -66) 1 1 0 )
(command "insert" "Center" '(240 -71) 1 1 0 )
(command "insert" "Center" '(261 -69) 1 1 0 )
(command "insert" "Center" '(222 -59) 1 1 0 )
(command "insert" "Center" '(229 -62) 1 1 0 )
(command "insert" "Center" '(252 -63) 1 1 0 )
(command "insert" "Center" '(246 -58) 1 1 0 )
(command "insert" "Center" '(223 -50) 1 1 0 )
(command "insert" "Center" '(260 -72) 1 1 0 )
(command "insert" "Center" '(253 -62) 1 1 0 )
(command "insert" "Center" '(227 -55) 1 1 0 )
(command "insert" "Center" '(242 -69) 1 1 0 )
(command "insert" "Center" '(254 -61) 1 1 0 )
(command "insert" "Center" '(228 -48) 1 1 0 )
(command "insert" "Center" '(235 -55) 1 1 0 )
(command "insert" "Center" '(257 -75) 1 1 0 )
(command "insert" "Center" '(262 -66) 1 1 0 )
(command "insert" "Center" '(246 -71) 1 1 0 )
(command "insert" "Center" '(229 -53) 1 1 0 )
(command "insert" "Center" '(240 -51) 1 1 0 )
(command "insert" "Center" '(230 -58) 1 1 0 )
(command "insert" "Center" '(237 -53) 1 1 0 )
(command "insert" "Center" '(234 -73) 1 1 0 )
(command "insert" "Center" '(262 -72) 1 1 0 )
(command "insert" "Center" '(242 -57) 1 1 0 )
(command "insert" "Center" '(260 -58) 1 1 0 )
(command "insert" "Center" '(236 -71) 1 1 0 )
(command "insert" "Center" '(251 -68) 1 1 0 )
(command "insert" "Center" '(248 -66) 1 1 0 )
(command "insert" "Center" '(238 -53) 1 1 0 )
(command "insert" "Center" '(228 -66) 1 1 0 )
(command "insert" "Center" '(225 -64) 1 1 0 )
(command "insert" "Center" '(255 -74) 1 1 0 )
(command "insert" "Center" '(265 -71) 1 1 0 )
(command "insert" "Center" '(253 -70) 1 1 0 )
(command "insert" "Center" '(250 -56) 1 1 0 )
(command "insert" "Center" '(224 -59) 1 1 0 )
(command "insert" "Center" '(261 -71) 1 1 0 )
(command "insert" "Center" '(266 -68) 1 1 0 )
(command "insert" "Center" '(225 -58) 1 1 0 )
(command "insert" "Center" '(241 -64) 1 1 0 )
(command "insert" "Center" '(267 -73) 1 1 0 )
(command "insert" "Center" '(252 -54) 1 1 0 )
(command "insert" "Center" '(231 -68) 1 1 0 )
(command "insert" "Center" '(223 -59) 1 1 0 )
(command "insert" "Center" '(253 -55) 1 1 0 )
(command "insert" "Center" '(258 -67) 1 1 0 )
(command "insert" "Center" '(229 -50) 1 1 0 )
(command "insert" "Center" '(228 -63) 1 1 0 )
(command "insert" "Center" '(258 -69) 1 1 0 )
(command "insert" "Center" '(262 -69) 1 1 0 )
(command "insert" "Center" '(259 -69) 1 1 0 )
(command "insert" "Center" '(247 -68) 1 1 0 )
(command "insert" "Center" '(230 -61) 1 1 0 )
(command "insert" "Center" '(235 -66) 1 1 0 )
(command "insert" "Center" '(232 -64) 1 1 0 )
(command "insert" "Center" '(231 -56) 1 1 0 )
(command "insert" "Center" '(227 -65) 1 1 0 )
(command "insert" "Center" '(230 -65) 1 1 0 )
(command "insert" "Center" '(264 -68) 1 1 0 )
(command "insert" "Center" '(248 -73) 1 1 0 )
(command "insert" "Center" '(238 -60) 1 1 0 )
(command "insert" "Center" '(245 -55) 1 1 0 )
(command "insert" "Center" '(219 -52) 1 1 0 )
(command "insert" "Center" '(256 -58) 1 1 0 )
(command "insert" "Center" '(239 -57) 1 1 0 )
(command "insert" "Center" '(245 -64) 1 1 0 )
(command "insert" "Center" '(265 -72) 1 1 0 )
(command "insert" "Center" '(266 -70) 1 1 0 )
(command "insert" "Center" '(250 -67) 1 1 0 )
(command "insert" "Center" '(224 -50) 1 1 0 )
(command "insert" "Center" '(230 -67) 1 1 0 )
(command "insert" "Center" '(225 -51) 1 1 0 )
(command "insert" "Center" '(227 -53) 1 1 0 )
(command "insert" "Center" '(254 -69) 1 1 0 )
(command "insert" "Center" '(259 -61) 1 1 0 )
(command "insert" "Center" '(252 -77) 1 1 0 )
(command "insert" "Center" '(226 -56) 1 1 0 )
(command "insert" "Center" '(260 -62) 1 1 0 )
(command "insert" "Center" '(264 -57) 1 1 0 )
(command "insert" "Center" '(232 -56) 1 1 0 )
(command "insert" "Center" '(229 -48) 1 1 0 )
(command "insert" "Center" '(233 -53) 1 1 0 )
(command "insert" "Center" '(259 -74) 1 1 0 )
(command "insert" "Center" '(260 -68) 1 1 0 )
(command "insert" "Center" '(244 -65) 1 1 0 )
(command "insert" "Center" '(262 -58) 1 1 0 )
(command "insert" "Center" '(263 -57) 1 1 0 )
(command "insert" "Center" '(230 -52) 1 1 0 )
(command "insert" "Center" '(235 -59) 1 1 0 )
(command "insert" "Center" '(232 -71) 1 1 0 )
(command "insert" "Center" '(266 -62) 1 1 0 )
(command "insert" "Center" '(236 -60) 1 1 0 )
(command "insert" "Center" '(237 -65) 1 1 0 )
(command "insert" "Center" '(234 -69) 1 1 0 )
(command "insert" "Center" '(262 -74) 1 1 0 )
(command "insert" "Center" '(249 -70) 1 1 0 )
(command "insert" "Center" '(243 -56) 1 1 0 )
(command "insert" "Center" '(226 -64) 1 1 0 )
(command "insert" "Center" '(239 -70) 1 1 0 )
(command "insert" "Center" '(266 -65) 1 1 0 )
(command "insert" "Center" '(250 -74) 1 1 0 )
(command "insert" "Center" '(251 -72) 1 1 0 )
(command "insert" "Center" '(248 -54) 1 1 0 )
(command "insert" "Center" '(256 -74) 1 1 0 )
(command "insert" "Center" '(258 -59) 1 1 0 )
(command "insert" "Center" '(255 -62) 1 1 0 )
(command "insert" "Center" '(249 -55) 1 1 0 )
(command "insert" "Center" '(254 -76) 1 1 0 )
(command "insert" "Center" '(246 -57) 1 1 0 )
(command "insert" "Center" '(252 -68) 1 1 0 )
(command "insert" "Center" '(226 -51) 1 1 0 )
(command "insert" "Center" '(247 -60) 1 1 0 )
(command "insert" "Center" '(251 -57) 1 1 0 )
(command "insert" "Center" '(243 -68) 1 1 0 )
(command "insert" "Center" '(240 -66) 1 1 0 )
(command "insert" "Center" '(232 -63) 1 1 0 )
(command "insert" "Center" '(222 -54) 1 1 0 )
(command "insert" "Center" '(265 -61) 1 1 0 )
(command "insert" "Center" '(233 -62) 1 1 0 )
(command "insert" "Center" '(223 -55) 1 1 0 )
(command "insert" "Center" '(260 -67) 1 1 0 )
(command "insert" "Center" '(257 -71) 1 1 0 )
(command "insert" "Center" '(245 -70) 1 1 0 )
(command "insert" "Center" '(234 -61) 1 1 0 )
(command "insert" "Center" '(254 -56) 1 1 0 )
(command "insert" "Center" '(247 -65) 1 1 0 )
(command "insert" "Center" '(258 -71) 1 1 0 )
(command "insert" "Center" '(233 -64) 1 1 0 )
(command "insert" "Center" '(255 -61) 1 1 0 )
(command "insert" "Center" '(234 -65) 1 1 0 )
(command "insert" "Center" '(236 -59) 1 1 0 )
(command "insert" "Center" '(240 -62) 1 1 0 )
(command "insert" "Center" '(237 -58) 1 1 0 )
(command "insert" "Center" '(263 -71) 1 1 0 )
(command "insert" "Center" '(241 -63) 1 1 0 )
(command "insert" "Center" '(238 -65) 1 1 0 )
(command "insert" "Center" '(254 -68) 1 1 0 )
(command "insert" "Center" '(242 -60) 1 1 0 )
(command "insert" "Center" '(236 -74) 1 1 0 )
(command "insert" "Center" '(255 -70) 1 1 0 )
(command "insert" "Center" '(244 -58) 1 1 0 )
(command "insert" "Center" '(251 -65) 1 1 0 )
(command "insert" "Center" '(248 -61) 1 1 0 )
(command "insert" "Center" '(257 -76) 1 1 0 )
(command "insert" "Center" '(245 -59) 1 1 0 )
(command "insert" "Center" '(249 -56) 1 1 0 )
(command "insert" "Center" '(239 -53) 1 1 0 )
(command "insert" "Center" '(268 -70) 1 1 0 )
(command "insert" "Center" '(252 -67) 1 1 0 )
(command "insert" "Center" '(253 -75) 1 1 0 )
(command "insert" "Center" '(250 -63) 1 1 0 )
(command "insert" "Center" '(251 -62) 1 1 0 )
(command "insert" "Center" '(256 -68) 1 1 0 )
(command "insert" "Center" '(222 -57) 1 1 0 )
(command "insert" "Center" '(252 -57) 1 1 0 )
(command "insert" "Center" '(262 -65) 1 1 0 )
(command "insert" "Center" '(231 -73) 1 1 0 )
(command "insert" "Center" '(223 -60) 1 1 0 )
(command "insert" "Center" '(260 -74) 1 1 0 )
(command "insert" "Center" '(253 -60) 1 1 0 )
(command "insert" "Center" '(227 -57) 1 1 0 )
(command "insert" "Center" '(242 -67) 1 1 0 )
(command "insert" "Center" '(229 -64) 1 1 0 )
(command "insert" "Center" '(228 -50) 1 1 0 )
(command "insert" "Center" '(254 -73) 1 1 0 )
(command "insert" "Center" '(262 -64) 1 1 0 )
(command "insert" "Center" '(246 -69) 1 1 0 )
(command "insert" "Center" '(229 -51) 1 1 0 )
(command "insert" "Center" '(240 -53) 1 1 0 )
(command "insert" "Center" '(230 -56) 1 1 0 )
(command "insert" "Center" '(237 -51) 1 1 0 )
(command "insert" "Center" '(231 -61) 1 1 0 )
(command "insert" "Center" '(242 -55) 1 1 0 )
(command "insert" "Center" '(236 -65) 1 1 0 )
(command "insert" "Center" '(251 -70) 1 1 0 )
(command "insert" "Center" '(248 -68) 1 1 0 )
(command "insert" "Center" '(238 -59) 1 1 0 )
(command "insert" "Center" '(265 -69) 1 1 0 )
(command "insert" "Center" '(253 -68) 1 1 0 )
(command "insert" "Center" '(250 -70) 1 1 0 )
(command "insert" "Center" '(224 -61) 1 1 0 )
(command "insert" "Center" '(258 -70) 1 1 0 )
(command "insert" "Center" '(251 -55) 1 1 0 )
(command "insert" "Center" '(225 -56) 1 1 0 )
(command "insert" "Center" '(241 -70) 1 1 0 )
(command "insert" "Center" '(254 -64) 1 1 0 )
(command "insert" "Center" '(226 -63) 1 1 0 )
(command "insert" "Center" '(231 -70) 1 1 0 )
(command "insert" "Center" '(269 -71) 1 1 0 )
(command "insert" "Center" '(258 -65) 1 1 0 )
(command "insert" "Center" '(248 -58) 1 1 0 )
(command "insert" "Center" '(232 -51) 1 1 0 )
(command "insert" "Center" '(261 -63) 1 1 0 )
(command "insert" "Center" '(228 -57) 1 1 0 )
(command "insert" "Center" '(262 -59) 1 1 0 )
(command "insert" "Center" '(259 -71) 1 1 0 )
(command "insert" "Center" '(229 -60) 1 1 0 )
(command "insert" "Center" '(244 -68) 1 1 0 )
(command "insert" "Center" '(255 -76) 1 1 0 )
(command "insert" "Center" '(230 -51) 1 1 0 )
(command "insert" "Center" '(265 -74) 1 1 0 )
(command "insert" "Center" '(235 -68) 1 1 0 )
(command "insert" "Center" '(258 -73) 1 1 0 )
(command "insert" "Center" '(231 -58) 1 1 0 )
(command "insert" "Center" '(234 -67) 1 1 0 )
(command "insert" "Center" '(237 -70) 1 1 0 )
(command "insert" "Center" '(227 -64) 1 1 0 )
(command "insert" "Center" '(262 -60) 1 1 0 )
(command "insert" "Center" '(264 -70) 1 1 0 )
(command "insert" "Center" '(249 -67) 1 1 0 )
(command "insert" "Center" '(256 -60) 1 1 0 )
(command "insert" "Center" '(239 -59) 1 1 0 )
(command "insert" "Center" '(257 -57) 1 1 0 )
(command "insert" "Center" '(250 -65) 1 1 0 )
(command "insert" "Center" '(224 -52) 1 1 0 )
(command "insert" "Center" '(221 -52) 1 1 0 )
(command "insert" "Center" '(258 -62) 1 1 0 )
(command "insert" "Center" '(225 -49) 1 1 0 )
(command "insert" "Center" '(254 -75) 1 1 0 )
(command "insert" "Center" '(259 -63) 1 1 0 )
(command "insert" "Center" '(226 -54) 1 1 0 )
(command "insert" "Center" '(264 -59) 1 1 0 )
(command "insert" "Center" '(256 -72) 1 1 0 )
(command "insert" "Center" '(269 -74) 1 1 0 )
(command "insert" "Center" '(232 -58) 1 1 0 )
(command "insert" "Center" '(265 -58) 1 1 0 )
(command "insert" "Center" '(262 -67) 1 1 0 )
(command "insert" "Center" '(233 -59) 1 1 0 )
(command "insert" "Center" '(260 -70) 1 1 0 )
(command "insert" "Center" '(244 -67) 1 1 0 )
(command "insert" "Center" '(246 -68) 1 1 0 )
(command "insert" "Center" '(263 -59) 1 1 0 )
(command "insert" "Center" '(254 -55) 1 1 0 )
(command "insert" "Center" '(235 -61) 1 1 0 )
(command "insert" "Center" '(232 -73) 1 1 0 )
(command "insert" "Center" '(231 -51) 1 1 0 )
(command "insert" "Center" '(246 -73) 1 1 0 )
(command "insert" "Center" '(236 -62) 1 1 0 )
(command "insert" "Center" '(240 -57) 1 1 0 )
(command "insert" "Center" '(246 -60) 1 1 0 )
(command "insert" "Center" '(237 -63) 1 1 0 )
(command "insert" "Center" '(263 -72) 1 1 0 )
(command "insert" "Center" '(244 -54) 1 1 0 )
(command "insert" "Center" '(234 -55) 1 1 0 )
(command "insert" "Center" '(261 -64) 1 1 0 )
(command "insert" "Center" '(249 -68) 1 1 0 )
(command "insert" "Center" '(243 -58) 1 1 0 )
(command "insert" "Center" '(239 -64) 1 1 0 )
(command "insert" "Center" '(244 -61) 1 1 0 )
(command "insert" "Center" '(250 -72) 1 1 0 )
(command "insert" "Center" '(251 -74) 1 1 0 )
(command "insert" "Center" '(248 -56) 1 1 0 )
(command "insert" "Center" '(258 -57) 1 1 0 )
(command "insert" "Center" '(246 -63) 1 1 0 )
(command "insert" "Center" '(252 -70) 1 1 0 )
(command "insert" "Center" '(226 -49) 1 1 0 )
(command "insert" "Center" '(255 -63) 1 1 0 )
(command "insert" "Center" '(229 -68) 1 1 0 )
(command "insert" "Center" '(251 -59) 1 1 0 )
(command "insert" "Center" '(243 -70) 1 1 0 )
(command "insert" "Center" '(240 -68) 1 1 0 )
(command "insert" "Center" '(222 -52) 1 1 0 )
(command "insert" "Center" '(252 -60) 1 1 0 )
(command "insert" "Center" '(233 -60) 1 1 0 )
(command "insert" "Center" '(223 -49) 1 1 0 )
(command "insert" "Center" '(257 -69) 1 1 0 )
(command "insert" "Center" '(245 -68) 1 1 0 )
(command "insert" "Center" '(242 -70) 1 1 0 )
(command "insert" "Center" '(234 -59) 1 1 0 )
(command "insert" "Center" '(257 -68) 1 1 0 )
(command "insert" "Center" '(254 -62) 1 1 0 )
(command "insert" "Center" '(228 -53) 1 1 0 )
(command "insert" "Center" '(233 -70) 1 1 0 )
(command "insert" "Center" '(246 -64) 1 1 0 )
(command "insert" "Center" '(236 -53) 1 1 0 )
(command "insert" "Center" '(237 -56) 1 1 0 )
(command "insert" "Center" '(234 -74) 1 1 0 )
(command "insert" "Center" '(235 -72) 1 1 0 )
(command "insert" "Center" '(241 -61) 1 1 0 )
(command "insert" "Center" '(238 -71) 1 1 0 )
(command "insert" "Center" '(266 -73) 1 1 0 )
(command "insert" "Center" '(242 -58) 1 1 0 )
(command "insert" "Center" '(249 -77) 1 1 0 )
(command "insert" "Center" '(236 -68) 1 1 0 )
(command "insert" "Center" '(266 -66) 1 1 0 )
(command "insert" "Center" '(262 -62) 1 1 0 )
(command "insert" "Center" '(251 -67) 1 1 0 )
(command "insert" "Center" '(248 -63) 1 1 0 )
(command "insert" "Center" '(238 -54) 1 1 0 )
(command "insert" "Center" '(245 -57) 1 1 0 )
(command "insert" "Center" '(249 -62) 1 1 0 )
(command "insert" "Center" '(239 -55) 1 1 0 )
(command "insert" "Center" '(246 -54) 1 1 0 )
(command "insert" "Center" '(265 -66) 1 1 0 )
(command "insert" "Center" '(268 -73) 1 1 0 )
(command "insert" "Center" '(250 -61) 1 1 0 )
(command "insert" "Center" '(224 -56) 1 1 0 )
(command "insert" "Center" '(247 -55) 1 1 0 )
(command "insert" "Center" '(256 -70) 1 1 0 )
(command "insert" "Center" '(241 -67) 1 1 0 )
(command "insert" "Center" '(247 -70) 1 1 0 )
(command "insert" "Center" '(252 -59) 1 1 0 )
(command "insert" "Center" '(223 -62) 1 1 0 )
(command "insert" "Center" '(253 -58) 1 1 0 )
(command "insert" "Center" '(227 -59) 1 1 0 )
(command "insert" "Center" '(242 -65) 1 1 0 )
(command "insert" "Center" '(263 -63) 1 1 0 )
(command "insert" "Center" '(222 -65) 1 1 0 )
(command "insert" "Center" '(228 -60) 1 1 0 )
(command "insert" "Center" '(262 -70) 1 1 0 )
(command "insert" "Center" '(259 -64) 1 1 0 )
(command "insert" "Center" '(229 -49) 1 1 0 )
(command "insert" "Center" '(246 -70) 1 1 0 )
(command "insert" "Center" '(257 -73) 1 1 0 )
(command "insert" "Center" '(247 -62) 1 1 0 )
(command "insert" "Center" '(240 -55) 1 1 0 )
(command "insert" "Center" '(230 -62) 1 1 0 )
(command "insert" "Center" '(235 -65) 1 1 0 )
(command "insert" "Center" '(241 -54) 1 1 0 )
(command "insert" "Center" '(231 -63) 1 1 0 )
(command "insert" "Center" '(242 -53) 1 1 0 )
(command "insert" "Center" '(236 -67) 1 1 0 )
(command "insert" "Center" '(224 -64) 1 1 0 )
(command "insert" "Center" '(264 -65) 1 1 0 )
(command "insert" "Center" '(248 -70) 1 1 0 )
(command "insert" "Center" '(238 -57) 1 1 0 )
(command "insert" "Center" '(219 -51) 1 1 0 )
(command "insert" "Center" '(239 -60) 1 1 0 )
(command "insert" "Center" '(220 -52) 1 1 0 )
(command "insert" "Center" '(253 -66) 1 1 0 )
(command "insert" "Center" '(250 -68) 1 1 0 )
(command "insert" "Center" '(224 -63) 1 1 0 )
(command "insert" "Center" '(225 -62) 1 1 0 )
(command "insert" "Center" '(241 -68) 1 1 0 )
(command "insert" "Center" '(254 -70) 1 1 0 )
(command "insert" "Center" '(226 -61) 1 1 0 )
(command "insert" "Center" '(231 -64) 1 1 0 )
(command "insert" "Center" '(257 -60) 1 1 0 )
(command "insert" "Center" '(257 -58) 1 1 0 )
(command "insert" "Center" '(263 -67) 1 1 0 )
(command "insert" "Center" '(232 -53) 1 1 0 )
(command "insert" "Center" '(228 -59) 1 1 0 )
(command "insert" "Center" '(262 -57) 1 1 0 )
(command "insert" "Center" '(259 -73) 1 1 0 )
(command "insert" "Center" '(229 -58) 1 1 0 )
(command "insert" "Center" '(244 -70) 1 1 0 )
(command "insert" "Center" '(263 -60) 1 1 0 )
(command "insert" "Center" '(230 -49) 1 1 0 )
(command "insert" "Center" '(235 -70) 1 1 0 )
(command "insert" "Center" '(232 -68) 1 1 0 )
(command "insert" "Center" '(231 -52) 1 1 0 )
(command "insert" "Center" '(237 -68) 1 1 0 )
(command "insert" "Center" '(234 -70) 1 1 0 )
(command "insert" "Center" '(243 -65) 1 1 0 )
(command "insert" "Center" '(227 -50) 1 1 0 )
(command "insert" "Center" '(264 -72) 1 1 0 )
(command "insert" "Center" '(249 -65) 1 1 0 )
(command "insert" "Center" '(243 -55) 1 1 0 )
(command "insert" "Center" '(239 -69) 1 1 0 )
(command "insert" "Center" '(220 -51) 1 1 0 )
(command "insert" "Center" '(257 -63) 1 1 0 )
(command "insert" "Center" '(224 -54) 1 1 0 )
(command "insert" "Center" '(258 -60) 1 1 0 )
(command "insert" "Center" '(225 -55) 1 1 0 )
(command "insert" "Center" '(255 -58) 1 1 0 )
(command "insert" "Center" '(255 -69) 1 1 0 )
(command "insert" "Center" '(252 -73) 1 1 0 )
(command "insert" "Center" '(226 -52) 1 1 0 )
(command "insert" "Center" '(257 -74) 1 1 0 )
(command "insert" "Center" '(264 -61) 1 1 0 )
(command "insert" "Center" '(243 -67) 1 1 0 )
(command "insert" "Center" '(269 -72) 1 1 0 )
(command "insert" "Center" '(261 -59) 1 1 0 )
(command "insert" "Center" '(222 -51) 1 1 0 )
(command "insert" "Center" '(233 -57) 1 1 0 )
(command "insert" "Center" '(260 -64) 1 1 0 )
(command "insert" "Center" '(257 -66) 1 1 0 )
(command "insert" "Center" '(234 -62) 1 1 0 )
(command "insert" "Center" '(244 -71) 1 1 0 )
(command "insert" "Center" '(235 -63) 1 1 0 )
(command "insert" "Center" '(233 -67) 1 1 0 )
(command "insert" "Center" '(236 -56) 1 1 0 )
(command "insert" "Center" '(267 -72) 1 1 0 )
(command "insert" "Center" '(240 -59) 1 1 0 )
(command "insert" "Center" '(237 -61) 1 1 0 )
(command "insert" "Center" '(263 -74) 1 1 0 )
(command "insert" "Center" '(263 -61) 1 1 0 )
(command "insert" "Center" '(241 -58) 1 1 0 )
(command "insert" "Center" '(238 -66) 1 1 0 )
(command "insert" "Center" '(249 -74) 1 1 0 )
(command "insert" "Center" '(243 -60) 1 1 0 )
(command "insert" "Center" '(256 -63) 1 1 0 )
(command "insert" "Center" '(239 -66) 1 1 0 )
(command "insert" "Center" '(256 -77) 1 1 0 )
(command "insert" "Center" '(244 -63) 1 1 0 )
(command "insert" "Center" '(251 -76) 1 1 0 )
(command "insert" "Center" '(261 -68) 1 1 0 )
(command "insert" "Center" '(269 -69) 1 1 0 )
(command "insert" "Center" '(245 -62) 1 1 0 )
(command "insert" "Center" '(249 -59) 1 1 0 )
(command "insert" "Center" '(246 -61) 1 1 0 )
(command "insert" "Center" '(252 -64) 1 1 0 )
(command "insert" "Center" '(229 -66) 1 1 0 )
(command "insert" "Center" '(251 -61) 1 1 0 )
(command "insert" "Center" '(256 -65) 1 1 0 )
(command "insert" "Center" '(240 -70) 1 1 0 )
(command "insert" "Center" '(222 -58) 1 1 0 )
(command "insert" "Center" '(252 -62) 1 1 0 )
(command "insert" "Center" '(227 -63) 1 1 0 )
(command "insert" "Center" '(266 -67) 1 1 0 )
(command "insert" "Center" '(253 -63) 1 1 0 )
(command "insert" "Center" '(227 -52) 1 1 0 )
(command "insert" "Center" '(242 -68) 1 1 0 )
(command "insert" "Center" '(234 -57) 1 1 0 )
(command "insert" "Center" '(254 -60) 1 1 0 )
(command "insert" "Center" '(228 -55) 1 1 0 )
(command "insert" "Center" '(235 -52) 1 1 0 )
(command "insert" "Center" '(233 -68) 1 1 0 )
(command "insert" "Center" '(255 -57) 1 1 0 )
(command "insert" "Center" '(229 -54) 1 1 0 )
(command "insert" "Center" '(236 -55) 1 1 0 )
(command "insert" "Center" '(223 -64) 1 1 0 )
(command "insert" "Center" '(237 -54) 1 1 0 )
(command "insert" "Center" '(234 -72) 1 1 0 )
(command "insert" "Center" '(235 -74) 1 1 0 )
(command "insert" "Center" '(241 -51) 1 1 0 )
(command "insert" "Center" '(238 -69) 1 1 0 )
(command "insert" "Center" '(242 -56) 1 1 0 )
(command "insert" "Center" '(266 -58) 1 1 0 )
(command "insert" "Center" '(236 -70) 1 1 0 )
(command "insert" "Center" '(227 -48) 1 1 0 )
(command "insert" "Center" '(262 -68) 1 1 0 )
(command "insert" "Center" '(263 -65) 1 1 0 )
(command "insert" "Center" '(251 -69) 1 1 0 )
(command "insert" "Center" '(248 -65) 1 1 0 )
(command "insert" "Center" '(238 -52) 1 1 0 )
(command "insert" "Center" '(228 -65) 1 1 0 )
(command "insert" "Center" '(225 -65) 1 1 0 )
(command "insert" "Center" '(249 -60) 1 1 0 )
(command "insert" "Center" '(261 -66) 1 1 0 )
(command "insert" "Center" '(255 -75) 1 1 0 )
(command "insert" "Center" '(265 -64) 1 1 0 )
(command "insert" "Center" '(253 -71) 1 1 0 )
(command "insert" "Center" '(250 -59) 1 1 0 )
(command "insert" "Center" '(224 -58) 1 1 0 )
(command "insert" "Center" '(225 -59) 1 1 0 )
(command "insert" "Center" '(241 -65) 1 1 0 )
(command "insert" "Center" '(222 -61) 1 1 0 )
(command "insert" "Center" '(247 -71) 1 1 0 )
(command "insert" "Center" '(255 -68) 1 1 0 )
(command "insert" "Center" '(231 -69) 1 1 0 )
(command "insert" "Center" '(223 -56) 1 1 0 )
(command "insert" "Center" '(253 -56) 1 1 0 )
(command "insert" "Center" '(252 -74) 1 1 0 )
(command "insert" "Center" '(228 -62) 1 1 0 )
(command "insert" "Center" '(267 -71) 1 1 0 )
(command "insert" "Center" '(259 -66) 1 1 0 )
(command "insert" "Center" '(247 -69) 1 1 0 )
(command "insert" "Center" '(261 -73) 1 1 0 )
(command "insert" "Center" '(267 -74) 1 1 0 )
(command "insert" "Center" '(262 -73) 1 1 0 )
(command "insert" "Center" '(241 -52) 1 1 0 )
(command "insert" "Center" '(231 -57) 1 1 0 )
(command "insert" "Center" '(246 -66) 1 1 0 )
(command "insert" "Center" '(242 -51) 1 1 0 )
(command "insert" "Center" '(266 -63) 1 1 0 )
(command "insert" "Center" '(264 -67) 1 1 0 )
(command "insert" "Center" '(248 -72) 1 1 0 )
(command "insert" "Center" '(238 -63) 1 1 0 )
(command "insert" "Center" '(219 -53) 1 1 0 )
(command "insert" "Center" '(256 -57) 1 1 0 )
(command "insert" "Center" '(239 -62) 1 1 0 )
(command "insert" "Center" '(257 -61) 1 1 0 )
(command "insert" "Center" '(229 -67) 1 1 0 )
(command "insert" "Center" '(256 -75) 1 1 0 )
(command "insert" "Center" '(253 -64) 1 1 0 )
(command "insert" "Center" '(250 -66) 1 1 0 )
(command "insert" "Center" '(224 -49) 1 1 0 )
(command "insert" "Center" '(232 -65) 1 1 0 )
(command "insert" "Center" '(230 -66) 1 1 0 )
(command "insert" "Center" '(225 -60) 1 1 0 )
(command "insert" "Center" '(261 -58) 1 1 0 )
(command "insert" "Center" '(259 -58) 1 1 0 )
(command "insert" "Center" '(252 -76) 1 1 0 )
(command "insert" "Center" '(226 -59) 1 1 0 )
(command "insert" "Center" '(231 -66) 1 1 0 )
(command "insert" "Center" '(260 -61) 1 1 0 )
(command "insert" "Center" '(232 -55) 1 1 0 )
(command "insert" "Center" '(258 -66) 1 1 0 )
(command "insert" "Center" '(233 -54) 1 1 0 )
(command "insert" "Center" '(266 -69) 1 1 0 )
(command "insert" "Center" '(229 -56) 1 1 0 )
(command "insert" "Center" '(244 -64) 1 1 0 )
(command "insert" "Center" '(263 -62) 1 1 0 )
(command "insert" "Center" '(230 -55) 1 1 0 )
(command "insert" "Center" '(235 -56) 1 1 0 )
(command "insert" "Center" '(232 -70) 1 1 0 )
(command "insert" "Center" '(231 -54) 1 1 0 )
(command "insert" "Center" '(246 -74) 1 1 0 )
(command "insert" "Center" '(255 -71) 1 1 0 )
(command "insert" "Center" '(237 -66) 1 1 0 )
(command "insert" "Center" '(234 -68) 1 1 0 )
(command "insert" "Center" '(225 -52) 1 1 0 )
(command "insert" "Center" '(255 -73) 1 1 0 )
(command "insert" "Center" '(264 -74) 1 1 0 )
(command "insert" "Center" '(249 -71) 1 1 0 )
(command "insert" "Center" '(258 -63) 1 1 0 )
(command "insert" "Center" '(243 -57) 1 1 0 )
(command "insert" "Center" '(239 -71) 1 1 0 )
(command "insert" "Center" '(253 -73) 1 1 0 )
(command "insert" "Center" '(266 -64) 1 1 0 )
(command "insert" "Center" '(250 -77) 1 1 0 )
(command "insert" "Center" '(251 -73) 1 1 0 )
(command "insert" "Center" '(258 -58) 1 1 0 )
(command "insert" "Center" '(225 -53) 1 1 0 )
(command "insert" "Center" '(246 -56) 1 1 0 )
(command "insert" "Center" '(252 -75) 1 1 0 )
(command "insert" "Center" '(226 -50) 1 1 0 )
(command "insert" "Center" '(250 -55) 1 1 0 )
(command "insert" "Center" '(247 -61) 1 1 0 )
(command "insert" "Center" '(264 -63) 1 1 0 )
(command "insert" "Center" '(243 -69) 1 1 0 )
(command "insert" "Center" '(269 -70) 1 1 0 )
(command "insert" "Center" '(261 -57) 1 1 0 )
(command "insert" "Center" '(222 -49) 1 1 0 )
(command "insert" "Center" '(229 -63) 1 1 0 )
(command "insert" "Center" '(265 -62) 1 1 0 )
(command "insert" "Center" '(233 -63) 1 1 0 )
(command "insert" "Center" '(223 -52) 1 1 0 )
(command "insert" "Center" '(260 -66) 1 1 0 )
(command "insert" "Center" '(266 -61) 1 1 0 )
(command "insert" "Center" '(227 -49) 1 1 0 )
(command "insert" "Center" '(234 -60) 1 1 0 )
(command "insert" "Center" '(254 -59) 1 1 0 )
(command "insert" "Center" '(261 -74) 1 1 0 )
(command "insert" "Center" '(233 -65) 1 1 0 )
(command "insert" "Center" '(245 -66) 1 1 0 )
(command "insert" "Center" '(236 -58) 1 1 0 )
(command "insert" "Center" '(258 -72) 1 1 0 )
(command "insert" "Center" '(240 -61) 1 1 0 )
(command "insert" "Center" '(237 -59) 1 1 0 )
(command "insert" "Center" '(263 -68) 1 1 0 )
(command "insert" "Center" '(241 -56) 1 1 0 )
(command "insert" "Center" '(238 -64) 1 1 0 )
(command "insert" "Center" '(230 -60) 1 1 0 )
(command "insert" "Center" '(242 -63) 1 1 0 )
(command "insert" "Center" '(222 -63) 1 1 0 )
(command "insert" "Center" '(249 -72) 1 1 0 )
(command "insert" "Center" '(236 -73) 1 1 0 )
(command "insert" "Center" '(243 -62) 1 1 0 )
(command "insert" "Center" '(268 -74) 1 1 0 )
(command "insert" "Center" '(265 -73) 1 1 0 )
(command "insert" "Center" '(244 -57) 1 1 0 )
(command "insert" "Center" '(266 -72) 1 1 0 )
(command "insert" "Center" '(238 -51) 1 1 0 )
(command "insert" "Center" '(245 -60) 1 1 0 )
(command "insert" "Center" '(228 -68) 1 1 0 )
(command "insert" "Center" '(249 -57) 1 1 0 )
(command "insert" "Center" '(235 -67) 1 1 0 )
(command "insert" "Center" '(268 -69) 1 1 0 )
(command "insert" "Center" '(256 -73) 1 1 0 )
(command "insert" "Center" '(253 -76) 1 1 0 )
(command "insert" "Center" '(250 -62) 1 1 0 )
(command "insert" "Center" '(247 -58) 1 1 0 )
(command "insert" "Center" '(251 -63) 1 1 0 )
(command "insert" "Center" '(256 -67) 1 1 0 )
(command "insert" "Center" '(222 -56) 1 1 0 )
(command "insert" "Center" '(252 -56) 1 1 0 )
(command "insert" "Center" '(223 -61) 1 1 0 )
(command "insert" "Center" '(260 -73) 1 1 0 )
(command "insert" "Center" '(253 -61) 1 1 0 )
(command "insert" "Center" '(227 -54) 1 1 0 )
(command "insert" "Center" '(242 -66) 1 1 0 )
(command "insert" "Center" '(247 -73) 1 1 0 )
(command "insert" "Center" '(257 -59) 1 1 0 )
(command "insert" "Center" '(228 -49) 1 1 0 )
(command "insert" "Center" '(235 -54) 1 1 0 )
(command "insert" "Center" '(258 -68) 1 1 0 )
(command "insert" "Center" '(233 -74) 1 1 0 )
(command "insert" "Center" '(255 -59) 1 1 0 )
(command "insert" "Center" '(229 -52) 1 1 0 )
(command "insert" "Center" '(240 -52) 1 1 0 )
(command "insert" "Center" '(230 -59) 1 1 0 )
(command "insert" "Center" '(237 -52) 1 1 0 )
(command "insert" "Center" '(223 -51) 1 1 0 )
(command "insert" "Center" '(245 -65) 1 1 0 )
(command "insert" "Center" '(242 -54) 1 1 0 )
(command "insert" "Center" '(236 -64) 1 1 0 )
(command "insert" "Center" '(229 -65) 1 1 0 )
(command "insert" "Center" '(230 -64) 1 1 0 )
(command "insert" "Center" '(251 -71) 1 1 0 )
(command "insert" "Center" '(248 -67) 1 1 0 )
(command "insert" "Center" '(238 -58) 1 1 0 )
(command "insert" "Center" '(228 -67) 1 1 0 )
(command "insert" "Center" '(239 -51) 1 1 0 )
(command "insert" "Center" '(265 -70) 1 1 0 )
(command "insert" "Center" '(253 -69) 1 1 0 )
(command "insert" "Center" '(250 -57) 1 1 0 )
(command "insert" "Center" '(224 -60) 1 1 0 )
(command "insert" "Center" '(225 -57) 1 1 0 )
(command "insert" "Center" '(232 -60) 1 1 0 )
(command "insert" "Center" '(241 -71) 1 1 0 )
(command "insert" "Center" '(254 -67) 1 1 0 )
(command "insert" "Center" '(252 -55) 1 1 0 )
(command "insert" "Center" '(226 -62) 1 1 0 )
(command "insert" "Center" '(231 -71) 1 1 0 )
(command "insert" "Center" '(223 -58) 1 1 0 )
(command "insert" "Center" '(253 -54) 1 1 0 )
(command "insert" "Center" '(258 -64) 1 1 0 )
(command "insert" "Center" '(228 -56) 1 1 0 )
(command "insert" "Center" '(233 -51) 1 1 0 )
(command "insert" "Center" '(259 -68) 1 1 0 )
(command "insert" "Center" '(229 -61) 1 1 0 )
(command "insert" "Center" '(266 -60) 1 1 0 )
(command "insert" "Center" '(230 -50) 1 1 0 )
(command "insert" "Center" '(235 -69) 1 1 0 )
(command "insert" "Center" '(261 -70) 1 1 0 )
(command "insert" "Center" '(231 -59) 1 1 0 )
(command "insert" "Center" '(237 -71) 1 1 0 )
(command "insert" "Center" '(261 -67) 1 1 0 )
(command "insert" "Center" '(264 -69) 1 1 0 )
(command "insert" "Center" '(248 -74) 1 1 0 )
(command "insert" "Center" '(238 -61) 1 1 0 )
(command "insert" "Center" '(256 -59) 1 1 0 )
(command "insert" "Center" '(239 -56) 1 1 0 )
(command "insert" "Center" '(266 -71) 1 1 0 )
(command "insert" "Center" '(250 -64) 1 1 0 )
(command "insert" "Center" '(224 -51) 1 1 0 )
(command "insert" "Center" '(266 -74) 1 1 0 )
(command "insert" "Center" '(221 -53) 1 1 0 )
(command "insert" "Center" '(225 -50) 1 1 0 )
(command "insert" "Center" '(254 -74) 1 1 0 )
(command "insert" "Center" '(259 -60) 1 1 0 )
(command "insert" "Center" '(226 -57) 1 1 0 )
(command "insert" "Center" '(260 -63) 1 1 0 )
(command "insert" "Center" '(264 -58) 1 1 0 )
(command "insert" "Center" '(247 -56) 1 1 0 )
(command "layer" "m" "Idust" "" )
(command "insert" "Idust" '(152 -33) 1 1 0 )
(command "insert" "Idust" '(174 -43) 1 1 0 )
(command "insert" "Idust" '(155 -33) 1 1 0 )
(command "insert" "Idust" '(151 -40) 1 1 0 )
(command "insert" "Idust" '(168 -42) 1 1 0 )
(command "insert" "Idust" '(163 -40) 1 1 0 )
(command "insert" "Idust" '(161 -40) 1 1 0 )
(command "insert" "Idust" '(169 -43) 1 1 0 )
(command "insert" "Idust" '(164 -35) 1 1 0 )
(command "insert" "Idust" '(150 -35) 1 1 0 )
(command "insert" "Idust" '(176 -38) 1 1 0 )
(command "insert" "Idust" '(166 -41) 1 1 0 )
(command "insert" "Idust" '(176 -41) 1 1 0 )
(command "insert" "Idust" '(152 -40) 1 1 0 )
(command "insert" "Idust" '(153 -37) 1 1 0 )
(command "insert" "Idust" '(168 -44) 1 1 0 )
(command "insert" "Idust" '(155 -38) 1 1 0 )
(command "insert" "Idust" '(154 -34) 1 1 0 )
(command "insert" "Idust" '(175 -43) 1 1 0 )
(command "insert" "Idust" '(156 -33) 1 1 0 )
(command "insert" "Idust" '(160 -36) 1 1 0 )
(command "insert" "Idust" '(175 -36) 1 1 0 )
(command "insert" "Idust" '(158 -36) 1 1 0 )
(command "insert" "Idust" '(157 -36) 1 1 0 )
(command "insert" "Idust" '(161 -33) 1 1 0 )
(command "insert" "Idust" '(169 -44) 1 1 0 )
(command "insert" "Idust" '(168 -36) 1 1 0 )
(command "insert" "Idust" '(164 -42) 1 1 0 )
(command "insert" "Idust" '(163 -34) 1 1 0 )
(command "insert" "Idust" '(162 -38) 1 1 0 )
(command "insert" "Idust" '(170 -43) 1 1 0 )
(command "insert" "Idust" '(165 -43) 1 1 0 )
(command "insert" "Idust" '(164 -37) 1 1 0 )
(command "insert" "Idust" '(170 -38) 1 1 0 )
(command "insert" "Idust" '(172 -37) 1 1 0 )
(command "insert" "Idust" '(167 -37) 1 1 0 )
(command "insert" "Idust" '(173 -40) 1 1 0 )
(command "insert" "Idust" '(152 -34) 1 1 0 )
(command "insert" "Idust" '(153 -35) 1 1 0 )
(command "insert" "Idust" '(174 -40) 1 1 0 )
(command "insert" "Idust" '(150 -34) 1 1 0 )
(command "insert" "Idust" '(168 -43) 1 1 0 )
(command "insert" "Idust" '(158 -34) 1 1 0 )
(command "insert" "Idust" '(163 -43) 1 1 0 )
(command "insert" "Idust" '(162 -33) 1 1 0 )
(command "insert" "Idust" '(169 -42) 1 1 0 )
(command "insert" "Idust" '(164 -44) 1 1 0 )
(command "insert" "Idust" '(162 -44) 1 1 0 )
(command "insert" "Idust" '(171 -44) 1 1 0 )
(command "insert" "Idust" '(176 -39) 1 1 0 )
(command "insert" "Idust" '(176 -42) 1 1 0 )
(command "insert" "Idust" '(152 -41) 1 1 0 )
(command "insert" "Idust" '(153 -36) 1 1 0 )
(command "insert" "Idust" '(154 -35) 1 1 0 )
(command "insert" "Idust" '(175 -42) 1 1 0 )
(command "insert" "Idust" '(174 -38) 1 1 0 )
(command "insert" "Idust" '(156 -34) 1 1 0 )
(command "insert" "Idust" '(160 -37) 1 1 0 )
(command "insert" "Idust" '(175 -39) 1 1 0 )
(command "insert" "Idust" '(158 -37) 1 1 0 )
(command "insert" "Idust" '(157 -35) 1 1 0 )
(command "insert" "Idust" '(160 -40) 1 1 0 )
(command "insert" "Idust" '(168 -37) 1 1 0 )
(command "insert" "Idust" '(164 -43) 1 1 0 )
(command "insert" "Idust" '(163 -37) 1 1 0 )
(command "insert" "Idust" '(162 -39) 1 1 0 )
(command "insert" "Idust" '(170 -40) 1 1 0 )
(command "insert" "Idust" '(165 -42) 1 1 0 )
(command "insert" "Idust" '(164 -38) 1 1 0 )
(command "insert" "Idust" '(171 -37) 1 1 0 )
(command "insert" "Idust" '(170 -39) 1 1 0 )
(command "insert" "Idust" '(165 -39) 1 1 0 )
(command "insert" "Idust" '(172 -38) 1 1 0 )
(command "insert" "Idust" '(167 -36) 1 1 0 )
(command "insert" "Idust" '(173 -39) 1 1 0 )
(command "insert" "Idust" '(152 -35) 1 1 0 )
(command "insert" "Idust" '(153 -34) 1 1 0 )
(command "insert" "Idust" '(174 -41) 1 1 0 )
(command "insert" "Idust" '(151 -41) 1 1 0 )
(command "insert" "Idust" '(155 -35) 1 1 0 )
(command "insert" "Idust" '(175 -44) 1 1 0 )
(command "insert" "Idust" '(159 -44) 1 1 0 )
(command "insert" "Idust" '(156 -36) 1 1 0 )
(command "insert" "Idust" '(159 -41) 1 1 0 )
(command "insert" "Idust" '(158 -35) 1 1 0 )
(command "insert" "Idust" '(157 -41) 1 1 0 )
(command "insert" "Idust" '(163 -42) 1 1 0 )
(command "insert" "Idust" '(169 -41) 1 1 0 )
(command "insert" "Idust" '(172 -40) 1 1 0 )
(command "insert" "Idust" '(176 -43) 1 1 0 )
(command "insert" "Idust" '(174 -39) 1 1 0 )
(command "insert" "Idust" '(156 -35) 1 1 0 )
(command "insert" "Idust" '(167 -44) 1 1 0 )
(command "insert" "Idust" '(175 -38) 1 1 0 )
(command "insert" "Idust" '(157 -34) 1 1 0 )
(command "insert" "Idust" '(161 -39) 1 1 0 )
(command "insert" "Idust" '(160 -41) 1 1 0 )
(command "insert" "Idust" '(168 -38) 1 1 0 )
(command "insert" "Idust" '(163 -36) 1 1 0 )
(command "insert" "Idust" '(162 -36) 1 1 0 )
(command "insert" "Idust" '(170 -41) 1 1 0 )
(command "insert" "Idust" '(169 -39) 1 1 0 )
(command "insert" "Idust" '(165 -41) 1 1 0 )
(command "insert" "Idust" '(164 -39) 1 1 0 )
(command "insert" "Idust" '(171 -36) 1 1 0 )
(command "insert" "Idust" '(170 -36) 1 1 0 )
(command "insert" "Idust" '(166 -38) 1 1 0 )
(command "insert" "Idust" '(165 -38) 1 1 0 )
(command "insert" "Idust" '(172 -39) 1 1 0 )
(command "insert" "Idust" '(171 -41) 1 1 0 )
(command "insert" "Idust" '(167 -39) 1 1 0 )
(command "insert" "Idust" '(173 -38) 1 1 0 )
(command "insert" "Idust" '(160 -39) 1 1 0 )
(command "insert" "Idust" '(152 -36) 1 1 0 )
(command "insert" "Idust" '(153 -33) 1 1 0 )
(command "insert" "Idust" '(155 -34) 1 1 0 )
(command "insert" "Idust" '(154 -38) 1 1 0 )
(command "insert" "Idust" '(160 -42) 1 1 0 )
(command "insert" "Idust" '(156 -37) 1 1 0 )
(command "insert" "Idust" '(151 -37) 1 1 0 )
(command "insert" "Idust" '(159 -40) 1 1 0 )
(command "insert" "Idust" '(159 -34) 1 1 0 )
(command "insert" "Idust" '(157 -40) 1 1 0 )
(command "insert" "Idust" '(169 -40) 1 1 0 )
(command "insert" "Idust" '(159 -37) 1 1 0 )
(command "insert" "Idust" '(162 -42) 1 1 0 )
(command "insert" "Idust" '(166 -44) 1 1 0 )
(command "insert" "Idust" '(172 -41) 1 1 0 )
(command "insert" "Idust" '(167 -41) 1 1 0 )
(command "insert" "Idust" '(173 -44) 1 1 0 )
(command "insert" "Idust" '(151 -35) 1 1 0 )
(command "insert" "Idust" '(150 -41) 1 1 0 )
(command "insert" "Idust" '(154 -33) 1 1 0 )
(command "insert" "Idust" '(174 -36) 1 1 0 )
(command "insert" "Idust" '(151 -34) 1 1 0 )
(command "insert" "Idust" '(157 -33) 1 1 0 )
(command "insert" "Idust" '(161 -38) 1 1 0 )
(command "insert" "Idust" '(150 -37) 1 1 0 )
(command "insert" "Idust" '(168 -39) 1 1 0 )
(command "insert" "Idust" '(159 -35) 1 1 0 )
(command "insert" "Idust" '(163 -39) 1 1 0 )
(command "insert" "Idust" '(162 -37) 1 1 0 )
(command "insert" "Idust" '(161 -43) 1 1 0 )
(command "insert" "Idust" '(169 -38) 1 1 0 )
(command "insert" "Idust" '(165 -40) 1 1 0 )
(command "insert" "Idust" '(171 -39) 1 1 0 )
(command "insert" "Idust" '(170 -37) 1 1 0 )
(command "insert" "Idust" '(166 -39) 1 1 0 )
(command "insert" "Idust" '(165 -37) 1 1 0 )
(command "insert" "Idust" '(171 -40) 1 1 0 )
(command "insert" "Idust" '(167 -38) 1 1 0 )
(command "insert" "Idust" '(166 -42) 1 1 0 )
(command "insert" "Idust" '(173 -37) 1 1 0 )
(command "insert" "Idust" '(150 -40) 1 1 0 )
(command "insert" "Idust" '(152 -37) 1 1 0 )
(command "insert" "Idust" '(154 -40) 1 1 0 )
(command "insert" "Idust" '(155 -37) 1 1 0 )
(command "insert" "Idust" '(154 -39) 1 1 0 )
(command "insert" "Idust" '(150 -33) 1 1 0 )
(command "insert" "Idust" '(158 -39) 1 1 0 )
(command "insert" "Idust" '(156 -38) 1 1 0 )
(command "insert" "Idust" '(151 -36) 1 1 0 )
(command "insert" "Idust" '(159 -43) 1 1 0 )
(command "insert" "Idust" '(158 -33) 1 1 0 )
(command "insert" "Idust" '(157 -39) 1 1 0 )
(command "insert" "Idust" '(163 -44) 1 1 0 )
(command "insert" "Idust" '(161 -44) 1 1 0 )
(command "insert" "Idust" '(150 -36) 1 1 0 )
(command "insert" "Idust" '(159 -36) 1 1 0 )
(command "insert" "Idust" '(163 -33) 1 1 0 )
(command "insert" "Idust" '(162 -43) 1 1 0 )
(command "insert" "Idust" '(170 -44) 1 1 0 )
(command "insert" "Idust" '(172 -42) 1 1 0 )
(command "insert" "Idust" '(167 -40) 1 1 0 )
(command "insert" "Idust" '(173 -43) 1 1 0 )
(command "insert" "Idust" '(151 -33) 1 1 0 )
(command "insert" "Idust" '(153 -41) 1 1 0 )
(command "insert" "Idust" '(174 -37) 1 1 0 )
(command "insert" "Idust" '(155 -39) 1 1 0 )
(command "insert" "Idust" '(158 -40) 1 1 0 )
(command "insert" "Idust" '(156 -40) 1 1 0 )
(command "insert" "Idust" '(161 -37) 1 1 0 )
(command "insert" "Idust" '(160 -43) 1 1 0 )
(command "insert" "Idust" '(168 -40) 1 1 0 )
(command "insert" "Idust" '(163 -38) 1 1 0 )
(command "insert" "Idust" '(162 -34) 1 1 0 )
(command "insert" "Idust" '(161 -42) 1 1 0 )
(command "insert" "Idust" '(169 -37) 1 1 0 )
(command "insert" "Idust" '(159 -33) 1 1 0 )
(command "insert" "Idust" '(164 -33) 1 1 0 )
(command "insert" "Idust" '(171 -38) 1 1 0 )
(command "insert" "Idust" '(166 -36) 1 1 0 )
(command "insert" "Idust" '(165 -36) 1 1 0 )
(command "insert" "Idust" '(171 -43) 1 1 0 )
(command "insert" "Idust" '(176 -36) 1 1 0 )
(command "insert" "Idust" '(166 -43) 1 1 0 )
(command "insert" "Idust" '(173 -36) 1 1 0 )
(command "insert" "Idust" '(172 -44) 1 1 0 )
(command "insert" "Idust" '(151 -38) 1 1 0 )
(command "insert" "Idust" '(152 -38) 1 1 0 )
(command "insert" "Idust" '(154 -41) 1 1 0 )
(command "insert" "Idust" '(153 -39) 1 1 0 )
(command "insert" "Idust" '(174 -44) 1 1 0 )
(command "insert" "Idust" '(155 -36) 1 1 0 )
(command "insert" "Idust" '(154 -36) 1 1 0 )
(command "insert" "Idust" '(175 -41) 1 1 0 )
(command "insert" "Idust" '(156 -39) 1 1 0 )
(command "insert" "Idust" '(155 -41) 1 1 0 )
(command "insert" "Idust" '(160 -34) 1 1 0 )
(command "insert" "Idust" '(159 -42) 1 1 0 )
(command "insert" "Idust" '(158 -38) 1 1 0 )
(command "insert" "Idust" '(157 -38) 1 1 0 )
(command "insert" "Idust" '(161 -35) 1 1 0 )
(command "insert" "Idust" '(159 -39) 1 1 0 )
(command "insert" "Idust" '(164 -40) 1 1 0 )
(command "insert" "Idust" '(162 -40) 1 1 0 )
(command "insert" "Idust" '(150 -38) 1 1 0 )
(command "insert" "Idust" '(172 -43) 1 1 0 )
(command "insert" "Idust" '(167 -43) 1 1 0 )
(command "insert" "Idust" '(173 -42) 1 1 0 )
(command "insert" "Idust" '(151 -39) 1 1 0 )
(command "insert" "Idust" '(153 -40) 1 1 0 )
(command "insert" "Idust" '(174 -42) 1 1 0 )
(command "insert" "Idust" '(158 -41) 1 1 0 )
(command "insert" "Idust" '(156 -41) 1 1 0 )
(command "insert" "Idust" '(161 -36) 1 1 0 )
(command "insert" "Idust" '(160 -44) 1 1 0 )
(command "insert" "Idust" '(168 -41) 1 1 0 )
(command "insert" "Idust" '(163 -41) 1 1 0 )
(command "insert" "Idust" '(162 -35) 1 1 0 )
(command "insert" "Idust" '(161 -41) 1 1 0 )
(command "insert" "Idust" '(169 -36) 1 1 0 )
(command "insert" "Idust" '(164 -34) 1 1 0 )
(command "insert" "Idust" '(166 -37) 1 1 0 )
(command "insert" "Idust" '(171 -42) 1 1 0 )
(command "insert" "Idust" '(176 -37) 1 1 0 )
(command "insert" "Idust" '(166 -40) 1 1 0 )
(command "insert" "Idust" '(176 -40) 1 1 0 )
(command "insert" "Idust" '(176 -44) 1 1 0 )
(command "insert" "Idust" '(160 -33) 1 1 0 )
(command "insert" "Idust" '(152 -39) 1 1 0 )
(command "insert" "Idust" '(153 -38) 1 1 0 )
(command "insert" "Idust" '(160 -38) 1 1 0 )
(command "insert" "Idust" '(154 -37) 1 1 0 )
(command "insert" "Idust" '(175 -40) 1 1 0 )
(command "insert" "Idust" '(155 -40) 1 1 0 )
(command "insert" "Idust" '(160 -35) 1 1 0 )
(command "insert" "Idust" '(175 -37) 1 1 0 )
(command "insert" "Idust" '(150 -39) 1 1 0 )
(command "insert" "Idust" '(157 -37) 1 1 0 )
(command "insert" "Idust" '(161 -34) 1 1 0 )
(command "insert" "Idust" '(159 -38) 1 1 0 )
(command "insert" "Idust" '(164 -41) 1 1 0 )
(command "insert" "Idust" '(163 -35) 1 1 0 )
(command "insert" "Idust" '(162 -41) 1 1 0 )
(command "insert" "Idust" '(170 -42) 1 1 0 )
(command "insert" "Idust" '(165 -44) 1 1 0 )
(command "insert" "Idust" '(164 -36) 1 1 0 )
(command "insert" "Idust" '(172 -36) 1 1 0 )
(command "insert" "Idust" '(167 -42) 1 1 0 )
(command "insert" "Idust" '(173 -41) 1 1 0 )
(command "layer" "m" "ped" "" )
(command "insert" "ped" '(172 -66) 1 1 0 )
(command "insert" "ped" '(169 -64) 1 1 0 )
(command "insert" "ped" '(128 -49) 1 1 0 )
(command "insert" "ped" '(152 -46) 1 1 0 )
(command "insert" "ped" '(174 -65) 1 1 0 )
(command "insert" "ped" '(135 -50) 1 1 0 )
(command "insert" "ped" '(151 -65) 1 1 0 )
(command "insert" "ped" '(149 -49) 1 1 0 )
(command "insert" "ped" '(117 -50) 1 1 0 )
(command "insert" "ped" '(150 -62) 1 1 0 )
(command "insert" "ped" '(151 -63) 1 1 0 )
(command "insert" "ped" '(167 -65) 1 1 0 )
(command "insert" "ped" '(164 -69) 1 1 0 )
(command "insert" "ped" '(117 -45) 1 1 0 )
(command "insert" "ped" '(152 -67) 1 1 0 )
(command "insert" "ped" '(168 -61) 1 1 0 )
(command "insert" "ped" '(180 -69) 1 1 0 )
(command "insert" "ped" '(145 -45) 1 1 0 )
(command "insert" "ped" '(169 -56) 1 1 0 )
(command "insert" "ped" '(151 -57) 1 1 0 )
(command "insert" "ped" '(146 -42) 1 1 0 )
(command "insert" "ped" '(170 -63) 1 1 0 )
(command "insert" "ped" '(168 -67) 1 1 0 )
(command "insert" "ped" '(159 -66) 1 1 0 )
(command "insert" "ped" '(171 -62) 1 1 0 )
(command "insert" "ped" '(158 -67) 1 1 0 )
(command "insert" "ped" '(172 -57) 1 1 0 )
(command "insert" "ped" '(176 -60) 1 1 0 )
(command "insert" "ped" '(173 -60) 1 1 0 )
(command "insert" "ped" '(124 -49) 1 1 0 )
(command "insert" "ped" '(152 -53) 1 1 0 )
(command "insert" "ped" '(179 -63) 1 1 0 )
(command "insert" "ped" '(143 -45) 1 1 0 )
(command "insert" "ped" '(147 -38) 1 1 0 )
(command "insert" "ped" '(130 -50) 1 1 0 )
(command "insert" "ped" '(163 -64) 1 1 0 )
(command "insert" "ped" '(128 -46) 1 1 0 )
(command "insert" "ped" '(150 -49) 1 1 0 )
(command "insert" "ped" '(118 -48) 1 1 0 )
(command "insert" "ped" '(129 -47) 1 1 0 )
(command "insert" "ped" '(151 -52) 1 1 0 )
(command "insert" "ped" '(149 -36) 1 1 0 )
(command "insert" "ped" '(131 -49) 1 1 0 )
(command "insert" "ped" '(144 -39) 1 1 0 )
(command "insert" "ped" '(134 -46) 1 1 0 )
(command "insert" "ped" '(177 -70) 1 1 0 )
(command "insert" "ped" '(135 -47) 1 1 0 )
(command "insert" "ped" '(154 -64) 1 1 0 )
(command "insert" "ped" '(160 -68) 1 1 0 )
(command "insert" "ped" '(171 -55) 1 1 0 )
(command "insert" "ped" '(141 -50) 1 1 0 )
(command "insert" "ped" '(170 -64) 1 1 0 )
(command "insert" "ped" '(171 -68) 1 1 0 )
(command "insert" "ped" '(152 -60) 1 1 0 )
(command "insert" "ped" '(175 -67) 1 1 0 )
(command "insert" "ped" '(137 -48) 1 1 0 )
(command "insert" "ped" '(143 -42) 1 1 0 )
(command "insert" "ped" '(173 -70) 1 1 0 )
(command "insert" "ped" '(147 -47) 1 1 0 )
(command "insert" "ped" '(154 -62) 1 1 0 )
(command "insert" "ped" '(160 -69) 1 1 0 )
(command "insert" "ped" '(148 -40) 1 1 0 )
(command "insert" "ped" '(155 -63) 1 1 0 )
(command "insert" "ped" '(116 -47) 1 1 0 )
(command "insert" "ped" '(149 -45) 1 1 0 )
(command "insert" "ped" '(119 -50) 1 1 0 )
(command "insert" "ped" '(165 -67) 1 1 0 )
(command "insert" "ped" '(162 -71) 1 1 0 )
(command "insert" "ped" '(136 -46) 1 1 0 )
(command "insert" "ped" '(176 -69) 1 1 0 )
(command "insert" "ped" '(118 -45) 1 1 0 )
(command "insert" "ped" '(137 -47) 1 1 0 )
(command "insert" "ped" '(166 -65) 1 1 0 )
(command "insert" "ped" '(132 -49) 1 1 0 )
(command "insert" "ped" '(165 -68) 1 1 0 )
(command "insert" "ped" '(123 -45) 1 1 0 )
(command "insert" "ped" '(178 -71) 1 1 0 )
(command "insert" "ped" '(125 -46) 1 1 0 )
(command "insert" "ped" '(162 -70) 1 1 0 )
(command "insert" "ped" '(163 -60) 1 1 0 )
(command "insert" "ped" '(137 -49) 1 1 0 )
(command "insert" "ped" '(140 -42) 1 1 0 )
(command "insert" "ped" '(164 -63) 1 1 0 )
(command "insert" "ped" '(125 -47) 1 1 0 )
(command "insert" "ped" '(145 -49) 1 1 0 )
(command "insert" "ped" '(141 -43) 1 1 0 )
(command "insert" "ped" '(165 -62) 1 1 0 )
(command "insert" "ped" '(109 -44) 1 1 0 )
(command "insert" "ped" '(166 -61) 1 1 0 )
(command "insert" "ped" '(112 -45) 1 1 0 )
(command "insert" "ped" '(114 -46) 1 1 0 )
(command "insert" "ped" '(172 -69) 1 1 0 )
(command "insert" "ped" '(159 -64) 1 1 0 )
(command "insert" "ped" '(161 -66) 1 1 0 )
(command "insert" "ped" '(174 -60) 1 1 0 )
(command "insert" "ped" '(175 -57) 1 1 0 )
(command "insert" "ped" '(120 -49) 1 1 0 )
(command "insert" "ped" '(126 -45) 1 1 0 )
(command "insert" "ped" '(155 -64) 1 1 0 )
(command "insert" "ped" '(144 -43) 1 1 0 )
(command "insert" "ped" '(134 -50) 1 1 0 )
(command "insert" "ped" '(179 -70) 1 1 0 )
(command "insert" "ped" '(145 -42) 1 1 0 )
(command "insert" "ped" '(146 -49) 1 1 0 )
(command "insert" "ped" '(171 -59) 1 1 0 )
(command "insert" "ped" '(172 -60) 1 1 0 )
(command "insert" "ped" '(169 -70) 1 1 0 )
(command "insert" "ped" '(152 -48) 1 1 0 )
(command "insert" "ped" '(174 -71) 1 1 0 )
(command "insert" "ped" '(129 -50) 1 1 0 )
(command "insert" "ped" '(124 -45) 1 1 0 )
(command "insert" "ped" '(110 -47) 1 1 0 )
(command "insert" "ped" '(117 -48) 1 1 0 )
(command "insert" "ped" '(150 -60) 1 1 0 )
(command "insert" "ped" '(111 -46) 1 1 0 )
(command "insert" "ped" '(148 -36) 1 1 0 )
(command "insert" "ped" '(122 -50) 1 1 0 )
(command "insert" "ped" '(167 -67) 1 1 0 )
(command "insert" "ped" '(164 -71) 1 1 0 )
(command "insert" "ped" '(168 -63) 1 1 0 )
(command "insert" "ped" '(180 -71) 1 1 0 )
(command "insert" "ped" '(177 -67) 1 1 0 )
(command "insert" "ped" '(135 -48) 1 1 0 )
(command "insert" "ped" '(157 -67) 1 1 0 )
(command "insert" "ped" '(146 -40) 1 1 0 )
(command "insert" "ped" '(170 -61) 1 1 0 )
(command "insert" "ped" '(168 -69) 1 1 0 )
(command "insert" "ped" '(158 -65) 1 1 0 )
(command "insert" "ped" '(172 -59) 1 1 0 )
(command "insert" "ped" '(170 -71) 1 1 0 )
(command "insert" "ped" '(176 -62) 1 1 0 )
(command "insert" "ped" '(173 -58) 1 1 0 )
(command "insert" "ped" '(159 -70) 1 1 0 )
(command "insert" "ped" '(176 -66) 1 1 0 )
(command "insert" "ped" '(150 -68) 1 1 0 )
(command "insert" "ped" '(171 -65) 1 1 0 )
(command "insert" "ped" '(152 -55) 1 1 0 )
(command "insert" "ped" '(142 -46) 1 1 0 )
(command "insert" "ped" '(175 -68) 1 1 0 )
(command "insert" "ped" '(143 -47) 1 1 0 )
(command "insert" "ped" '(147 -40) 1 1 0 )
(command "insert" "ped" '(130 -48) 1 1 0 )
(command "insert" "ped" '(163 -66) 1 1 0 )
(command "insert" "ped" '(160 -64) 1 1 0 )
(command "insert" "ped" '(150 -55) 1 1 0 )
(command "insert" "ped" '(131 -45) 1 1 0 )
(command "insert" "ped" '(129 -45) 1 1 0 )
(command "insert" "ped" '(151 -54) 1 1 0 )
(command "insert" "ped" '(132 -46) 1 1 0 )
(command "insert" "ped" '(123 -48) 1 1 0 )
(command "insert" "ped" '(133 -47) 1 1 0 )
(command "insert" "ped" '(153 -66) 1 1 0 )
(command "insert" "ped" '(119 -45) 1 1 0 )
(command "insert" "ped" '(177 -68) 1 1 0 )
(command "insert" "ped" '(139 -42) 1 1 0 )
(command "insert" "ped" '(140 -45) 1 1 0 )
(command "insert" "ped" '(108 -44) 1 1 0 )
(command "insert" "ped" '(141 -48) 1 1 0 )
(command "insert" "ped" '(167 -61) 1 1 0 )
(command "insert" "ped" '(168 -59) 1 1 0 )
(command "insert" "ped" '(171 -70) 1 1 0 )
(command "insert" "ped" '(152 -62) 1 1 0 )
(command "insert" "ped" '(142 -49) 1 1 0 )
(command "insert" "ped" '(153 -63) 1 1 0 )
(command "insert" "ped" '(173 -68) 1 1 0 )
(command "insert" "ped" '(147 -49) 1 1 0 )
(command "insert" "ped" '(154 -60) 1 1 0 )
(command "insert" "ped" '(115 -46) 1 1 0 )
(command "insert" "ped" '(174 -59) 1 1 0 )
(command "insert" "ped" '(148 -42) 1 1 0 )
(command "insert" "ped" '(149 -43) 1 1 0 )
(command "insert" "ped" '(165 -65) 1 1 0 )
(command "insert" "ped" '(162 -69) 1 1 0 )
(command "insert" "ped" '(176 -71) 1 1 0 )
(command "insert" "ped" '(137 -45) 1 1 0 )
(command "insert" "ped" '(122 -46) 1 1 0 )
(command "insert" "ped" '(166 -71) 1 1 0 )
(command "insert" "ped" '(138 -42) 1 1 0 )
(command "insert" "ped" '(162 -63) 1 1 0 )
(command "insert" "ped" '(123 -47) 1 1 0 )
(command "insert" "ped" '(178 -69) 1 1 0 )
(command "insert" "ped" '(133 -50) 1 1 0 )
(command "insert" "ped" '(163 -62) 1 1 0 )
(command "insert" "ped" '(127 -45) 1 1 0 )
(command "insert" "ped" '(182 -71) 1 1 0 )
(command "insert" "ped" '(125 -45) 1 1 0 )
(command "insert" "ped" '(108 -43) 1 1 0 )
(command "insert" "ped" '(159 -67) 1 1 0 )
(command "insert" "ped" '(165 -60) 1 1 0 )
(command "insert" "ped" '(126 -50) 1 1 0 )
(command "insert" "ped" '(109 -42) 1 1 0 )
(command "insert" "ped" '(113 -47) 1 1 0 )
(command "insert" "ped" '(172 -71) 1 1 0 )
(command "insert" "ped" '(169 -67) 1 1 0 )
(command "insert" "ped" '(159 -68) 1 1 0 )
(command "insert" "ped" '(176 -64) 1 1 0 )
(command "insert" "ped" '(161 -64) 1 1 0 )
(command "insert" "ped" '(174 -66) 1 1 0 )
(command "insert" "ped" '(148 -49) 1 1 0 )
(command "insert" "ped" '(151 -68) 1 1 0 )
(command "insert" "ped" '(175 -59) 1 1 0 )
(command "insert" "ped" '(110 -42) 1 1 0 )
(command "insert" "ped" '(121 -50) 1 1 0 )
(command "insert" "ped" '(167 -68) 1 1 0 )
(command "insert" "ped" '(155 -66) 1 1 0 )
(command "insert" "ped" '(152 -64) 1 1 0 )
(command "insert" "ped" '(144 -45) 1 1 0 )
(command "insert" "ped" '(134 -48) 1 1 0 )
(command "insert" "ped" '(145 -40) 1 1 0 )
(command "insert" "ped" '(169 -59) 1 1 0 )
(command "insert" "ped" '(146 -47) 1 1 0 )
(command "insert" "ped" '(168 -64) 1 1 0 )
(command "insert" "ped" '(127 -48) 1 1 0 )
(command "insert" "ped" '(171 -61) 1 1 0 )
(command "insert" "ped" '(172 -62) 1 1 0 )
(command "insert" "ped" '(169 -68) 1 1 0 )
(command "insert" "ped" '(176 -57) 1 1 0 )
(command "insert" "ped" '(173 -63) 1 1 0 )
(command "insert" "ped" '(150 -67) 1 1 0 )
(command "insert" "ped" '(152 -50) 1 1 0 )
(command "insert" "ped" '(174 -69) 1 1 0 )
(command "insert" "ped" '(129 -48) 1 1 0 )
(command "insert" "ped" '(110 -45) 1 1 0 )
(command "insert" "ped" '(147 -37) 1 1 0 )
(command "insert" "ped" '(150 -50) 1 1 0 )
(command "insert" "ped" '(148 -38) 1 1 0 )
(command "insert" "ped" '(122 -48) 1 1 0 )
(command "insert" "ped" '(149 -39) 1 1 0 )
(command "insert" "ped" '(164 -65) 1 1 0 )
(command "insert" "ped" '(177 -65) 1 1 0 )
(command "insert" "ped" '(169 -60) 1 1 0 )
(command "insert" "ped" '(157 -65) 1 1 0 )
(command "insert" "ped" '(170 -59) 1 1 0 )
(command "insert" "ped" '(168 -71) 1 1 0 )
(command "insert" "ped" '(140 -48) 1 1 0 )
(command "insert" "ped" '(170 -69) 1 1 0 )
(command "insert" "ped" '(173 -56) 1 1 0 )
(command "insert" "ped" '(171 -67) 1 1 0 )
(command "insert" "ped" '(152 -57) 1 1 0 )
(command "insert" "ped" '(142 -44) 1 1 0 )
(command "insert" "ped" '(175 -70) 1 1 0 )
(command "insert" "ped" '(147 -42) 1 1 0 )
(command "insert" "ped" '(163 -68) 1 1 0 )
(command "insert" "ped" '(160 -66) 1 1 0 )
(command "insert" "ped" '(150 -53) 1 1 0 )
(command "insert" "ped" '(148 -45) 1 1 0 )
(command "insert" "ped" '(131 -47) 1 1 0 )
(command "insert" "ped" '(151 -48) 1 1 0 )
(command "insert" "ped" '(119 -49) 1 1 0 )
(command "insert" "ped" '(165 -70) 1 1 0 )
(command "insert" "ped" '(123 -50) 1 1 0 )
(command "insert" "ped" '(150 -47) 1 1 0 )
(command "insert" "ped" '(133 -45) 1 1 0 )
(command "insert" "ped" '(118 -46) 1 1 0 )
(command "insert" "ped" '(151 -46) 1 1 0 )
(command "insert" "ped" '(166 -66) 1 1 0 )
(command "insert" "ped" '(158 -63) 1 1 0 )
(command "insert" "ped" '(119 -47) 1 1 0 )
(command "insert" "ped" '(136 -49) 1 1 0 )
(command "insert" "ped" '(139 -44) 1 1 0 )
(command "insert" "ped" '(144 -49) 1 1 0 )
(command "insert" "ped" '(140 -47) 1 1 0 )
(command "insert" "ped" '(164 -60) 1 1 0 )
(command "insert" "ped" '(108 -46) 1 1 0 )
(command "insert" "ped" '(141 -46) 1 1 0 )
(command "insert" "ped" '(109 -47) 1 1 0 )
(command "insert" "ped" '(166 -62) 1 1 0 )
(command "insert" "ped" '(167 -63) 1 1 0 )
(command "insert" "ped" '(150 -57) 1 1 0 )
(command "insert" "ped" '(153 -61) 1 1 0 )
(command "insert" "ped" '(173 -66) 1 1 0 )
(command "insert" "ped" '(120 -46) 1 1 0 )
(command "insert" "ped" '(174 -57) 1 1 0 )
(command "insert" "ped" '(175 -60) 1 1 0 )
(command "insert" "ped" '(149 -41) 1 1 0 )
(command "insert" "ped" '(162 -67) 1 1 0 )
(command "insert" "ped" '(160 -63) 1 1 0 )
(command "insert" "ped" '(121 -47) 1 1 0 )
(command "insert" "ped" '(124 -50) 1 1 0 )
(command "insert" "ped" '(166 -69) 1 1 0 )
(command "insert" "ped" '(125 -49) 1 1 0 )
(command "insert" "ped" '(162 -61) 1 1 0 )
(command "insert" "ped" '(178 -67) 1 1 0 )
(command "insert" "ped" '(151 -58) 1 1 0 )
(command "insert" "ped" '(133 -48) 1 1 0 )
(command "insert" "ped" '(126 -46) 1 1 0 )
(command "insert" "ped" '(144 -40) 1 1 0 )
(command "insert" "ped" '(127 -47) 1 1 0 )
(command "insert" "ped" '(182 -69) 1 1 0 )
(command "insert" "ped" '(138 -50) 1 1 0 )
(command "insert" "ped" '(156 -65) 1 1 0 )
(command "insert" "ped" '(126 -48) 1 1 0 )
(command "insert" "ped" '(146 -50) 1 1 0 )
(command "insert" "ped" '(170 -55) 1 1 0 )
(command "insert" "ped" '(113 -45) 1 1 0 )
(command "insert" "ped" '(181 -71) 1 1 0 )
(command "insert" "ped" '(172 -65) 1 1 0 )
(command "insert" "ped" '(169 -65) 1 1 0 )
(command "insert" "ped" '(169 -62) 1 1 0 )
(command "insert" "ped" '(128 -48) 1 1 0 )
(command "insert" "ped" '(161 -70) 1 1 0 )
(command "insert" "ped" '(174 -64) 1 1 0 )
(command "insert" "ped" '(149 -50) 1 1 0 )
(command "insert" "ped" '(121 -48) 1 1 0 )
(command "insert" "ped" '(111 -45) 1 1 0 )
(command "insert" "ped" '(151 -60) 1 1 0 )
(command "insert" "ped" '(167 -70) 1 1 0 )
(command "insert" "ped" '(164 -68) 1 1 0 )
(command "insert" "ped" '(160 -70) 1 1 0 )
(command "insert" "ped" '(155 -68) 1 1 0 )
(command "insert" "ped" '(152 -66) 1 1 0 )
(command "insert" "ped" '(144 -47) 1 1 0 )
(command "insert" "ped" '(168 -60) 1 1 0 )
(command "insert" "ped" '(145 -46) 1 1 0 )
(command "insert" "ped" '(169 -57) 1 1 0 )
(command "insert" "ped" '(139 -48) 1 1 0 )
(command "insert" "ped" '(146 -45) 1 1 0 )
(command "insert" "ped" '(170 -62) 1 1 0 )
(command "insert" "ped" '(168 -66) 1 1 0 )
(command "insert" "ped" '(127 -50) 1 1 0 )
(command "insert" "ped" '(171 -63) 1 1 0 )
(command "insert" "ped" '(158 -66) 1 1 0 )
(command "insert" "ped" '(172 -56) 1 1 0 )
(command "insert" "ped" '(176 -59) 1 1 0 )
(command "insert" "ped" '(173 -61) 1 1 0 )
(command "insert" "ped" '(150 -65) 1 1 0 )
(command "insert" "ped" '(152 -52) 1 1 0 )
(command "insert" "ped" '(142 -43) 1 1 0 )
(command "insert" "ped" '(147 -39) 1 1 0 )
(command "insert" "ped" '(163 -65) 1 1 0 )
(command "insert" "ped" '(128 -45) 1 1 0 )
(command "insert" "ped" '(150 -48) 1 1 0 )
(command "insert" "ped" '(151 -53) 1 1 0 )
(command "insert" "ped" '(149 -37) 1 1 0 )
(command "insert" "ped" '(164 -67) 1 1 0 )
(command "insert" "ped" '(130 -47) 1 1 0 )
(command "insert" "ped" '(179 -69) 1 1 0 )
(command "insert" "ped" '(145 -39) 1 1 0 )
(command "insert" "ped" '(154 -67) 1 1 0 )
(command "insert" "ped" '(170 -57) 1 1 0 )
(command "insert" "ped" '(140 -50) 1 1 0 )
(command "insert" "ped" '(153 -64) 1 1 0 )
(command "insert" "ped" '(172 -55) 1 1 0 )
(command "insert" "ped" '(170 -67) 1 1 0 )
(command "insert" "ped" '(173 -54) 1 1 0 )
(command "insert" "ped" '(171 -69) 1 1 0 )
(command "insert" "ped" '(152 -59) 1 1 0 )
(command "insert" "ped" '(142 -50) 1 1 0 )
(command "insert" "ped" '(175 -64) 1 1 0 )
(command "insert" "ped" '(143 -43) 1 1 0 )
(command "insert" "ped" '(173 -71) 1 1 0 )
(command "insert" "ped" '(147 -44) 1 1 0 )
(command "insert" "ped" '(161 -68) 1 1 0 )
(command "insert" "ped" '(163 -70) 1 1 0 )
(command "insert" "ped" '(115 -45) 1 1 0 )
(command "insert" "ped" '(148 -47) 1 1 0 )
(command "insert" "ped" '(155 -60) 1 1 0 )
(command "insert" "ped" '(116 -46) 1 1 0 )
(command "insert" "ped" '(151 -50) 1 1 0 )
(command "insert" "ped" '(149 -46) 1 1 0 )
(command "insert" "ped" '(156 -63) 1 1 0 )
(command "insert" "ped" '(117 -47) 1 1 0 )
(command "insert" "ped" '(136 -45) 1 1 0 )
(command "insert" "ped" '(150 -45) 1 1 0 )
(command "insert" "ped" '(176 -68) 1 1 0 )
(command "insert" "ped" '(166 -64) 1 1 0 )
(command "insert" "ped" '(132 -48) 1 1 0 )
(command "insert" "ped" '(138 -47) 1 1 0 )
(command "insert" "ped" '(178 -70) 1 1 0 )
(command "insert" "ped" '(139 -46) 1 1 0 )
(command "insert" "ped" '(163 -61) 1 1 0 )
(command "insert" "ped" '(137 -50) 1 1 0 )
(command "insert" "ped" '(152 -45) 1 1 0 )
(command "insert" "ped" '(164 -62) 1 1 0 )
(command "insert" "ped" '(145 -50) 1 1 0 )
(command "insert" "ped" '(141 -44) 1 1 0 )
(command "insert" "ped" '(156 -68) 1 1 0 )
(command "insert" "ped" '(109 -45) 1 1 0 )
(command "insert" "ped" '(166 -60) 1 1 0 )
(command "insert" "ped" '(172 -68) 1 1 0 )
(command "insert" "ped" '(143 -48) 1 1 0 )
(command "insert" "ped" '(173 -64) 1 1 0 )
(command "insert" "ped" '(161 -67) 1 1 0 )
(command "insert" "ped" '(174 -63) 1 1 0 )
(command "insert" "ped" '(175 -62) 1 1 0 )
(command "insert" "ped" '(120 -48) 1 1 0 )
(command "insert" "ped" '(162 -65) 1 1 0 )
(command "insert" "ped" '(121 -45) 1 1 0 )
(command "insert" "ped" '(178 -65) 1 1 0 )
(command "insert" "ped" '(179 -67) 1 1 0 )
(command "insert" "ped" '(117 -46) 1 1 0 )
(command "insert" "ped" '(155 -65) 1 1 0 )
(command "insert" "ped" '(144 -42) 1 1 0 )
(command "insert" "ped" '(168 -55) 1 1 0 )
(command "insert" "ped" '(138 -48) 1 1 0 )
(command "insert" "ped" '(145 -43) 1 1 0 )
(command "insert" "ped" '(169 -54) 1 1 0 )
(command "insert" "ped" '(156 -67) 1 1 0 )
(command "insert" "ped" '(146 -48) 1 1 0 )
(command "insert" "ped" '(181 -69) 1 1 0 )
(command "insert" "ped" '(112 -46) 1 1 0 )
(command "insert" "ped" '(171 -56) 1 1 0 )
(command "insert" "ped" '(172 -67) 1 1 0 )
(command "insert" "ped" '(169 -71) 1 1 0 )
(command "insert" "ped" '(124 -48) 1 1 0 )
(command "insert" "ped" '(128 -50) 1 1 0 )
(command "insert" "ped" '(152 -47) 1 1 0 )
(command "insert" "ped" '(174 -70) 1 1 0 )
(command "insert" "ped" '(151 -64) 1 1 0 )
(command "insert" "ped" '(149 -48) 1 1 0 )
(command "insert" "ped" '(110 -46) 1 1 0 )
(command "insert" "ped" '(117 -49) 1 1 0 )
(command "insert" "ped" '(150 -63) 1 1 0 )
(command "insert" "ped" '(111 -47) 1 1 0 )
(command "insert" "ped" '(151 -62) 1 1 0 )
(command "insert" "ped" '(167 -64) 1 1 0 )
(command "insert" "ped" '(164 -70) 1 1 0 )
(command "insert" "ped" '(138 -44) 1 1 0 )
(command "insert" "ped" '(168 -62) 1 1 0 )
(command "insert" "ped" '(121 -49) 1 1 0 )
(command "insert" "ped" '(180 -70) 1 1 0 )
(command "insert" "ped" '(145 -44) 1 1 0 )
(command "insert" "ped" '(135 -49) 1 1 0 )
(command "insert" "ped" '(139 -50) 1 1 0 )
(command "insert" "ped" '(152 -68) 1 1 0 )
(command "insert" "ped" '(146 -43) 1 1 0 )
(command "insert" "ped" '(170 -60) 1 1 0 )
(command "insert" "ped" '(168 -68) 1 1 0 )
(command "insert" "ped" '(158 -64) 1 1 0 )
(command "insert" "ped" '(172 -58) 1 1 0 )
(command "insert" "ped" '(170 -70) 1 1 0 )
(command "insert" "ped" '(176 -61) 1 1 0 )
(command "insert" "ped" '(173 -59) 1 1 0 )
(command "insert" "ped" '(178 -63) 1 1 0 )
(command "insert" "ped" '(152 -54) 1 1 0 )
(command "insert" "ped" '(175 -69) 1 1 0 )
(command "insert" "ped" '(124 -46) 1 1 0 )
(command "insert" "ped" '(143 -44) 1 1 0 )
(command "insert" "ped" '(147 -41) 1 1 0 )
(command "insert" "ped" '(163 -67) 1 1 0 )
(command "insert" "ped" '(128 -47) 1 1 0 )
(command "insert" "ped" '(150 -54) 1 1 0 )
(command "insert" "ped" '(118 -49) 1 1 0 )
(command "insert" "ped" '(169 -63) 1 1 0 )
(command "insert" "ped" '(129 -46) 1 1 0 )
(command "insert" "ped" '(151 -55) 1 1 0 )
(command "insert" "ped" '(132 -45) 1 1 0 )
(command "insert" "ped" '(130 -45) 1 1 0 )
(command "insert" "ped" '(123 -49) 1 1 0 )
(command "insert" "ped" '(131 -48) 1 1 0 )
(command "insert" "ped" '(151 -45) 1 1 0 )
(command "insert" "ped" '(134 -47) 1 1 0 )
(command "insert" "ped" '(157 -68) 1 1 0 )
(command "insert" "ped" '(177 -69) 1 1 0 )
(command "insert" "ped" '(135 -46) 1 1 0 )
(command "insert" "ped" '(179 -65) 1 1 0 )
(command "insert" "ped" '(139 -43) 1 1 0 )
(command "insert" "ped" '(154 -65) 1 1 0 )
(command "insert" "ped" '(140 -44) 1 1 0 )
(command "insert" "ped" '(171 -54) 1 1 0 )
(command "insert" "ped" '(141 -49) 1 1 0 )
(command "insert" "ped" '(170 -65) 1 1 0 )
(command "insert" "ped" '(159 -65) 1 1 0 )
(command "insert" "ped" '(171 -71) 1 1 0 )
(command "insert" "ped" '(165 -63) 1 1 0 )
(command "insert" "ped" '(152 -61) 1 1 0 )
(command "insert" "ped" '(142 -48) 1 1 0 )
(command "insert" "ped" '(175 -66) 1 1 0 )
(command "insert" "ped" '(173 -69) 1 1 0 )
(command "insert" "ped" '(147 -46) 1 1 0 )
(command "insert" "ped" '(154 -63) 1 1 0 )
(command "insert" "ped" '(115 -47) 1 1 0 )
(command "insert" "ped" '(174 -58) 1 1 0 )
(command "insert" "ped" '(148 -41) 1 1 0 )
(command "insert" "ped" '(155 -62) 1 1 0 )
(command "insert" "ped" '(149 -44) 1 1 0 )
(command "insert" "ped" '(165 -66) 1 1 0 )
(command "insert" "ped" '(162 -68) 1 1 0 )
(command "insert" "ped" '(136 -47) 1 1 0 )
(command "insert" "ped" '(176 -70) 1 1 0 )
(command "insert" "ped" '(137 -46) 1 1 0 )
(command "insert" "ped" '(153 -68) 1 1 0 )
(command "insert" "ped" '(166 -70) 1 1 0 )
(command "insert" "ped" '(132 -50) 1 1 0 )
(command "insert" "ped" '(138 -45) 1 1 0 )
(command "insert" "ped" '(162 -62) 1 1 0 )
(command "insert" "ped" '(178 -68) 1 1 0 )
(command "insert" "ped" '(163 -63) 1 1 0 )
(command "insert" "ped" '(124 -47) 1 1 0 )
(command "insert" "ped" '(140 -43) 1 1 0 )
(command "insert" "ped" '(182 -70) 1 1 0 )
(command "insert" "ped" '(179 -64) 1 1 0 )
(command "insert" "ped" '(108 -42) 1 1 0 )
(command "insert" "ped" '(145 -48) 1 1 0 )
(command "insert" "ped" '(141 -42) 1 1 0 )
(command "insert" "ped" '(165 -61) 1 1 0 )
(command "insert" "ped" '(109 -43) 1 1 0 )
(command "insert" "ped" '(114 -47) 1 1 0 )
(command "insert" "ped" '(172 -70) 1 1 0 )
(command "insert" "ped" '(177 -63) 1 1 0 )
(command "insert" "ped" '(143 -50) 1 1 0 )
(command "insert" "ped" '(161 -65) 1 1 0 )
(command "insert" "ped" '(174 -61) 1 1 0 )
(command "insert" "ped" '(148 -48) 1 1 0 )
(command "insert" "ped" '(120 -50) 1 1 0 )
(command "insert" "ped" '(150 -58) 1 1 0 )
(command "insert" "ped" '(150 -59) 1 1 0 )
(command "insert" "ped" '(167 -69) 1 1 0 )
(command "insert" "ped" '(155 -67) 1 1 0 )
(command "insert" "ped" '(144 -44) 1 1 0 )
(command "insert" "ped" '(168 -57) 1 1 0 )
(command "insert" "ped" '(145 -41) 1 1 0 )
(command "insert" "ped" '(146 -46) 1 1 0 )
(command "insert" "ped" '(127 -49) 1 1 0 )
(command "insert" "ped" '(171 -58) 1 1 0 )
(command "insert" "ped" '(172 -61) 1 1 0 )
(command "insert" "ped" '(169 -69) 1 1 0 )
(command "insert" "ped" '(141 -45) 1 1 0 )
(command "insert" "ped" '(176 -65) 1 1 0 )
(command "insert" "ped" '(150 -66) 1 1 0 )
(command "insert" "ped" '(152 -49) 1 1 0 )
(command "insert" "ped" '(174 -68) 1 1 0 )
(command "insert" "ped" '(129 -49) 1 1 0 )
(command "insert" "ped" '(151 -66) 1 1 0 )
(command "insert" "ped" '(110 -44) 1 1 0 )
(command "insert" "ped" '(150 -61) 1 1 0 )
(command "insert" "ped" '(148 -37) 1 1 0 )
(command "insert" "ped" '(151 -56) 1 1 0 )
(command "insert" "ped" '(167 -66) 1 1 0 )
(command "insert" "ped" '(164 -64) 1 1 0 )
(command "insert" "ped" '(177 -66) 1 1 0 )
(command "insert" "ped" '(169 -61) 1 1 0 )
(command "insert" "ped" '(157 -66) 1 1 0 )
(command "insert" "ped" '(154 -68) 1 1 0 )
(command "insert" "ped" '(146 -41) 1 1 0 )
(command "insert" "ped" '(170 -58) 1 1 0 )
(command "insert" "ped" '(168 -70) 1 1 0 )
(command "insert" "ped" '(170 -68) 1 1 0 )
(command "insert" "ped" '(176 -63) 1 1 0 )
(command "insert" "ped" '(173 -57) 1 1 0 )
(command "insert" "ped" '(168 -58) 1 1 0 )
(command "insert" "ped" '(171 -64) 1 1 0 )
(command "insert" "ped" '(152 -56) 1 1 0 )
(command "insert" "ped" '(142 -47) 1 1 0 )
(command "insert" "ped" '(175 -71) 1 1 0 )
(command "insert" "ped" '(143 -46) 1 1 0 )
(command "insert" "ped" '(147 -43) 1 1 0 )
(command "insert" "ped" '(130 -49) 1 1 0 )
(command "insert" "ped" '(163 -69) 1 1 0 )
(command "insert" "ped" '(160 -65) 1 1 0 )
(command "insert" "ped" '(150 -52) 1 1 0 )
(command "insert" "ped" '(148 -44) 1 1 0 )
(command "insert" "ped" '(161 -69) 1 1 0 )
(command "insert" "ped" '(151 -49) 1 1 0 )
(command "insert" "ped" '(132 -47) 1 1 0 )
(command "insert" "ped" '(165 -71) 1 1 0 )
(command "insert" "ped" '(150 -46) 1 1 0 )
(command "insert" "ped" '(133 -46) 1 1 0 )
(command "insert" "ped" '(131 -50) 1 1 0 )
(command "insert" "ped" '(153 -65) 1 1 0 )
(command "insert" "ped" '(134 -45) 1 1 0 )
(command "insert" "ped" '(136 -48) 1 1 0 )
(command "insert" "ped" '(159 -63) 1 1 0 )
(command "insert" "ped" '(139 -45) 1 1 0 )
(command "insert" "ped" '(144 -48) 1 1 0 )
(command "insert" "ped" '(140 -46) 1 1 0 )
(command "insert" "ped" '(108 -45) 1 1 0 )
(command "insert" "ped" '(141 -47) 1 1 0 )
(command "insert" "ped" '(151 -47) 1 1 0 )
(command "insert" "ped" '(167 -60) 1 1 0 )
(command "insert" "ped" '(152 -63) 1 1 0 )
(command "insert" "ped" '(159 -69) 1 1 0 )
(command "insert" "ped" '(153 -62) 1 1 0 )
(command "insert" "ped" '(173 -67) 1 1 0 )
(command "insert" "ped" '(147 -48) 1 1 0 )
(command "insert" "ped" '(154 -61) 1 1 0 )
(command "insert" "ped" '(148 -43) 1 1 0 )
(command "insert" "ped" '(175 -61) 1 1 0 )
(command "insert" "ped" '(149 -42) 1 1 0 )
(command "insert" "ped" '(165 -64) 1 1 0 )
(command "insert" "ped" '(162 -66) 1 1 0 )
(command "insert" "ped" '(161 -63) 1 1 0 )
(command "insert" "ped" '(122 -47) 1 1 0 )
(command "insert" "ped" '(166 -68) 1 1 0 )
(command "insert" "ped" '(153 -67) 1 1 0 )
(command "insert" "ped" '(125 -50) 1 1 0 )
(command "insert" "ped" '(162 -60) 1 1 0 )
(command "insert" "ped" '(123 -46) 1 1 0 )
(command "insert" "ped" '(178 -66) 1 1 0 )
(command "insert" "ped" '(133 -49) 1 1 0 )
(command "insert" "ped" '(179 -66) 1 1 0 )
(command "insert" "ped" '(112 -47) 1 1 0 )
(command "insert" "ped" '(156 -64) 1 1 0 )
(command "insert" "ped" '(170 -54) 1 1 0 )
(command "insert" "ped" '(113 -46) 1 1 0 )
(command "insert" "ped" '(114 -45) 1 1 0 )
(command "insert" "ped" '(138 -49) 1 1 0 )
(command "insert" "ped" '(172 -64) 1 1 0 )
(command "insert" "ped" '(169 -66) 1 1 0 )
(command "insert" "ped" '(168 -56) 1 1 0 )
(command "insert" "ped" '(120 -47) 1 1 0 )
(command "insert" "ped" '(161 -71) 1 1 0 )
(command "insert" "ped" '(174 -67) 1 1 0 )
(command "insert" "ped" '(148 -50) 1 1 0 )
(command "insert" "ped" '(175 -58) 1 1 0 )
(command "insert" "ped" '(110 -43) 1 1 0 )
(command "insert" "ped" '(150 -56) 1 1 0 )
(command "insert" "ped" '(151 -61) 1 1 0 )
(command "insert" "ped" '(179 -71) 1 1 0 )
(command "insert" "ped" '(167 -71) 1 1 0 )
(command "insert" "ped" '(152 -65) 1 1 0 )
(command "insert" "ped" '(144 -46) 1 1 0 )
(command "insert" "ped" '(134 -49) 1 1 0 )
(command "insert" "ped" '(145 -47) 1 1 0 )
(command "insert" "ped" '(169 -58) 1 1 0 )
(command "insert" "ped" '(139 -49) 1 1 0 )
(command "insert" "ped" '(146 -44) 1 1 0 )
(command "insert" "ped" '(168 -65) 1 1 0 )
(command "insert" "ped" '(171 -60) 1 1 0 )
(command "insert" "ped" '(172 -63) 1 1 0 )
(command "insert" "ped" '(176 -58) 1 1 0 )
(command "insert" "ped" '(173 -62) 1 1 0 )
(command "insert" "ped" '(150 -64) 1 1 0 )
(command "insert" "ped" '(152 -51) 1 1 0 )
(command "insert" "ped" '(142 -42) 1 1 0 )
(command "insert" "ped" '(147 -36) 1 1 0 )
(command "insert" "ped" '(150 -51) 1 1 0 )
(command "insert" "ped" '(148 -39) 1 1 0 )
(command "insert" "ped" '(118 -50) 1 1 0 )
(command "insert" "ped" '(122 -49) 1 1 0 )
(command "insert" "ped" '(149 -38) 1 1 0 )
(command "insert" "ped" '(164 -66) 1 1 0 )
(command "insert" "ped" '(130 -46) 1 1 0 )
(command "insert" "ped" '(177 -64) 1 1 0 )
(command "insert" "ped" '(135 -45) 1 1 0 )
(command "insert" "ped" '(157 -64) 1 1 0 )
(command "insert" "ped" '(154 -66) 1 1 0 )
(command "insert" "ped" '(146 -39) 1 1 0 )
(command "insert" "ped" '(170 -56) 1 1 0 )
(command "insert" "ped" '(140 -49) 1 1 0 )
(command "insert" "ped" '(158 -68) 1 1 0 )
(command "insert" "ped" '(172 -54) 1 1 0 )
(command "insert" "ped" '(170 -66) 1 1 0 )
(command "insert" "ped" '(173 -55) 1 1 0 )
(command "insert" "ped" '(171 -66) 1 1 0 )
(command "insert" "ped" '(177 -71) 1 1 0 )
(command "insert" "ped" '(152 -58) 1 1 0 )
(command "insert" "ped" '(142 -45) 1 1 0 )
(command "insert" "ped" '(175 -65) 1 1 0 )
(command "insert" "ped" '(147 -45) 1 1 0 )
(command "insert" "ped" '(120 -45) 1 1 0 )
(command "insert" "ped" '(160 -67) 1 1 0 )
(command "insert" "ped" '(148 -46) 1 1 0 )
(command "insert" "ped" '(131 -46) 1 1 0 )
(command "insert" "ped" '(155 -61) 1 1 0 )
(command "insert" "ped" '(116 -45) 1 1 0 )
(command "insert" "ped" '(151 -51) 1 1 0 )
(command "insert" "ped" '(149 -47) 1 1 0 )
(command "insert" "ped" '(119 -48) 1 1 0 )
(command "insert" "ped" '(165 -69) 1 1 0 )
(command "insert" "ped" '(176 -67) 1 1 0 )
(command "insert" "ped" '(157 -63) 1 1 0 )
(command "insert" "ped" '(118 -47) 1 1 0 )
(command "insert" "ped" '(166 -67) 1 1 0 )
(command "insert" "ped" '(119 -46) 1 1 0 )
(command "insert" "ped" '(138 -46) 1 1 0 )
(command "insert" "ped" '(136 -50) 1 1 0 )
(command "insert" "ped" '(151 -59) 1 1 0 )
(command "insert" "ped" '(139 -47) 1 1 0 )
(command "insert" "ped" '(144 -50) 1 1 0 )
(command "insert" "ped" '(164 -61) 1 1 0 )
(command "insert" "ped" '(108 -47) 1 1 0 )
(command "insert" "ped" '(159 -71) 1 1 0 )
(command "insert" "ped" '(109 -46) 1 1 0 )
(command "insert" "ped" '(166 -63) 1 1 0 )
(command "insert" "ped" '(163 -71) 1 1 0 )
(command "insert" "ped" '(167 -62) 1 1 0 )
(command "insert" "ped" '(160 -71) 1 1 0 )
(command "insert" "ped" '(153 -60) 1 1 0 )
(command "insert" "ped" '(143 -49) 1 1 0 )
(command "insert" "ped" '(173 -65) 1 1 0 )
(command "insert" "ped" '(147 -50) 1 1 0 )
(command "insert" "ped" '(174 -62) 1 1 0 )
(command "insert" "ped" '(175 -63) 1 1 0 )
(command "insert" "ped" '(149 -40) 1 1 0 )
(command "insert" "ped" '(162 -64) 1 1 0 )
(command "insert" "ped" '(121 -46) 1 1 0 )
(command "insert" "ped" '(138 -43) 1 1 0 )
(command "insert" "ped" '(122 -45) 1 1 0 )
(command "insert" "ped" '(125 -48) 1 1 0 )
(command "insert" "ped" '(178 -64) 1 1 0 )
(command "insert" "ped" '(126 -47) 1 1 0 )
(command "insert" "ped" '(151 -67) 1 1 0 )
(command "insert" "ped" '(144 -41) 1 1 0 )
(command "insert" "ped" '(168 -54) 1 1 0 )
(command "insert" "ped" '(127 -46) 1 1 0 )
(command "insert" "ped" '(179 -68) 1 1 0 )
(command "insert" "ped" '(169 -55) 1 1 0 )
(command "insert" "ped" '(156 -66) 1 1 0 )
(command "insert" "ped" '(126 -49) 1 1 0 )
(command "insert" "ped" '(181 -70) 1 1 0 )
(command "insert" "ped" '(171 -57) 1 1 0 )
(command "layer" "m" "Res" "" )
(command "insert" "Res" '(241 -82) 1 1 0 )
(command "insert" "Res" '(246 -86) 1 1 0 )
(command "insert" "Res" '(253 -84) 1 1 0 )
(command "insert" "Res" '(260 -80) 1 1 0 )
(command "insert" "Res" '(252 -85) 1 1 0 )
(command "insert" "Res" '(261 -79) 1 1 0 )
(command "insert" "Res" '(259 -83) 1 1 0 )
(command "insert" "Res" '(238 -85) 1 1 0 )
(command "insert" "Res" '(238 -72) 1 1 0 )
(command "insert" "Res" '(258 -81) 1 1 0 )
(command "insert" "Res" '(249 -80) 1 1 0 )
(command "insert" "Res" '(239 -84) 1 1 0 )
(command "insert" "Res" '(260 -79) 1 1 0 )
(command "insert" "Res" '(236 -76) 1 1 0 )
(command "insert" "Res" '(242 -83) 1 1 0 )
(command "insert" "Res" '(260 -85) 1 1 0 )
(command "insert" "Res" '(239 -72) 1 1 0 )
(command "insert" "Res" '(262 -80) 1 1 0 )
(command "insert" "Res" '(238 -86) 1 1 0 )
(command "insert" "Res" '(243 -82) 1 1 0 )
(command "insert" "Res" '(258 -82) 1 1 0 )
(command "insert" "Res" '(256 -78) 1 1 0 )
(command "insert" "Res" '(249 -83) 1 1 0 )
(command "insert" "Res" '(231 -78) 1 1 0 )
(command "insert" "Res" '(237 -80) 1 1 0 )
(command "insert" "Res" '(251 -80) 1 1 0 )
(command "insert" "Res" '(240 -86) 1 1 0 )
(command "insert" "Res" '(247 -85) 1 1 0 )
(command "insert" "Res" '(250 -81) 1 1 0 )
(command "insert" "Res" '(242 -84) 1 1 0 )
(command "insert" "Res" '(232 -79) 1 1 0 )
(command "insert" "Res" '(262 -78) 1 1 0 )
(command "insert" "Res" '(234 -77) 1 1 0 )
(command "insert" "Res" '(243 -81) 1 1 0 )
(command "insert" "Res" '(249 -78) 1 1 0 )
(command "insert" "Res" '(244 -83) 1 1 0 )
(command "insert" "Res" '(240 -83) 1 1 0 )
(command "insert" "Res" '(250 -82) 1 1 0 )
(command "insert" "Res" '(252 -81) 1 1 0 )
(command "insert" "Res" '(255 -78) 1 1 0 )
(command "insert" "Res" '(240 -84) 1 1 0 )
(command "insert" "Res" '(237 -73) 1 1 0 )
(command "insert" "Res" '(248 -85) 1 1 0 )
(command "insert" "Res" '(241 -81) 1 1 0 )
(command "insert" "Res" '(237 -86) 1 1 0 )
(command "insert" "Res" '(253 -83) 1 1 0 )
(command "insert" "Res" '(251 -79) 1 1 0 )
(command "insert" "Res" '(260 -81) 1 1 0 )
(command "insert" "Res" '(252 -86) 1 1 0 )
(command "insert" "Res" '(261 -78) 1 1 0 )
(command "insert" "Res" '(259 -82) 1 1 0 )
(command "insert" "Res" '(241 -86) 1 1 0 )
(command "insert" "Res" '(238 -73) 1 1 0 )
(command "insert" "Res" '(231 -79) 1 1 0 )
(command "insert" "Res" '(236 -77) 1 1 0 )
(command "insert" "Res" '(257 -79) 1 1 0 )
(command "insert" "Res" '(253 -86) 1 1 0 )
(command "insert" "Res" '(250 -78) 1 1 0 )
(command "insert" "Res" '(260 -86) 1 1 0 )
(command "insert" "Res" '(259 -81) 1 1 0 )
(command "insert" "Res" '(239 -78) 1 1 0 )
(command "insert" "Res" '(235 -77) 1 1 0 )
(command "insert" "Res" '(238 -74) 1 1 0 )
(command "insert" "Res" '(258 -83) 1 1 0 )
(command "insert" "Res" '(263 -79) 1 1 0 )
(command "insert" "Res" '(256 -79) 1 1 0 )
(command "insert" "Res" '(249 -82) 1 1 0 )
(command "insert" "Res" '(254 -84) 1 1 0 )
(command "insert" "Res" '(257 -80) 1 1 0 )
(command "insert" "Res" '(237 -79) 1 1 0 )
(command "insert" "Res" '(251 -83) 1 1 0 )
(command "insert" "Res" '(239 -74) 1 1 0 )
(command "insert" "Res" '(247 -84) 1 1 0 )
(command "insert" "Res" '(242 -85) 1 1 0 )
(command "insert" "Res" '(262 -79) 1 1 0 )
(command "insert" "Res" '(247 -86) 1 1 0 )
(command "insert" "Res" '(238 -80) 1 1 0 )
(command "insert" "Res" '(255 -80) 1 1 0 )
(command "insert" "Res" '(258 -84) 1 1 0 )
(command "insert" "Res" '(241 -85) 1 1 0 )
(command "insert" "Res" '(254 -81) 1 1 0 )
(command "insert" "Res" '(239 -73) 1 1 0 )
(command "insert" "Res" '(258 -78) 1 1 0 )
(command "insert" "Res" '(250 -83) 1 1 0 )
(command "insert" "Res" '(252 -82) 1 1 0 )
(command "insert" "Res" '(242 -86) 1 1 0 )
(command "insert" "Res" '(242 -82) 1 1 0 )
(command "insert" "Res" '(259 -86) 1 1 0 )
(command "insert" "Res" '(239 -79) 1 1 0 )
(command "insert" "Res" '(246 -85) 1 1 0 )
(command "insert" "Res" '(237 -72) 1 1 0 )
(command "insert" "Res" '(248 -86) 1 1 0 )
(command "insert" "Res" '(254 -82) 1 1 0 )
(command "insert" "Res" '(244 -81) 1 1 0 )
(command "insert" "Res" '(237 -85) 1 1 0 )
(command "insert" "Res" '(240 -81) 1 1 0 )
(command "insert" "Res" '(259 -79) 1 1 0 )
(command "insert" "Res" '(253 -82) 1 1 0 )
(command "insert" "Res" '(251 -78) 1 1 0 )
(command "insert" "Res" '(233 -79) 1 1 0 )
(command "insert" "Res" '(260 -82) 1 1 0 )
(command "insert" "Res" '(259 -85) 1 1 0 )
(command "insert" "Res" '(256 -80) 1 1 0 )
(command "insert" "Res" '(238 -78) 1 1 0 )
(command "insert" "Res" '(232 -80) 1 1 0 )
(command "insert" "Res" '(245 -83) 1 1 0 )
(command "insert" "Res" '(239 -86) 1 1 0 )
(command "insert" "Res" '(241 -83) 1 1 0 )
(command "insert" "Res" '(257 -78) 1 1 0 )
(command "insert" "Res" '(253 -85) 1 1 0 )
(command "insert" "Res" '(242 -81) 1 1 0 )
(command "insert" "Res" '(252 -84) 1 1 0 )
(command "insert" "Res" '(259 -80) 1 1 0 )
(command "insert" "Res" '(238 -84) 1 1 0 )
(command "insert" "Res" '(235 -76) 1 1 0 )
(command "insert" "Res" '(258 -80) 1 1 0 )
(command "insert" "Res" '(263 -78) 1 1 0 )
(command "insert" "Res" '(249 -81) 1 1 0 )
(command "insert" "Res" '(254 -85) 1 1 0 )
(command "insert" "Res" '(246 -84) 1 1 0 )
(command "insert" "Res" '(237 -78) 1 1 0 )
(command "insert" "Res" '(251 -82) 1 1 0 )
(command "insert" "Res" '(239 -85) 1 1 0 )
(command "insert" "Res" '(260 -78) 1 1 0 )
(command "insert" "Res" '(236 -75) 1 1 0 )
(command "insert" "Res" '(245 -81) 1 1 0 )
(command "insert" "Res" '(260 -84) 1 1 0 )
(command "insert" "Res" '(234 -75) 1 1 0 )
(command "insert" "Res" '(243 -83) 1 1 0 )
(command "insert" "Res" '(261 -80) 1 1 0 )
(command "insert" "Res" '(239 -80) 1 1 0 )
(command "insert" "Res" '(258 -85) 1 1 0 )
(command "insert" "Res" '(241 -84) 1 1 0 )
(command "insert" "Res" '(254 -86) 1 1 0 )
(command "insert" "Res" '(251 -81) 1 1 0 )
(command "insert" "Res" '(240 -85) 1 1 0 )
(command "insert" "Res" '(258 -79) 1 1 0 )
(command "insert" "Res" '(250 -80) 1 1 0 )
(command "insert" "Res" '(231 -80) 1 1 0 )
(command "insert" "Res" '(252 -83) 1 1 0 )
(command "insert" "Res" '(250 -79) 1 1 0 )
(command "insert" "Res" '(232 -78) 1 1 0 )
(command "insert" "Res" '(234 -76) 1 1 0 )
(command "insert" "Res" '(258 -86) 1 1 0 )
(command "insert" "Res" '(263 -80) 1 1 0 )
(command "insert" "Res" '(249 -79) 1 1 0 )
(command "insert" "Res" '(254 -83) 1 1 0 )
(command "insert" "Res" '(244 -82) 1 1 0 )
(command "insert" "Res" '(237 -84) 1 1 0 )
(command "insert" "Res" '(240 -82) 1 1 0 )
(command "insert" "Res" '(259 -78) 1 1 0 )
(command "insert" "Res" '(235 -75) 1 1 0 )
(command "insert" "Res" '(253 -81) 1 1 0 )
(command "insert" "Res" '(233 -78) 1 1 0 )
(command "insert" "Res" '(260 -83) 1 1 0 )
(command "insert" "Res" '(245 -82) 1 1 0 )
(command "insert" "Res" '(259 -84) 1 1 0 )
(command "insert" "Res" '(255 -79) 1 1 0 )
(command "insert" "Res" '(233 -80) 1 1 0 )
(command "insert" "Res" '(238 -79) 1 1 0 )
(command "insert" "Res" '(237 -74) 1 1 0 )
(command "insert" "Res" '(248 -84) 1 1 0 )
(command "layer" "m" "Res" "" )
(command "insert" "Res" '(197 -73) 1 1 0 )
(command "insert" "Res" '(196 -72) 1 1 0 )
(command "insert" "Res" '(194 -72) 1 1 0 )
(command "insert" "Res" '(199 -71) 1 1 0 )
(command "insert" "Res" '(195 -74) 1 1 0 )
(command "insert" "Res" '(192 -74) 1 1 0 )
(command "insert" "Res" '(192 -63) 1 1 0 )
(command "insert" "Res" '(200 -69) 1 1 0 )
(command "insert" "Res" '(193 -66) 1 1 0 )
(command "insert" "Res" '(190 -65) 1 1 0 )
(command "insert" "Res" '(198 -71) 1 1 0 )
(command "insert" "Res" '(195 -67) 1 1 0 )
(command "insert" "Res" '(202 -71) 1 1 0 )
(command "insert" "Res" '(192 -68) 1 1 0 )
(command "insert" "Res" '(193 -74) 1 1 0 )
(command "insert" "Res" '(201 -71) 1 1 0 )
(command "insert" "Res" '(196 -74) 1 1 0 )
(command "insert" "Res" '(197 -68) 1 1 0 )
(command "insert" "Res" '(189 -65) 1 1 0 )
(command "insert" "Res" '(194 -67) 1 1 0 )
(command "insert" "Res" '(200 -71) 1 1 0 )
(command "insert" "Res" '(196 -66) 1 1 0 )
(command "insert" "Res" '(193 -64) 1 1 0 )
(command "insert" "Res" '(198 -69) 1 1 0 )
(command "insert" "Res" '(192 -65) 1 1 0 )
(command "insert" "Res" '(202 -69) 1 1 0 )
(command "insert" "Res" '(197 -74) 1 1 0 )
(command "insert" "Res" '(191 -63) 1 1 0 )
(command "insert" "Res" '(195 -72) 1 1 0 )
(command "insert" "Res" '(193 -72) 1 1 0 )
(command "insert" "Res" '(192 -73) 1 1 0 )
(command "insert" "Res" '(201 -69) 1 1 0 )
(command "insert" "Res" '(197 -66) 1 1 0 )
(command "insert" "Res" '(194 -68) 1 1 0 )
(command "insert" "Res" '(203 -70) 1 1 0 )
(command "insert" "Res" '(193 -63) 1 1 0 )
(command "insert" "Res" '(193 -67) 1 1 0 )
(command "insert" "Res" '(190 -64) 1 1 0 )
(command "insert" "Res" '(198 -70) 1 1 0 )
(command "insert" "Res" '(202 -70) 1 1 0 )
(command "insert" "Res" '(194 -65) 1 1 0 )
(command "insert" "Res" '(192 -67) 1 1 0 )
(command "insert" "Res" '(197 -72) 1 1 0 )
(command "insert" "Res" '(196 -73) 1 1 0 )
(command "insert" "Res" '(194 -73) 1 1 0 )
(command "insert" "Res" '(203 -69) 1 1 0 )
(command "insert" "Res" '(191 -64) 1 1 0 )
(command "insert" "Res" '(199 -70) 1 1 0 )
(command "insert" "Res" '(196 -68) 1 1 0 )
(command "insert" "Res" '(194 -66) 1 1 0 )
(command "insert" "Res" '(200 -70) 1 1 0 )
(command "insert" "Res" '(193 -65) 1 1 0 )
(command "insert" "Res" '(195 -66) 1 1 0 )
(command "insert" "Res" '(192 -64) 1 1 0 )
(command "insert" "Res" '(193 -68) 1 1 0 )
(command "insert" "Res" '(194 -74) 1 1 0 )
(command "insert" "Res" '(199 -69) 1 1 0 )
(command "insert" "Res" '(193 -73) 1 1 0 )
(command "insert" "Res" '(192 -72) 1 1 0 )
(command "insert" "Res" '(201 -70) 1 1 0 )
(command "insert" "Res" '(197 -67) 1 1 0 )
(command "insert" "Res" '(203 -71) 1 1 0 )
(command "insert" "Res" '(194 -63) 1 1 0 )
(command "insert" "Res" '(189 -63) 1 1 0 )
(command "insert" "Res" '(189 -64) 1 1 0 )
(command "insert" "Res" '(194 -64) 1 1 0 )
(command "insert" "Res" '(195 -73) 1 1 0 )
(command "insert" "Res" '(196 -67) 1 1 0 )
(command "insert" "Res" '(190 -63) 1 1 0 )
(command "insert" "Res" '(191 -65) 1 1 0 )
(command "insert" "Res" '(195 -68) 1 1 0 )
(command "insert" "Res" '(192 -66) 1 1 0 )
(command "layer" "m" "edge" "" )
(command "insert" "edge" '(241 -40) 1 1 0 )
(command "insert" "edge" '(248 -40) 1 1 0 )
(command "insert" "edge" '(237 -40) 1 1 0 )
(command "insert" "edge" '(230 -38) 1 1 0 )
(command "insert" "edge" '(229 -38) 1 1 0 )
(command "insert" "edge" '(236 -39) 1 1 0 )
(command "insert" "edge" '(235 -41) 1 1 0 )
(command "insert" "edge" '(231 -39) 1 1 0 )
(command "insert" "edge" '(226 -33) 1 1 0 )
(command "insert" "edge" '(239 -40) 1 1 0 )
(command "insert" "edge" '(251 -43) 1 1 0 )
(command "insert" "edge" '(229 -33) 1 1 0 )
(command "insert" "edge" '(231 -34) 1 1 0 )
(command "insert" "edge" '(225 -34) 1 1 0 )
(command "insert" "edge" '(232 -35) 1 1 0 )
(command "insert" "edge" '(243 -41) 1 1 0 )
(command "insert" "edge" '(227 -35) 1 1 0 )
(command "insert" "edge" '(233 -34) 1 1 0 )
(command "insert" "edge" '(236 -41) 1 1 0 )
(command "insert" "edge" '(228 -36) 1 1 0 )
(command "insert" "edge" '(230 -35) 1 1 0 )
(command "insert" "edge" '(225 -37) 1 1 0 )
(command "insert" "edge" '(232 -40) 1 1 0 )
(command "insert" "edge" '(246 -40) 1 1 0 )
(command "insert" "edge" '(227 -38) 1 1 0 )
(command "insert" "edge" '(226 -34) 1 1 0 )
(command "insert" "edge" '(233 -37) 1 1 0 )
(command "insert" "edge" '(227 -37) 1 1 0 )
(command "insert" "edge" '(228 -33) 1 1 0 )
(command "insert" "edge" '(230 -36) 1 1 0 )
(command "insert" "edge" '(229 -36) 1 1 0 )
(command "insert" "edge" '(249 -43) 1 1 0 )
(command "insert" "edge" '(231 -33) 1 1 0 )
(command "insert" "edge" '(233 -40) 1 1 0 )
(command "insert" "edge" '(247 -40) 1 1 0 )
(command "insert" "edge" '(245 -41) 1 1 0 )
(command "insert" "edge" '(244 -39) 1 1 0 )
(command "insert" "edge" '(239 -39) 1 1 0 )
(command "insert" "edge" '(237 -41) 1 1 0 )
(command "insert" "edge" '(232 -37) 1 1 0 )
(command "insert" "edge" '(247 -39) 1 1 0 )
(command "insert" "edge" '(231 -41) 1 1 0 )
(command "insert" "edge" '(234 -40) 1 1 0 )
(command "insert" "edge" '(228 -38) 1 1 0 )
(command "insert" "edge" '(248 -39) 1 1 0 )
(command "insert" "edge" '(234 -39) 1 1 0 )
(command "insert" "edge" '(230 -33) 1 1 0 )
(command "insert" "edge" '(225 -33) 1 1 0 )
(command "insert" "edge" '(231 -36) 1 1 0 )
(command "insert" "edge" '(237 -39) 1 1 0 )
(command "insert" "edge" '(244 -41) 1 1 0 )
(command "insert" "edge" '(228 -35) 1 1 0 )
(command "insert" "edge" '(239 -41) 1 1 0 )
(command "insert" "edge" '(250 -43) 1 1 0 )
(command "insert" "edge" '(232 -36) 1 1 0 )
(command "insert" "edge" '(229 -34) 1 1 0 )
(command "insert" "edge" '(241 -41) 1 1 0 )
(command "insert" "edge" '(231 -35) 1 1 0 )
(command "insert" "edge" '(225 -35) 1 1 0 )
(command "insert" "edge" '(232 -34) 1 1 0 )
(command "insert" "edge" '(241 -39) 1 1 0 )
(command "insert" "edge" '(240 -41) 1 1 0 )
(command "insert" "edge" '(251 -44) 1 1 0 )
(command "insert" "edge" '(233 -35) 1 1 0 )
(command "insert" "edge" '(227 -36) 1 1 0 )
(command "insert" "edge" '(249 -44) 1 1 0 )
(command "insert" "edge" '(230 -34) 1 1 0 )
(command "insert" "edge" '(225 -38) 1 1 0 )
(command "insert" "edge" '(232 -39) 1 1 0 )
(command "insert" "edge" '(242 -40) 1 1 0 )
(command "insert" "edge" '(226 -37) 1 1 0 )
(command "insert" "edge" '(233 -38) 1 1 0 )
(command "insert" "edge" '(238 -41) 1 1 0 )
(command "insert" "edge" '(248 -41) 1 1 0 )
(command "insert" "edge" '(235 -39) 1 1 0 )
(command "insert" "edge" '(229 -37) 1 1 0 )
(command "insert" "edge" '(227 -33) 1 1 0 )
(command "insert" "edge" '(235 -40) 1 1 0 )
(command "insert" "edge" '(231 -38) 1 1 0 )
(command "insert" "edge" '(233 -41) 1 1 0 )
(command "insert" "edge" '(247 -41) 1 1 0 )
(command "insert" "edge" '(251 -42) 1 1 0 )
(command "insert" "edge" '(240 -39) 1 1 0 )
(command "insert" "edge" '(242 -41) 1 1 0 )
(command "insert" "edge" '(245 -39) 1 1 0 )
(command "insert" "edge" '(250 -44) 1 1 0 )
(command "insert" "edge" '(236 -40) 1 1 0 )
(command "insert" "edge" '(243 -40) 1 1 0 )
(command "insert" "edge" '(227 -34) 1 1 0 )
(command "insert" "edge" '(226 -38) 1 1 0 )
(command "insert" "edge" '(233 -33) 1 1 0 )
(command "insert" "edge" '(228 -37) 1 1 0 )
(command "insert" "edge" '(225 -36) 1 1 0 )
(command "insert" "edge" '(232 -41) 1 1 0 )
(command "insert" "edge" '(246 -41) 1 1 0 )
(command "insert" "edge" '(231 -37) 1 1 0 )
(command "insert" "edge" '(226 -35) 1 1 0 )
(command "insert" "edge" '(233 -36) 1 1 0 )
(command "insert" "edge" '(244 -40) 1 1 0 )
(command "insert" "edge" '(228 -34) 1 1 0 )
(command "insert" "edge" '(230 -37) 1 1 0 )
(command "insert" "edge" '(229 -35) 1 1 0 )
(command "insert" "edge" '(249 -42) 1 1 0 )
(command "insert" "edge" '(232 -33) 1 1 0 )
(command "insert" "edge" '(243 -39) 1 1 0 )
(command "insert" "edge" '(240 -40) 1 1 0 )
(command "insert" "edge" '(238 -39) 1 1 0 )
(command "insert" "edge" '(245 -40) 1 1 0 )
(command "insert" "edge" '(226 -36) 1 1 0 )
(command "insert" "edge" '(242 -39) 1 1 0 )
(command "insert" "edge" '(246 -39) 1 1 0 )
(command "insert" "edge" '(250 -42) 1 1 0 )
(command "insert" "edge" '(232 -38) 1 1 0 )
(command "insert" "edge" '(231 -40) 1 1 0 )
(command "insert" "edge" '(238 -40) 1 1 0 )
(command "insert" "edge" '(234 -41) 1 1 0 )
(command "insert" "edge" '(233 -39) 1 1 0 )
(command "layer" "m" "Commmer" "" )
(command "insert" "Commmer" '(91 -23) 1 1 0 )
(command "insert" "Commmer" '(90 -21) 1 1 0 )
(command "insert" "Commmer" '(81 -19) 1 1 0 )
(command "insert" "Commmer" '(87 -16) 1 1 0 )
(command "insert" "Commmer" '(86 -24) 1 1 0 )
(command "insert" "Commmer" '(91 -24) 1 1 0 )
(command "insert" "Commmer" '(87 -29) 1 1 0 )
(command "insert" "Commmer" '(93 -21) 1 1 0 )
(command "insert" "Commmer" '(67 -19) 1 1 0 )
(command "insert" "Commmer" '(72 -17) 1 1 0 )
(command "insert" "Commmer" '(68 -20) 1 1 0 )
(command "insert" "Commmer" '(83 -20) 1 1 0 )
(command "insert" "Commmer" '(89 -28) 1 1 0 )
(command "insert" "Commmer" '(88 -20) 1 1 0 )
(command "insert" "Commmer" '(70 -19) 1 1 0 )
(command "insert" "Commmer" '(85 -25) 1 1 0 )
(command "insert" "Commmer" '(84 -23) 1 1 0 )
(command "insert" "Commmer" '(90 -27) 1 1 0 )
(command "insert" "Commmer" '(89 -17) 1 1 0 )
(command "insert" "Commmer" '(86 -22) 1 1 0 )
(command "insert" "Commmer" '(85 -22) 1 1 0 )
(command "insert" "Commmer" '(101 -17) 1 1 0 )
(command "insert" "Commmer" '(90 -22) 1 1 0 )
(command "insert" "Commmer" '(96 -18) 1 1 0 )
(command "insert" "Commmer" '(92 -21) 1 1 0 )
(command "insert" "Commmer" '(82 -13) 1 1 0 )
(command "insert" "Commmer" '(97 -19) 1 1 0 )
(command "insert" "Commmer" '(73 -15) 1 1 0 )
(command "insert" "Commmer" '(79 -12) 1 1 0 )
(command "insert" "Commmer" '(84 -25) 1 1 0 )
(command "insert" "Commmer" '(83 -19) 1 1 0 )
(command "insert" "Commmer" '(74 -17) 1 1 0 )
(command "insert" "Commmer" '(88 -17) 1 1 0 )
(command "insert" "Commmer" '(76 -12) 1 1 0 )
(command "insert" "Commmer" '(100 -17) 1 1 0 )
(command "insert" "Commmer" '(90 -28) 1 1 0 )
(command "insert" "Commmer" '(81 -20) 1 1 0 )
(command "insert" "Commmer" '(82 -19) 1 1 0 )
(command "insert" "Commmer" '(71 -18) 1 1 0 )
(command "insert" "Commmer" '(92 -26) 1 1 0 )
(command "insert" "Commmer" '(99 -15) 1 1 0 )
(command "insert" "Commmer" '(73 -19) 1 1 0 )
(command "insert" "Commmer" '(104 -13) 1 1 0 )
(command "insert" "Commmer" '(68 -19) 1 1 0 )
(command "insert" "Commmer" '(73 -21) 1 1 0 )
(command "insert" "Commmer" '(88 -27) 1 1 0 )
(command "insert" "Commmer" '(87 -17) 1 1 0 )
(command "insert" "Commmer" '(94 -23) 1 1 0 )
(command "insert" "Commmer" '(101 -13) 1 1 0 )
(command "insert" "Commmer" '(83 -14) 1 1 0 )
(command "insert" "Commmer" '(74 -18) 1 1 0 )
(command "insert" "Commmer" '(71 -19) 1 1 0 )
(command "insert" "Commmer" '(95 -22) 1 1 0 )
(command "insert" "Commmer" '(81 -23) 1 1 0 )
(command "insert" "Commmer" '(91 -28) 1 1 0 )
(command "insert" "Commmer" '(82 -20) 1 1 0 )
(command "insert" "Commmer" '(97 -20) 1 1 0 )
(command "insert" "Commmer" '(98 -19) 1 1 0 )
(command "insert" "Commmer" '(69 -18) 1 1 0 )
(command "insert" "Commmer" '(97 -14) 1 1 0 )
(command "insert" "Commmer" '(100 -13) 1 1 0 )
(command "insert" "Commmer" '(73 -16) 1 1 0 )
(command "insert" "Commmer" '(75 -14) 1 1 0 )
(command "insert" "Commmer" '(83 -13) 1 1 0 )
(command "insert" "Commmer" '(99 -16) 1 1 0 )
(command "insert" "Commmer" '(81 -13) 1 1 0 )
(command "insert" "Commmer" '(79 -14) 1 1 0 )
(command "insert" "Commmer" '(95 -21) 1 1 0 )
(command "insert" "Commmer" '(91 -22) 1 1 0 )
(command "insert" "Commmer" '(77 -13) 1 1 0 )
(command "insert" "Commmer" '(81 -18) 1 1 0 )
(command "insert" "Commmer" '(87 -19) 1 1 0 )
(command "insert" "Commmer" '(86 -25) 1 1 0 )
(command "insert" "Commmer" '(91 -27) 1 1 0 )
(command "insert" "Commmer" '(87 -28) 1 1 0 )
(command "insert" "Commmer" '(75 -12) 1 1 0 )
(command "insert" "Commmer" '(92 -28) 1 1 0 )
(command "insert" "Commmer" '(98 -20) 1 1 0 )
(command "insert" "Commmer" '(96 -12) 1 1 0 )
(command "insert" "Commmer" '(82 -15) 1 1 0 )
(command "insert" "Commmer" '(67 -18) 1 1 0 )
(command "insert" "Commmer" '(72 -18) 1 1 0 )
(command "insert" "Commmer" '(83 -23) 1 1 0 )
(command "insert" "Commmer" '(98 -14) 1 1 0 )
(command "insert" "Commmer" '(80 -13) 1 1 0 )
(command "insert" "Commmer" '(85 -24) 1 1 0 )
(command "insert" "Commmer" '(90 -24) 1 1 0 )
(command "insert" "Commmer" '(89 -16) 1 1 0 )
(command "insert" "Commmer" '(79 -13) 1 1 0 )
(command "insert" "Commmer" '(86 -23) 1 1 0 )
(command "insert" "Commmer" '(85 -21) 1 1 0 )
(command "insert" "Commmer" '(101 -16) 1 1 0 )
(command "insert" "Commmer" '(91 -21) 1 1 0 )
(command "insert" "Commmer" '(90 -23) 1 1 0 )
(command "insert" "Commmer" '(96 -19) 1 1 0 )
(command "insert" "Commmer" '(86 -26) 1 1 0 )
(command "insert" "Commmer" '(92 -22) 1 1 0 )
(command "insert" "Commmer" '(97 -18) 1 1 0 )
(command "insert" "Commmer" '(93 -23) 1 1 0 )
(command "insert" "Commmer" '(94 -22) 1 1 0 )
(command "insert" "Commmer" '(84 -26) 1 1 0 )
(command "insert" "Commmer" '(83 -18) 1 1 0 )
(command "insert" "Commmer" '(88 -18) 1 1 0 )
(command "insert" "Commmer" '(84 -21) 1 1 0 )
(command "insert" "Commmer" '(90 -29) 1 1 0 )
(command "insert" "Commmer" '(89 -19) 1 1 0 )
(command "insert" "Commmer" '(77 -14) 1 1 0 )
(command "insert" "Commmer" '(72 -15) 1 1 0 )
(command "insert" "Commmer" '(92 -27) 1 1 0 )
(command "insert" "Commmer" '(72 -22) 1 1 0 )
(command "insert" "Commmer" '(83 -21) 1 1 0 )
(command "insert" "Commmer" '(99 -14) 1 1 0 )
(command "insert" "Commmer" '(104 -14) 1 1 0 )
(command "insert" "Commmer" '(82 -14) 1 1 0 )
(command "insert" "Commmer" '(73 -20) 1 1 0 )
(command "insert" "Commmer" '(88 -28) 1 1 0 )
(command "insert" "Commmer" '(101 -12) 1 1 0 )
(command "insert" "Commmer" '(83 -17) 1 1 0 )
(command "insert" "Commmer" '(74 -19) 1 1 0 )
(command "insert" "Commmer" '(88 -15) 1 1 0 )
(command "insert" "Commmer" '(81 -22) 1 1 0 )
(command "insert" "Commmer" '(82 -21) 1 1 0 )
(command "insert" "Commmer" '(92 -24) 1 1 0 )
(command "insert" "Commmer" '(78 -12) 1 1 0 )
(command "insert" "Commmer" '(97 -13) 1 1 0 )
(command "insert" "Commmer" '(100 -14) 1 1 0 )
(command "insert" "Commmer" '(73 -23) 1 1 0 )
(command "insert" "Commmer" '(70 -20) 1 1 0 )
(command "insert" "Commmer" '(69 -20) 1 1 0 )
(command "insert" "Commmer" '(101 -15) 1 1 0 )
(command "insert" "Commmer" '(83 -12) 1 1 0 )
(command "insert" "Commmer" '(74 -20) 1 1 0 )
(command "insert" "Commmer" '(89 -20) 1 1 0 )
(command "insert" "Commmer" '(102 -12) 1 1 0 )
(command "insert" "Commmer" '(81 -17) 1 1 0 )
(command "insert" "Commmer" '(87 -18) 1 1 0 )
(command "insert" "Commmer" '(91 -26) 1 1 0 )
(command "insert" "Commmer" '(82 -22) 1 1 0 )
(command "insert" "Commmer" '(81 -12) 1 1 0 )
(command "insert" "Commmer" '(103 -13) 1 1 0 )
(command "insert" "Commmer" '(92 -29) 1 1 0 )
(command "insert" "Commmer" '(72 -21) 1 1 0 )
(command "insert" "Commmer" '(96 -13) 1 1 0 )
(command "insert" "Commmer" '(74 -15) 1 1 0 )
(command "insert" "Commmer" '(72 -19) 1 1 0 )
(command "insert" "Commmer" '(83 -22) 1 1 0 )
(command "insert" "Commmer" '(73 -18) 1 1 0 )
(command "insert" "Commmer" '(80 -14) 1 1 0 )
(command "insert" "Commmer" '(90 -25) 1 1 0 )
(command "insert" "Commmer" '(81 -15) 1 1 0 )
(command "insert" "Commmer" '(71 -20) 1 1 0 )
(command "insert" "Commmer" '(77 -12) 1 1 0 )
(command "insert" "Commmer" '(66 -19) 1 1 0 )
(command "insert" "Commmer" '(82 -12) 1 1 0 )
(command "insert" "Commmer" '(96 -20) 1 1 0 )
(command "insert" "Commmer" '(103 -12) 1 1 0 )
(command "insert" "Commmer" '(92 -23) 1 1 0 )
(command "insert" "Commmer" '(91 -25) 1 1 0 )
(command "insert" "Commmer" '(72 -23) 1 1 0 )
(command "insert" "Commmer" '(98 -13) 1 1 0 )
(command "insert" "Commmer" '(66 -18) 1 1 0 )
(command "insert" "Commmer" '(93 -22) 1 1 0 )
(command "insert" "Commmer" '(76 -13) 1 1 0 )
(command "insert" "Commmer" '(87 -15) 1 1 0 )
(command "insert" "Commmer" '(72 -16) 1 1 0 )
(command "insert" "Commmer" '(75 -13) 1 1 0 )
(command "insert" "Commmer" '(89 -29) 1 1 0 )
(command "insert" "Commmer" '(88 -19) 1 1 0 )
(command "insert" "Commmer" '(70 -18) 1 1 0 )
(command "insert" "Commmer" '(85 -26) 1 1 0 )
(command "insert" "Commmer" '(76 -14) 1 1 0 )
(command "insert" "Commmer" '(90 -26) 1 1 0 )
(command "insert" "Commmer" '(89 -18) 1 1 0 )
(command "insert" "Commmer" '(85 -23) 1 1 0 )
(command "insert" "Commmer" '(66 -20) 1 1 0 )
(command "insert" "Commmer" '(82 -17) 1 1 0 )
(command "insert" "Commmer" '(87 -20) 1 1 0 )
(command "insert" "Commmer" '(74 -23) 1 1 0 )
(command "insert" "Commmer" '(99 -13) 1 1 0 )
(command "insert" "Commmer" '(88 -29) 1 1 0 )
(command "insert" "Commmer" '(94 -21) 1 1 0 )
(command "insert" "Commmer" '(82 -16) 1 1 0 )
(command "insert" "Commmer" '(80 -12) 1 1 0 )
(command "insert" "Commmer" '(74 -16) 1 1 0 )
(command "insert" "Commmer" '(88 -16) 1 1 0 )
(command "insert" "Commmer" '(100 -16) 1 1 0 )
(command "insert" "Commmer" '(81 -21) 1 1 0 )
(command "insert" "Commmer" '(89 -15) 1 1 0 )
(command "insert" "Commmer" '(82 -18) 1 1 0 )
(command "insert" "Commmer" '(87 -27) 1 1 0 )
(command "insert" "Commmer" '(92 -25) 1 1 0 )
(command "insert" "Commmer" '(73 -17) 1 1 0 )
(command "insert" "Commmer" '(99 -12) 1 1 0 )
(command "insert" "Commmer" '(97 -12) 1 1 0 )
(command "insert" "Commmer" '(104 -12) 1 1 0 )
(command "insert" "Commmer" '(68 -18) 1 1 0 )
(command "insert" "Commmer" '(100 -15) 1 1 0 )
(command "insert" "Commmer" '(73 -22) 1 1 0 )
(command "insert" "Commmer" '(103 -14) 1 1 0 )
(command "insert" "Commmer" '(78 -13) 1 1 0 )
(command "insert" "Commmer" '(69 -19) 1 1 0 )
(command "insert" "Commmer" '(101 -14) 1 1 0 )
(command "insert" "Commmer" '(83 -15) 1 1 0 )
(command "insert" "Commmer" '(74 -21) 1 1 0 )
(command "insert" "Commmer" '(89 -27) 1 1 0 )
(command "insert" "Commmer" '(95 -23) 1 1 0 )
(command "insert" "Commmer" '(102 -13) 1 1 0 )
(command "insert" "Commmer" '(81 -16) 1 1 0 )
(command "insert" "Commmer" '(91 -29) 1 1 0 )
(command "insert" "Commmer" '(82 -23) 1 1 0 )
(command "insert" "Commmer" '(74 -22) 1 1 0 )
(command "insert" "Commmer" '(98 -18) 1 1 0 )
(command "insert" "Commmer" '(96 -14) 1 1 0 )
(command "insert" "Commmer" '(84 -24) 1 1 0 )
(command "insert" "Commmer" '(67 -20) 1 1 0 )
(command "insert" "Commmer" '(72 -20) 1 1 0 )
(command "insert" "Commmer" '(83 -16) 1 1 0 )
(command "insert" "Commmer" '(100 -12) 1 1 0 )
(command "insert" "Commmer" '(98 -12) 1 1 0 )
(command "insert" "Commmer" '(78 -14) 1 1 0 )
(command "insert" "Commmer" '(84 -22) 1 1 0 )
(command "insert" "Commmer" '(99 -17) 1 1 0 )
(command "insert" "Commmer" '(81 -14) 1 1 0 )
(command "insert" "Commmer" '(86 -21) 1 1 0 )
(command "insert" "Commmer" '(102 -14) 1 1 0 )
(command "layer" "m" "ped" "" )
(command "insert" "ped" '(279 -70) 1 1 0 )
(command "insert" "ped" '(296 -74) 1 1 0 )
(command "insert" "ped" '(284 -67) 1 1 0 )
(command "insert" "ped" '(296 -80) 1 1 0 )
(command "insert" "ped" '(297 -71) 1 1 0 )
(command "insert" "ped" '(299 -68) 1 1 0 )
(command "insert" "ped" '(297 -84) 1 1 0 )
(command "insert" "ped" '(299 -73) 1 1 0 )
(command "insert" "ped" '(281 -57) 1 1 0 )
(command "insert" "ped" '(289 -68) 1 1 0 )
(command "insert" "ped" '(277 -67) 1 1 0 )
(command "insert" "ped" '(276 -61) 1 1 0 )
(command "insert" "ped" '(288 -69) 1 1 0 )
(command "insert" "ped" '(278 -63) 1 1 0 )
(command "insert" "ped" '(293 -67) 1 1 0 )
(command "insert" "ped" '(290 -71) 1 1 0 )
(command "insert" "ped" '(292 -70) 1 1 0 )
(command "insert" "ped" '(281 -69) 1 1 0 )
(command "insert" "ped" '(295 -77) 1 1 0 )
(command "insert" "ped" '(292 -81) 1 1 0 )
(command "insert" "ped" '(283 -70) 1 1 0 )
(command "insert" "ped" '(280 -68) 1 1 0 )
(command "insert" "ped" '(285 -68) 1 1 0 )
(command "insert" "ped" '(282 -70) 1 1 0 )
(command "insert" "ped" '(296 -68) 1 1 0 )
(command "insert" "ped" '(284 -69) 1 1 0 )
(command "insert" "ped" '(298 -75) 1 1 0 )
(command "insert" "ped" '(296 -87) 1 1 0 )
(command "insert" "ped" '(297 -72) 1 1 0 )
(command "insert" "ped" '(298 -70) 1 1 0 )
(command "insert" "ped" '(276 -64) 1 1 0 )
(command "insert" "ped" '(298 -85) 1 1 0 )
(command "insert" "ped" '(278 -71) 1 1 0 )
(command "insert" "ped" '(299 -78) 1 1 0 )
(command "insert" "ped" '(297 -82) 1 1 0 )
(command "insert" "ped" '(280 -54) 1 1 0 )
(command "insert" "ped" '(299 -83) 1 1 0 )
(command "insert" "ped" '(281 -55) 1 1 0 )
(command "insert" "ped" '(289 -66) 1 1 0 )
(command "insert" "ped" '(287 -70) 1 1 0 )
(command "insert" "ped" '(291 -67) 1 1 0 )
(command "insert" "ped" '(279 -55) 1 1 0 )
(command "insert" "ped" '(288 -71) 1 1 0 )
(command "insert" "ped" '(295 -74) 1 1 0 )
(command "insert" "ped" '(281 -67) 1 1 0 )
(command "insert" "ped" '(294 -79) 1 1 0 )
(command "insert" "ped" '(295 -87) 1 1 0 )
(command "insert" "ped" '(294 -82) 1 1 0 )
(command "insert" "ped" '(296 -75) 1 1 0 )
(command "insert" "ped" '(296 -81) 1 1 0 )
(command "insert" "ped" '(297 -70) 1 1 0 )
(command "insert" "ped" '(299 -71) 1 1 0 )
(command "insert" "ped" '(299 -72) 1 1 0 )
(command "insert" "ped" '(281 -56) 1 1 0 )
(command "insert" "ped" '(277 -66) 1 1 0 )
(command "insert" "ped" '(276 -62) 1 1 0 )
(command "insert" "ped" '(279 -67) 1 1 0 )
(command "insert" "ped" '(277 -63) 1 1 0 )
(command "insert" "ped" '(278 -60) 1 1 0 )
(command "insert" "ped" '(293 -66) 1 1 0 )
(command "insert" "ped" '(290 -68) 1 1 0 )
(command "insert" "ped" '(279 -57) 1 1 0 )
(command "insert" "ped" '(295 -67) 1 1 0 )
(command "insert" "ped" '(292 -71) 1 1 0 )
(command "insert" "ped" '(281 -68) 1 1 0 )
(command "insert" "ped" '(288 -70) 1 1 0 )
(command "insert" "ped" '(295 -76) 1 1 0 )
(command "insert" "ped" '(292 -82) 1 1 0 )
(command "insert" "ped" '(280 -69) 1 1 0 )
(command "insert" "ped" '(295 -89) 1 1 0 )
(command "insert" "ped" '(294 -88) 1 1 0 )
(command "insert" "ped" '(285 -67) 1 1 0 )
(command "insert" "ped" '(282 -71) 1 1 0 )
(command "insert" "ped" '(296 -69) 1 1 0 )
(command "insert" "ped" '(284 -70) 1 1 0 )
(command "insert" "ped" '(273 -69) 1 1 0 )
(command "insert" "ped" '(296 -88) 1 1 0 )
(command "insert" "ped" '(297 -79) 1 1 0 )
(command "insert" "ped" '(298 -71) 1 1 0 )
(command "insert" "ped" '(276 -65) 1 1 0 )
(command "insert" "ped" '(298 -82) 1 1 0 )
(command "insert" "ped" '(278 -68) 1 1 0 )
(command "insert" "ped" '(274 -70) 1 1 0 )
(command "insert" "ped" '(297 -81) 1 1 0 )
(command "insert" "ped" '(280 -55) 1 1 0 )
(command "insert" "ped" '(299 -82) 1 1 0 )
(command "insert" "ped" '(281 -54) 1 1 0 )
(command "insert" "ped" '(291 -66) 1 1 0 )
(command "insert" "ped" '(279 -69) 1 1 0 )
(command "insert" "ped" '(279 -54) 1 1 0 )
(command "insert" "ped" '(295 -69) 1 1 0 )
(command "insert" "ped" '(281 -66) 1 1 0 )
(command "insert" "ped" '(294 -76) 1 1 0 )
(command "insert" "ped" '(283 -67) 1 1 0 )
(command "insert" "ped" '(294 -83) 1 1 0 )
(command "insert" "ped" '(296 -71) 1 1 0 )
(command "insert" "ped" '(296 -76) 1 1 0 )
(command "insert" "ped" '(298 -78) 1 1 0 )
(command "insert" "ped" '(296 -82) 1 1 0 )
(command "insert" "ped" '(297 -69) 1 1 0 )
(command "insert" "ped" '(299 -70) 1 1 0 )
(command "insert" "ped" '(278 -66) 1 1 0 )
(command "insert" "ped" '(299 -75) 1 1 0 )
(command "insert" "ped" '(277 -65) 1 1 0 )
(command "insert" "ped" '(276 -63) 1 1 0 )
(command "insert" "ped" '(294 -70) 1 1 0 )
(command "insert" "ped" '(279 -66) 1 1 0 )
(command "insert" "ped" '(277 -62) 1 1 0 )
(command "insert" "ped" '(278 -61) 1 1 0 )
(command "insert" "ped" '(290 -69) 1 1 0 )
(command "insert" "ped" '(291 -81) 1 1 0 )
(command "insert" "ped" '(279 -56) 1 1 0 )
(command "insert" "ped" '(299 -66) 1 1 0 )
(command "insert" "ped" '(295 -66) 1 1 0 )
(command "insert" "ped" '(294 -71) 1 1 0 )
(command "insert" "ped" '(295 -79) 1 1 0 )
(command "insert" "ped" '(292 -83) 1 1 0 )
(command "insert" "ped" '(280 -70) 1 1 0 )
(command "insert" "ped" '(294 -74) 1 1 0 )
(command "insert" "ped" '(295 -88) 1 1 0 )
(command "insert" "ped" '(294 -89) 1 1 0 )
(command "insert" "ped" '(285 -66) 1 1 0 )
(command "insert" "ped" '(282 -68) 1 1 0 )
(command "insert" "ped" '(296 -70) 1 1 0 )
(command "insert" "ped" '(287 -67) 1 1 0 )
(command "insert" "ped" '(284 -71) 1 1 0 )
(command "insert" "ped" '(298 -73) 1 1 0 )
(command "insert" "ped" '(286 -70) 1 1 0 )
(command "insert" "ped" '(296 -89) 1 1 0 )
(command "insert" "ped" '(297 -78) 1 1 0 )
(command "insert" "ped" '(298 -68) 1 1 0 )
(command "insert" "ped" '(276 -66) 1 1 0 )
(command "insert" "ped" '(297 -67) 1 1 0 )
(command "insert" "ped" '(298 -83) 1 1 0 )
(command "insert" "ped" '(278 -69) 1 1 0 )
(command "insert" "ped" '(275 -69) 1 1 0 )
(command "insert" "ped" '(274 -71) 1 1 0 )
(command "insert" "ped" '(297 -80) 1 1 0 )
(command "insert" "ped" '(280 -56) 1 1 0 )
(command "insert" "ped" '(299 -85) 1 1 0 )
(command "insert" "ped" '(281 -53) 1 1 0 )
(command "insert" "ped" '(277 -71) 1 1 0 )
(command "insert" "ped" '(291 -69) 1 1 0 )
(command "insert" "ped" '(279 -68) 1 1 0 )
(command "insert" "ped" '(293 -71) 1 1 0 )
(command "insert" "ped" '(295 -68) 1 1 0 )
(command "insert" "ped" '(294 -77) 1 1 0 )
(command "insert" "ped" '(295 -81) 1 1 0 )
(command "insert" "ped" '(283 -66) 1 1 0 )
(command "insert" "ped" '(294 -80) 1 1 0 )
(command "insert" "ped" '(296 -77) 1 1 0 )
(command "insert" "ped" '(287 -69) 1 1 0 )
(command "insert" "ped" '(298 -79) 1 1 0 )
(command "insert" "ped" '(296 -83) 1 1 0 )
(command "insert" "ped" '(297 -68) 1 1 0 )
(command "insert" "ped" '(276 -68) 1 1 0 )
(command "insert" "ped" '(297 -89) 1 1 0 )
(command "insert" "ped" '(278 -67) 1 1 0 )
(command "insert" "ped" '(299 -74) 1 1 0 )
(command "insert" "ped" '(277 -64) 1 1 0 )
(command "insert" "ped" '(298 -72) 1 1 0 )
(command "insert" "ped" '(281 -51) 1 1 0 )
(command "insert" "ped" '(277 -61) 1 1 0 )
(command "insert" "ped" '(295 -82) 1 1 0 )
(command "insert" "ped" '(290 -66) 1 1 0 )
(command "insert" "ped" '(279 -59) 1 1 0 )
(command "insert" "ped" '(294 -68) 1 1 0 )
(command "insert" "ped" '(295 -78) 1 1 0 )
(command "insert" "ped" '(280 -71) 1 1 0 )
(command "insert" "ped" '(294 -75) 1 1 0 )
(command "insert" "ped" '(288 -66) 1 1 0 )
(command "insert" "ped" '(282 -69) 1 1 0 )
(command "insert" "ped" '(287 -66) 1 1 0 )
(command "insert" "ped" '(286 -71) 1 1 0 )
(command "insert" "ped" '(297 -77) 1 1 0 )
(command "insert" "ped" '(298 -69) 1 1 0 )
(command "insert" "ped" '(276 -67) 1 1 0 )
(command "insert" "ped" '(297 -66) 1 1 0 )
(command "insert" "ped" '(298 -80) 1 1 0 )
(command "insert" "ped" '(299 -67) 1 1 0 )
(command "insert" "ped" '(297 -87) 1 1 0 )
(command "insert" "ped" '(280 -57) 1 1 0 )
(command "insert" "ped" '(299 -84) 1 1 0 )
(command "insert" "ped" '(281 -52) 1 1 0 )
(command "insert" "ped" '(289 -71) 1 1 0 )
(command "insert" "ped" '(277 -70) 1 1 0 )
(command "insert" "ped" '(273 -70) 1 1 0 )
(command "insert" "ped" '(299 -89) 1 1 0 )
(command "insert" "ped" '(291 -68) 1 1 0 )
(command "insert" "ped" '(279 -71) 1 1 0 )
(command "insert" "ped" '(293 -70) 1 1 0 )
(command "insert" "ped" '(295 -71) 1 1 0 )
(command "insert" "ped" '(293 -83) 1 1 0 )
(command "insert" "ped" '(294 -66) 1 1 0 )
(command "insert" "ped" '(295 -80) 1 1 0 )
(command "insert" "ped" '(283 -69) 1 1 0 )
(command "insert" "ped" '(294 -81) 1 1 0 )
(command "insert" "ped" '(296 -78) 1 1 0 )
(command "insert" "ped" '(285 -71) 1 1 0 )
(command "insert" "ped" '(287 -68) 1 1 0 )
(command "insert" "ped" '(298 -76) 1 1 0 )
(command "insert" "ped" '(297 -75) 1 1 0 )
(command "insert" "ped" '(276 -69) 1 1 0 )
(command "insert" "ped" '(297 -88) 1 1 0 )
(command "insert" "ped" '(298 -86) 1 1 0 )
(command "insert" "ped" '(278 -64) 1 1 0 )
(command "insert" "ped" '(299 -77) 1 1 0 )
(command "insert" "ped" '(280 -51) 1 1 0 )
(command "insert" "ped" '(277 -60) 1 1 0 )
(command "insert" "ped" '(273 -71) 1 1 0 )
(command "insert" "ped" '(290 -67) 1 1 0 )
(command "insert" "ped" '(291 -83) 1 1 0 )
(command "insert" "ped" '(279 -58) 1 1 0 )
(command "insert" "ped" '(292 -66) 1 1 0 )
(command "insert" "ped" '(294 -69) 1 1 0 )
(command "insert" "ped" '(295 -73) 1 1 0 )
(command "insert" "ped" '(294 -72) 1 1 0 )
(command "insert" "ped" '(282 -66) 1 1 0 )
(command "insert" "ped" '(296 -72) 1 1 0 )
(command "insert" "ped" '(286 -68) 1 1 0 )
(command "insert" "ped" '(297 -76) 1 1 0 )
(command "insert" "ped" '(298 -66) 1 1 0 )
(command "insert" "ped" '(298 -81) 1 1 0 )
(command "insert" "ped" '(275 -71) 1 1 0 )
(command "insert" "ped" '(274 -69) 1 1 0 )
(command "insert" "ped" '(297 -86) 1 1 0 )
(command "insert" "ped" '(280 -58) 1 1 0 )
(command "insert" "ped" '(299 -87) 1 1 0 )
(command "insert" "ped" '(281 -59) 1 1 0 )
(command "insert" "ped" '(289 -70) 1 1 0 )
(command "insert" "ped" '(277 -69) 1 1 0 )
(command "insert" "ped" '(299 -88) 1 1 0 )
(command "insert" "ped" '(291 -71) 1 1 0 )
(command "insert" "ped" '(288 -67) 1 1 0 )
(command "insert" "ped" '(279 -51) 1 1 0 )
(command "insert" "ped" '(293 -69) 1 1 0 )
(command "insert" "ped" '(295 -70) 1 1 0 )
(command "insert" "ped" '(292 -68) 1 1 0 )
(command "insert" "ped" '(293 -82) 1 1 0 )
(command "insert" "ped" '(281 -71) 1 1 0 )
(command "insert" "ped" '(294 -67) 1 1 0 )
(command "insert" "ped" '(295 -83) 1 1 0 )
(command "insert" "ped" '(283 -68) 1 1 0 )
(command "insert" "ped" '(280 -66) 1 1 0 )
(command "insert" "ped" '(296 -79) 1 1 0 )
(command "insert" "ped" '(285 -70) 1 1 0 )
(command "insert" "ped" '(296 -66) 1 1 0 )
(command "insert" "ped" '(298 -77) 1 1 0 )
(command "insert" "ped" '(286 -66) 1 1 0 )
(command "insert" "ped" '(297 -74) 1 1 0 )
(command "insert" "ped" '(298 -88) 1 1 0 )
(command "insert" "ped" '(276 -70) 1 1 0 )
(command "insert" "ped" '(298 -87) 1 1 0 )
(command "insert" "ped" '(278 -65) 1 1 0 )
(command "insert" "ped" '(299 -76) 1 1 0 )
(command "insert" "ped" '(280 -52) 1 1 0 )
(command "insert" "ped" '(299 -81) 1 1 0 )
(command "insert" "ped" '(291 -82) 1 1 0 )
(command "insert" "ped" '(279 -53) 1 1 0 )
(command "insert" "ped" '(292 -67) 1 1 0 )
(command "insert" "ped" '(295 -72) 1 1 0 )
(command "insert" "ped" '(294 -73) 1 1 0 )
(command "insert" "ped" '(282 -67) 1 1 0 )
(command "insert" "ped" '(296 -73) 1 1 0 )
(command "insert" "ped" '(284 -66) 1 1 0 )
(command "insert" "ped" '(286 -69) 1 1 0 )
(command "insert" "ped" '(298 -67) 1 1 0 )
(command "insert" "ped" '(275 -70) 1 1 0 )
(command "insert" "ped" '(299 -69) 1 1 0 )
(command "insert" "ped" '(297 -85) 1 1 0 )
(command "insert" "ped" '(280 -59) 1 1 0 )
(command "insert" "ped" '(299 -86) 1 1 0 )
(command "insert" "ped" '(281 -58) 1 1 0 )
(command "insert" "ped" '(289 -69) 1 1 0 )
(command "insert" "ped" '(277 -68) 1 1 0 )
(command "insert" "ped" '(276 -60) 1 1 0 )
(command "insert" "ped" '(291 -70) 1 1 0 )
(command "insert" "ped" '(288 -68) 1 1 0 )
(command "insert" "ped" '(278 -62) 1 1 0 )
(command "insert" "ped" '(293 -68) 1 1 0 )
(command "insert" "ped" '(290 -70) 1 1 0 )
(command "insert" "ped" '(292 -69) 1 1 0 )
(command "insert" "ped" '(293 -81) 1 1 0 )
(command "insert" "ped" '(281 -70) 1 1 0 )
(command "insert" "ped" '(287 -71) 1 1 0 )
(command "insert" "ped" '(283 -71) 1 1 0 )
(command "insert" "ped" '(280 -67) 1 1 0 )
(command "insert" "ped" '(294 -87) 1 1 0 )
(command "insert" "ped" '(285 -69) 1 1 0 )
(command "insert" "ped" '(296 -67) 1 1 0 )
(command "insert" "ped" '(284 -68) 1 1 0 )
(command "insert" "ped" '(298 -74) 1 1 0 )
(command "insert" "ped" '(286 -67) 1 1 0 )
(command "insert" "ped" '(297 -73) 1 1 0 )
(command "insert" "ped" '(298 -89) 1 1 0 )
(command "insert" "ped" '(276 -71) 1 1 0 )
(command "insert" "ped" '(298 -84) 1 1 0 )
(command "insert" "ped" '(278 -70) 1 1 0 )
(command "insert" "ped" '(299 -79) 1 1 0 )
(command "insert" "ped" '(297 -83) 1 1 0 )
(command "insert" "ped" '(280 -53) 1 1 0 )
(command "insert" "ped" '(299 -80) 1 1 0 )
(command "insert" "ped" '(289 -67) 1 1 0 )
(command "insert" "ped" '(279 -52) 1 1 0 )
(command "insert" "ped" '(295 -75) 1 1 0 )
(command "insert" "ped" '(294 -78) 1 1 0 )
(command "layer" "m" "edge" "" )
(command "insert" "edge" '(95 -11) 1 1 0 )
(command "insert" "edge" '(89 -11) 1 1 0 )
(command "insert" "edge" '(98 -9) 1 1 0 )
(command "insert" "edge" '(76 -7) 1 1 0 )
(command "insert" "edge" '(78 -6) 1 1 0 )
(command "insert" "edge" '(77 -6) 1 1 0 )
(command "insert" "edge" '(84 -10) 1 1 0 )
(command "insert" "edge" '(96 -11) 1 1 0 )
(command "insert" "edge" '(94 -10) 1 1 0 )
(command "insert" "edge" '(79 -7) 1 1 0 )
(command "insert" "edge" '(85 -11) 1 1 0 )
(command "insert" "edge" '(97 -10) 1 1 0 )
(command "insert" "edge" '(94 -11) 1 1 0 )
(command "insert" "edge" '(87 -10) 1 1 0 )
(command "insert" "edge" '(92 -11) 1 1 0 )
(command "insert" "edge" '(93 -10) 1 1 0 )
(command "insert" "edge" '(98 -10) 1 1 0 )
(command "insert" "edge" '(72 -8) 1 1 0 )
(command "insert" "edge" '(86 -8) 1 1 0 )
(command "insert" "edge" '(89 -9) 1 1 0 )
(command "insert" "edge" '(75 -6) 1 1 0 )
(command "insert" "edge" '(97 -9) 1 1 0 )
(command "insert" "edge" '(80 -6) 1 1 0 )
(command "insert" "edge" '(81 -7) 1 1 0 )
(command "insert" "edge" '(73 -8) 1 1 0 )
(command "insert" "edge" '(85 -9) 1 1 0 )
(command "insert" "edge" '(84 -7) 1 1 0 )
(command "insert" "edge" '(90 -11) 1 1 0 )
(command "insert" "edge" '(86 -6) 1 1 0 )
(command "insert" "edge" '(85 -6) 1 1 0 )
(command "insert" "edge" '(88 -9) 1 1 0 )
(command "insert" "edge" '(74 -8) 1 1 0 )
(command "insert" "edge" '(74 -7) 1 1 0 )
(command "insert" "edge" '(76 -6) 1 1 0 )
(command "insert" "edge" '(91 -10) 1 1 0 )
(command "insert" "edge" '(82 -6) 1 1 0 )
(command "insert" "edge" '(84 -9) 1 1 0 )
(command "insert" "edge" '(96 -10) 1 1 0 )
(command "insert" "edge" '(83 -7) 1 1 0 )
(command "insert" "edge" '(97 -11) 1 1 0 )
(command "insert" "edge" '(83 -6) 1 1 0 )
(command "insert" "edge" '(92 -10) 1 1 0 )
(command "insert" "edge" '(90 -9) 1 1 0 )
(command "insert" "edge" '(93 -11) 1 1 0 )
(command "insert" "edge" '(72 -7) 1 1 0 )
(command "insert" "edge" '(86 -11) 1 1 0 )
(command "insert" "edge" '(88 -11) 1 1 0 )
(command "insert" "edge" '(91 -9) 1 1 0 )
(command "insert" "edge" '(73 -6) 1 1 0 )
(command "insert" "edge" '(95 -10) 1 1 0 )
(command "insert" "edge" '(89 -10) 1 1 0 )
(command "insert" "edge" '(75 -7) 1 1 0 )
(command "insert" "edge" '(75 -8) 1 1 0 )
(command "insert" "edge" '(80 -8) 1 1 0 )
(command "insert" "edge" '(78 -7) 1 1 0 )
(command "insert" "edge" '(84 -11) 1 1 0 )
(command "insert" "edge" '(87 -9) 1 1 0 )
(command "insert" "edge" '(82 -7) 1 1 0 )
(command "insert" "edge" '(79 -6) 1 1 0 )
(command "insert" "edge" '(77 -7) 1 1 0 )
(command "insert" "edge" '(85 -10) 1 1 0 )
(command "insert" "edge" '(84 -6) 1 1 0 )
(command "insert" "edge" '(90 -10) 1 1 0 )
(command "insert" "edge" '(85 -7) 1 1 0 )
(command "insert" "edge" '(78 -8) 1 1 0 )
(command "insert" "edge" '(76 -8) 1 1 0 )
(command "insert" "edge" '(83 -8) 1 1 0 )
(command "insert" "edge" '(81 -8) 1 1 0 )
(command "insert" "edge" '(95 -9) 1 1 0 )
(command "insert" "edge" '(93 -9) 1 1 0 )
(command "insert" "edge" '(74 -6) 1 1 0 )
(command "insert" "edge" '(98 -11) 1 1 0 )
(command "insert" "edge" '(86 -9) 1 1 0 )
(command "insert" "edge" '(79 -8) 1 1 0 )
(command "insert" "edge" '(91 -11) 1 1 0 )
(command "insert" "edge" '(77 -8) 1 1 0 )
(command "insert" "edge" '(84 -8) 1 1 0 )
(command "insert" "edge" '(96 -9) 1 1 0 )
(command "insert" "edge" '(82 -8) 1 1 0 )
(command "insert" "edge" '(80 -7) 1 1 0 )
(command "insert" "edge" '(81 -6) 1 1 0 )
(command "insert" "edge" '(87 -11) 1 1 0 )
(command "insert" "edge" '(94 -9) 1 1 0 )
(command "insert" "edge" '(92 -9) 1 1 0 )
(command "insert" "edge" '(85 -8) 1 1 0 )
(command "insert" "edge" '(86 -7) 1 1 0 )
(command "insert" "edge" '(72 -6) 1 1 0 )
(command "insert" "edge" '(86 -10) 1 1 0 )
(command "insert" "edge" '(88 -10) 1 1 0 )
(command "insert" "edge" '(73 -7) 1 1 0 )
(command "layer" "m" "edge" "" )
(command "insert" "edge" '(48 -43) 1 1 0 )
(command "insert" "edge" '(57 -50) 1 1 0 )
(command "insert" "edge" '(60 -42) 1 1 0 )
(command "insert" "edge" '(61 -43) 1 1 0 )
(command "insert" "edge" '(55 -44) 1 1 0 )
(command "insert" "edge" '(56 -43) 1 1 0 )
(command "insert" "edge" '(58 -50) 1 1 0 )
(command "insert" "edge" '(57 -42) 1 1 0 )
(command "insert" "edge" '(55 -43) 1 1 0 )
(command "insert" "edge" '(59 -44) 1 1 0 )
(command "insert" "edge" '(62 -43) 1 1 0 )
(command "insert" "edge" '(57 -45) 1 1 0 )
(command "insert" "edge" '(58 -42) 1 1 0 )
(command "insert" "edge" '(51 -42) 1 1 0 )
(command "insert" "edge" '(54 -42) 1 1 0 )
(command "insert" "edge" '(62 -44) 1 1 0 )
(command "insert" "edge" '(57 -48) 1 1 0 )
(command "insert" "edge" '(49 -42) 1 1 0 )
(command "insert" "edge" '(54 -47) 1 1 0 )
(command "insert" "edge" '(52 -42) 1 1 0 )
(command "insert" "edge" '(55 -46) 1 1 0 )
(command "insert" "edge" '(56 -45) 1 1 0 )
(command "insert" "edge" '(59 -43) 1 1 0 )
(command "insert" "edge" '(53 -43) 1 1 0 )
(command "insert" "edge" '(58 -48) 1 1 0 )
(command "insert" "edge" '(60 -44) 1 1 0 )
(command "insert" "edge" '(58 -47) 1 1 0 )
(command "insert" "edge" '(48 -42) 1 1 0 )
(command "insert" "edge" '(59 -46) 1 1 0 )
(command "insert" "edge" '(49 -43) 1 1 0 )
(command "insert" "edge" '(59 -48) 1 1 0 )
(command "insert" "edge" '(61 -44) 1 1 0 )
(command "insert" "edge" '(51 -44) 1 1 0 )
(command "insert" "edge" '(55 -45) 1 1 0 )
(command "insert" "edge" '(56 -42) 1 1 0 )
(command "insert" "edge" '(57 -43) 1 1 0 )
(command "insert" "edge" '(54 -45) 1 1 0 )
(command "insert" "edge" '(56 -47) 1 1 0 )
(command "insert" "edge" '(59 -45) 1 1 0 )
(command "insert" "edge" '(62 -42) 1 1 0 )
(command "insert" "edge" '(57 -46) 1 1 0 )
(command "insert" "edge" '(58 -45) 1 1 0 )
(command "insert" "edge" '(51 -43) 1 1 0 )
(command "insert" "edge" '(48 -44) 1 1 0 )
(command "insert" "edge" '(52 -44) 1 1 0 )
(command "insert" "edge" '(57 -49) 1 1 0 )
(command "insert" "edge" '(60 -43) 1 1 0 )
(command "insert" "edge" '(59 -50) 1 1 0 )
(command "insert" "edge" '(61 -42) 1 1 0 )
(command "insert" "edge" '(54 -46) 1 1 0 )
(command "insert" "edge" '(55 -47) 1 1 0 )
(command "insert" "edge" '(49 -44) 1 1 0 )
(command "insert" "edge" '(56 -44) 1 1 0 )
(command "insert" "edge" '(53 -44) 1 1 0 )
(command "insert" "edge" '(50 -42) 1 1 0 )
(command "insert" "edge" '(50 -43) 1 1 0 )
(command "insert" "edge" '(58 -46) 1 1 0 )
(command "insert" "edge" '(55 -42) 1 1 0 )
(command "insert" "edge" '(59 -47) 1 1 0 )
(command "insert" "edge" '(57 -44) 1 1 0 )
(command "insert" "edge" '(59 -49) 1 1 0 )
(command "insert" "edge" '(58 -43) 1 1 0 )
(command "insert" "edge" '(54 -43) 1 1 0 )
(command "insert" "edge" '(50 -44) 1 1 0 )
(command "insert" "edge" '(54 -44) 1 1 0 )
(command "insert" "edge" '(52 -43) 1 1 0 )
(command "insert" "edge" '(56 -46) 1 1 0 )
(command "insert" "edge" '(59 -42) 1 1 0 )
(command "insert" "edge" '(53 -42) 1 1 0 )
(command "insert" "edge" '(58 -49) 1 1 0 )
(command "insert" "edge" '(57 -47) 1 1 0 )
(command "insert" "edge" '(58 -44) 1 1 0 )
(command "layer" "m" "Commmer" "" )
(command "insert" "Commmer" '(49 -18) 1 1 0 )
(command "insert" "Commmer" '(44 -15) 1 1 0 )
(command "insert" "Commmer" '(43 -17) 1 1 0 )
(command "insert" "Commmer" '(46 -16) 1 1 0 )
(command "insert" "Commmer" '(42 -16) 1 1 0 )
(command "insert" "Commmer" '(50 -18) 1 1 0 )
(command "insert" "Commmer" '(53 -20) 1 1 0 )
(command "insert" "Commmer" '(45 -18) 1 1 0 )
(command "insert" "Commmer" '(48 -20) 1 1 0 )
(command "insert" "Commmer" '(43 -15) 1 1 0 )
(command "insert" "Commmer" '(47 -16) 1 1 0 )
(command "insert" "Commmer" '(49 -17) 1 1 0 )
(command "insert" "Commmer" '(43 -16) 1 1 0 )
(command "insert" "Commmer" '(46 -17) 1 1 0 )
(command "insert" "Commmer" '(48 -16) 1 1 0 )
(command "insert" "Commmer" '(51 -19) 1 1 0 )
(command "insert" "Commmer" '(42 -17) 1 1 0 )
(command "insert" "Commmer" '(47 -20) 1 1 0 )
(command "insert" "Commmer" '(52 -20) 1 1 0 )
(command "insert" "Commmer" '(49 -20) 1 1 0 )
(command "insert" "Commmer" '(50 -20) 1 1 0 )
(command "insert" "Commmer" '(42 -15) 1 1 0 )
(command "insert" "Commmer" '(45 -17) 1 1 0 )
(command "insert" "Commmer" '(50 -19) 1 1 0 )
(command "insert" "Commmer" '(44 -16) 1 1 0 )
(command "insert" "Commmer" '(47 -19) 1 1 0 )
(command "insert" "Commmer" '(49 -16) 1 1 0 )
(command "insert" "Commmer" '(49 -15) 1 1 0 )
(command "insert" "Commmer" '(48 -17) 1 1 0 )
(command "insert" "Commmer" '(51 -18) 1 1 0 )
(command "insert" "Commmer" '(46 -18) 1 1 0 )
(command "insert" "Commmer" '(45 -16) 1 1 0 )
(command "insert" "Commmer" '(50 -16) 1 1 0 )
(command "insert" "Commmer" '(44 -17) 1 1 0 )
(command "insert" "Commmer" '(48 -15) 1 1 0 )
(command "insert" "Commmer" '(52 -18) 1 1 0 )
(command "insert" "Commmer" '(45 -20) 1 1 0 )
(command "insert" "Commmer" '(48 -18) 1 1 0 )
(command "insert" "Commmer" '(53 -19) 1 1 0 )
(command "insert" "Commmer" '(47 -15) 1 1 0 )
(command "insert" "Commmer" '(49 -19) 1 1 0 )
(command "insert" "Commmer" '(46 -19) 1 1 0 )
(command "insert" "Commmer" '(51 -20) 1 1 0 )
(command "insert" "Commmer" '(45 -15) 1 1 0 )
(command "insert" "Commmer" '(50 -17) 1 1 0 )
(command "insert" "Commmer" '(47 -18) 1 1 0 )
(command "insert" "Commmer" '(50 -15) 1 1 0 )
(command "insert" "Commmer" '(46 -15) 1 1 0 )
(command "insert" "Commmer" '(52 -19) 1 1 0 )
(command "insert" "Commmer" '(45 -19) 1 1 0 )
(command "insert" "Commmer" '(46 -20) 1 1 0 )
(command "insert" "Commmer" '(48 -19) 1 1 0 )
(command "insert" "Commmer" '(53 -18) 1 1 0 )
(command "insert" "Commmer" '(47 -17) 1 1 0 )
(command "layer" "m" "Res" "" )
(command "insert" "Res" '(285 -81) 1 1 0 )
(command "insert" "Res" '(282 -85) 1 1 0 )
(command "insert" "Res" '(286 -78) 1 1 0 )
(command "insert" "Res" '(286 -84) 1 1 0 )
(command "insert" "Res" '(287 -79) 1 1 0 )
(command "insert" "Res" '(287 -81) 1 1 0 )
(command "insert" "Res" '(284 -84) 1 1 0 )
(command "insert" "Res" '(286 -80) 1 1 0 )
(command "insert" "Res" '(285 -79) 1 1 0 )
(command "insert" "Res" '(283 -86) 1 1 0 )
(command "insert" "Res" '(287 -85) 1 1 0 )
(command "insert" "Res" '(286 -79) 1 1 0 )
(command "insert" "Res" '(286 -85) 1 1 0 )
(command "insert" "Res" '(285 -84) 1 1 0 )
(command "insert" "Res" '(282 -86) 1 1 0 )
(command "insert" "Res" '(287 -80) 1 1 0 )
(command "insert" "Res" '(284 -85) 1 1 0 )
(command "insert" "Res" '(286 -81) 1 1 0 )
(command "insert" "Res" '(285 -85) 1 1 0 )
(command "insert" "Res" '(285 -80) 1 1 0 )
(command "insert" "Res" '(287 -84) 1 1 0 )
(command "insert" "Res" '(285 -83) 1 1 0 )
(command "insert" "Res" '(287 -83) 1 1 0 )
(command "insert" "Res" '(284 -86) 1 1 0 )
(command "insert" "Res" '(286 -86) 1 1 0 )
(command "insert" "Res" '(285 -78) 1 1 0 )
(command "insert" "Res" '(285 -82) 1 1 0 )
(command "insert" "Res" '(286 -82) 1 1 0 )
(command "insert" "Res" '(283 -84) 1 1 0 )
(command "insert" "Res" '(282 -84) 1 1 0 )
(command "insert" "Res" '(287 -82) 1 1 0 )
(command "insert" "Res" '(285 -86) 1 1 0 )
(command "insert" "Res" '(287 -86) 1 1 0 )
(command "insert" "Res" '(286 -83) 1 1 0 )
(command "insert" "Res" '(283 -85) 1 1 0 )
(command "insert" "Res" '(287 -78) 1 1 0 )
(command "layer" "m" "edge" "" )
(command "insert" "edge" '(206 -28) 1 1 0 )
(command "insert" "edge" '(204 -27) 1 1 0 )
(command "insert" "edge" '(205 -27) 1 1 0 )
(command "insert" "edge" '(206 -27) 1 1 0 )
(command "insert" "edge" '(205 -28) 1 1 0 )
(command "insert" "edge" '(205 -29) 1 1 0 )
(command "insert" "edge" '(204 -29) 1 1 0 )
(command "insert" "edge" '(204 -28) 1 1 0 )
(command "insert" "edge" '(206 -29) 1 1 0 )
(command "layer" "m" "Res" "" )
(command "insert" "Res" '(76 -21) 1 1 0 )
(command "insert" "Res" '(103 -15) 1 1 0 )
(command "insert" "Res" '(77 -24) 1 1 0 )
(command "insert" "Res" '(92 -16) 1 1 0 )
(command "insert" "Res" '(74 -26) 1 1 0 )
(command "insert" "Res" '(47 -28) 1 1 0 )
(command "insert" "Res" '(48 -25) 1 1 0 )
(command "insert" "Res" '(69 -15) 1 1 0 )
(command "insert" "Res" '(43 -20) 1 1 0 )
(command "insert" "Res" '(42 -20) 1 1 0 )
(command "insert" "Res" '(88 -22) 1 1 0 )
(command "insert" "Res" '(79 -18) 1 1 0 )
(command "insert" "Res" '(44 -23) 1 1 0 )
(command "insert" "Res" '(93 -15) 1 1 0 )
(command "insert" "Res" '(45 -22) 1 1 0 )
(command "insert" "Res" '(94 -18) 1 1 0 )
(command "insert" "Res" '(60 -29) 1 1 0 )
(command "insert" "Res" '(87 -23) 1 1 0 )
(command "insert" "Res" '(82 -29) 1 1 0 )
(command "insert" "Res" '(51 -22) 1 1 0 )
(command "insert" "Res" '(73 -26) 1 1 0 )
(command "insert" "Res" '(79 -27) 1 1 0 )
(command "insert" "Res" '(78 -17) 1 1 0 )
(command "insert" "Res" '(49 -28) 1 1 0 )
(command "insert" "Res" '(79 -20) 1 1 0 )
(command "insert" "Res" '(50 -27) 1 1 0 )
(command "insert" "Res" '(77 -17) 1 1 0 )
(command "insert" "Res" '(101 -20) 1 1 0 )
(command "insert" "Res" '(91 -17) 1 1 0 )
(command "insert" "Res" '(113 -12) 1 1 0 )
(command "insert" "Res" '(103 -17) 1 1 0 )
(command "insert" "Res" '(89 -24) 1 1 0 )
(command "insert" "Res" '(46 -23) 1 1 0 )
(command "insert" "Res" '(47 -22) 1 1 0 )
(command "insert" "Res" '(106 -17) 1 1 0 )
(command "insert" "Res" '(83 -29) 1 1 0 )
(command "insert" "Res" '(88 -21) 1 1 0 )
(command "insert" "Res" '(70 -16) 1 1 0 )
(command "insert" "Res" '(106 -15) 1 1 0 )
(command "insert" "Res" '(80 -22) 1 1 0 )
(command "insert" "Res" '(104 -19) 1 1 0 )
(command "insert" "Res" '(107 -14) 1 1 0 )
(command "insert" "Res" '(80 -25) 1 1 0 )
(command "insert" "Res" '(86 -28) 1 1 0 )
(command "insert" "Res" '(85 -12) 1 1 0 )
(command "insert" "Res" '(54 -23) 1 1 0 )
(command "insert" "Res" '(87 -25) 1 1 0 )
(command "insert" "Res" '(111 -12) 1 1 0 )
(command "insert" "Res" '(75 -16) 1 1 0 )
(command "insert" "Res" '(109 -12) 1 1 0 )
(command "insert" "Res" '(73 -14) 1 1 0 )
(command "insert" "Res" '(96 -15) 1 1 0 )
(command "insert" "Res" '(74 -13) 1 1 0 )
(command "insert" "Res" '(78 -24) 1 1 0 )
(command "insert" "Res" '(74 -24) 1 1 0 )
(command "insert" "Res" '(48 -27) 1 1 0 )
(command "insert" "Res" '(79 -29) 1 1 0 )
(command "insert" "Res" '(78 -15) 1 1 0 )
(command "insert" "Res" '(75 -21) 1 1 0 )
(command "insert" "Res" '(49 -26) 1 1 0 )
(command "insert" "Res" '(89 -21) 1 1 0 )
(command "insert" "Res" '(102 -15) 1 1 0 )
(command "insert" "Res" '(76 -22) 1 1 0 )
(command "insert" "Res" '(90 -18) 1 1 0 )
(command "insert" "Res" '(102 -18) 1 1 0 )
(command "insert" "Res" '(92 -17) 1 1 0 )
(command "insert" "Res" '(93 -20) 1 1 0 )
(command "insert" "Res" '(43 -23) 1 1 0 )
(command "insert" "Res" '(42 -21) 1 1 0 )
(command "insert" "Res" '(106 -16) 1 1 0 )
(command "insert" "Res" '(68 -21) 1 1 0 )
(command "insert" "Res" '(45 -21) 1 1 0 )
(command "insert" "Res" '(84 -16) 1 1 0 )
(command "insert" "Res" '(80 -16) 1 1 0 )
(command "insert" "Res" '(80 -19) 1 1 0 )
(command "insert" "Res" '(81 -29) 1 1 0 )
(command "insert" "Res" '(87 -22) 1 1 0 )
(command "insert" "Res" '(82 -26) 1 1 0 )
(command "insert" "Res" '(62 -28) 1 1 0 )
(command "insert" "Res" '(75 -17) 1 1 0 )
(command "insert" "Res" '(78 -16) 1 1 0 )
(command "insert" "Res" '(73 -25) 1 1 0 )
(command "insert" "Res" '(79 -26) 1 1 0 )
(command "insert" "Res" '(78 -22) 1 1 0 )
(command "insert" "Res" '(64 -21) 1 1 0 )
(command "insert" "Res" '(79 -23) 1 1 0 )
(command "insert" "Res" '(100 -18) 1 1 0 )
(command "insert" "Res" '(77 -16) 1 1 0 )
(command "insert" "Res" '(76 -24) 1 1 0 )
(command "insert" "Res" '(91 -16) 1 1 0 )
(command "insert" "Res" '(103 -16) 1 1 0 )
(command "insert" "Res" '(59 -22) 1 1 0 )
(command "insert" "Res" '(91 -18) 1 1 0 )
(command "insert" "Res" '(83 -28) 1 1 0 )
(command "insert" "Res" '(105 -15) 1 1 0 )
(command "insert" "Res" '(94 -20) 1 1 0 )
(command "insert" "Res" '(58 -22) 1 1 0 )
(command "insert" "Res" '(106 -12) 1 1 0 )
(command "insert" "Res" '(80 -23) 1 1 0 )
(command "insert" "Res" '(95 -17) 1 1 0 )
(command "insert" "Res" '(60 -21) 1 1 0 )
(command "insert" "Res" '(105 -17) 1 1 0 )
(command "insert" "Res" '(86 -29) 1 1 0 )
(command "insert" "Res" '(110 -14) 1 1 0 )
(command "insert" "Res" '(81 -27) 1 1 0 )
(command "insert" "Res" '(87 -24) 1 1 0 )
(command "insert" "Res" '(98 -16) 1 1 0 )
(command "insert" "Res" '(62 -26) 1 1 0 )
(command "insert" "Res" '(89 -25) 1 1 0 )
(command "insert" "Res" '(100 -19) 1 1 0 )
(command "insert" "Res" '(78 -25) 1 1 0 )
(command "insert" "Res" '(74 -25) 1 1 0 )
(command "insert" "Res" '(48 -28) 1 1 0 )
(command "insert" "Res" '(88 -25) 1 1 0 )
(command "insert" "Res" '(75 -20) 1 1 0 )
(command "insert" "Res" '(99 -19) 1 1 0 )
(command "insert" "Res" '(76 -23) 1 1 0 )
(command "insert" "Res" '(100 -20) 1 1 0 )
(command "insert" "Res" '(90 -19) 1 1 0 )
(command "insert" "Res" '(112 -12) 1 1 0 )
(command "insert" "Res" '(77 -22) 1 1 0 )
(command "insert" "Res" '(92 -18) 1 1 0 )
(command "insert" "Res" '(93 -19) 1 1 0 )
(command "insert" "Res" '(91 -15) 1 1 0 )
(command "insert" "Res" '(43 -22) 1 1 0 )
(command "insert" "Res" '(67 -21) 1 1 0 )
(command "insert" "Res" '(68 -22) 1 1 0 )
(command "insert" "Res" '(70 -17) 1 1 0 )
(command "insert" "Res" '(69 -23) 1 1 0 )
(command "insert" "Res" '(84 -17) 1 1 0 )
(command "insert" "Res" '(42 -18) 1 1 0 )
(command "insert" "Res" '(80 -17) 1 1 0 )
(command "insert" "Res" '(86 -20) 1 1 0 )
(command "insert" "Res" '(85 -20) 1 1 0 )
(command "insert" "Res" '(84 -12) 1 1 0 )
(command "insert" "Res" '(81 -28) 1 1 0 )
(command "insert" "Res" '(86 -27) 1 1 0 )
(command "insert" "Res" '(108 -12) 1 1 0 )
(command "insert" "Res" '(82 -27) 1 1 0 )
(command "insert" "Res" '(97 -17) 1 1 0 )
(command "insert" "Res" '(62 -29) 1 1 0 )
(command "insert" "Res" '(86 -14) 1 1 0 )
(command "insert" "Res" '(50 -24) 1 1 0 )
(command "insert" "Res" '(73 -24) 1 1 0 )
(command "insert" "Res" '(63 -21) 1 1 0 )
(command "insert" "Res" '(78 -23) 1 1 0 )
(command "insert" "Res" '(64 -22) 1 1 0 )
(command "insert" "Res" '(79 -22) 1 1 0 )
(command "insert" "Res" '(88 -24) 1 1 0 )
(command "insert" "Res" '(50 -25) 1 1 0 )
(command "insert" "Res" '(65 -23) 1 1 0 )
(command "insert" "Res" '(77 -15) 1 1 0 )
(command "insert" "Res" '(101 -18) 1 1 0 )
(command "insert" "Res" '(91 -19) 1 1 0 )
(command "insert" "Res" '(61 -21) 1 1 0 )
(command "insert" "Res" '(54 -21) 1 1 0 )
(command "insert" "Res" '(103 -19) 1 1 0 )
(command "insert" "Res" '(92 -20) 1 1 0 )
(command "insert" "Res" '(46 -21) 1 1 0 )
(command "insert" "Res" '(101 -19) 1 1 0 )
(command "insert" "Res" '(56 -21) 1 1 0 )
(command "insert" "Res" '(104 -15) 1 1 0 )
(command "insert" "Res" '(66 -23) 1 1 0 )
(command "insert" "Res" '(105 -14) 1 1 0 )
(command "insert" "Res" '(69 -16) 1 1 0 )
(command "insert" "Res" '(59 -21) 1 1 0 )
(command "insert" "Res" '(58 -23) 1 1 0 )
(command "insert" "Res" '(106 -13) 1 1 0 )
(command "insert" "Res" '(95 -16) 1 1 0 )
(command "insert" "Res" '(85 -29) 1 1 0 )
(command "insert" "Res" '(80 -27) 1 1 0 )
(command "insert" "Res" '(86 -18) 1 1 0 )
(command "insert" "Res" '(85 -19) 1 1 0 )
(command "insert" "Res" '(81 -26) 1 1 0 )
(command "insert" "Res" '(111 -14) 1 1 0 )
(command "insert" "Res" '(60 -23) 1 1 0 )
(command "insert" "Res" '(98 -17) 1 1 0 )
(command "insert" "Res" '(62 -27) 1 1 0 )
(command "insert" "Res" '(52 -21) 1 1 0 )
(command "insert" "Res" '(48 -29) 1 1 0 )
(command "insert" "Res" '(88 -26) 1 1 0 )
(command "insert" "Res" '(75 -23) 1 1 0 )
(command "insert" "Res" '(49 -24) 1 1 0 )
(command "insert" "Res" '(55 -21) 1 1 0 )
(command "insert" "Res" '(76 -16) 1 1 0 )
(command "insert" "Res" '(75 -24) 1 1 0 )
(command "insert" "Res" '(90 -16) 1 1 0 )
(command "insert" "Res" '(112 -13) 1 1 0 )
(command "insert" "Res" '(102 -16) 1 1 0 )
(command "insert" "Res" '(92 -19) 1 1 0 )
(command "insert" "Res" '(75 -25) 1 1 0 )
(command "insert" "Res" '(90 -15) 1 1 0 )
(command "insert" "Res" '(61 -22) 1 1 0 )
(command "insert" "Res" '(93 -18) 1 1 0 )
(command "insert" "Res" '(102 -20) 1 1 0 )
(command "insert" "Res" '(42 -19) 1 1 0 )
(command "insert" "Res" '(44 -18) 1 1 0 )
(command "insert" "Res" '(68 -23) 1 1 0 )
(command "insert" "Res" '(83 -25) 1 1 0 )
(command "insert" "Res" '(80 -15) 1 1 0 )
(command "insert" "Res" '(70 -22) 1 1 0 )
(command "insert" "Res" '(69 -22) 1 1 0 )
(command "insert" "Res" '(84 -18) 1 1 0 )
(command "insert" "Res" '(71 -23) 1 1 0 )
(command "insert" "Res" '(60 -24) 1 1 0 )
(command "insert" "Res" '(84 -13) 1 1 0 )
(command "insert" "Res" '(61 -29) 1 1 0 )
(command "insert" "Res" '(108 -13) 1 1 0 )
(command "insert" "Res" '(82 -24) 1 1 0 )
(command "insert" "Res" '(97 -16) 1 1 0 )
(command "insert" "Res" '(86 -15) 1 1 0 )
(command "insert" "Res" '(60 -22) 1 1 0 )
(command "insert" "Res" '(99 -18) 1 1 0 )
(command "insert" "Res" '(78 -20) 1 1 0 )
(command "insert" "Res" '(64 -23) 1 1 0 )
(command "insert" "Res" '(79 -17) 1 1 0 )
(command "insert" "Res" '(76 -15) 1 1 0 )
(command "insert" "Res" '(50 -22) 1 1 0 )
(command "insert" "Res" '(65 -22) 1 1 0 )
(command "insert" "Res" '(76 -26) 1 1 0 )
(command "insert" "Res" '(66 -21) 1 1 0 )
(command "insert" "Res" '(54 -22) 1 1 0 )
(command "insert" "Res" '(105 -16) 1 1 0 )
(command "insert" "Res" '(103 -18) 1 1 0 )
(command "insert" "Res" '(78 -19) 1 1 0 )
(command "insert" "Res" '(61 -23) 1 1 0 )
(command "insert" "Res" '(69 -17) 1 1 0 )
(command "insert" "Res" '(56 -22) 1 1 0 )
(command "insert" "Res" '(80 -18) 1 1 0 )
(command "insert" "Res" '(43 -19) 1 1 0 )
(command "insert" "Res" '(57 -23) 1 1 0 )
(command "insert" "Res" '(105 -13) 1 1 0 )
(command "insert" "Res" '(66 -22) 1 1 0 )
(command "insert" "Res" '(44 -20) 1 1 0 )
(command "insert" "Res" '(71 -21) 1 1 0 )
(command "insert" "Res" '(92 -15) 1 1 0 )
(command "insert" "Res" '(95 -19) 1 1 0 )
(command "insert" "Res" '(85 -28) 1 1 0 )
(command "insert" "Res" '(84 -20) 1 1 0 )
(command "insert" "Res" '(80 -28) 1 1 0 )
(command "insert" "Res" '(86 -19) 1 1 0 )
(command "insert" "Res" '(110 -12) 1 1 0 )
(command "insert" "Res" '(81 -25) 1 1 0 )
(command "insert" "Res" '(87 -26) 1 1 0 )
(command "insert" "Res" '(104 -20) 1 1 0 )
(command "insert" "Res" '(62 -24) 1 1 0 )
(command "insert" "Res" '(51 -21) 1 1 0 )
(command "insert" "Res" '(72 -24) 1 1 0 )
(command "insert" "Res" '(52 -22) 1 1 0 )
(command "insert" "Res" '(78 -18) 1 1 0 )
(command "insert" "Res" '(50 -29) 1 1 0 )
(command "insert" "Res" '(75 -22) 1 1 0 )
(command "insert" "Res" '(89 -26) 1 1 0 )
(command "insert" "Res" '(76 -17) 1 1 0 )
(command "insert" "Res" '(73 -12) 1 1 0 )
(command "insert" "Res" '(90 -17) 1 1 0 )
(command "insert" "Res" '(112 -14) 1 1 0 )
(command "insert" "Res" '(102 -17) 1 1 0 )
(command "insert" "Res" '(46 -29) 1 1 0 )
(command "insert" "Res" '(80 -26) 1 1 0 )
(command "insert" "Res" '(103 -20) 1 1 0 )
(command "insert" "Res" '(93 -17) 1 1 0 )
(command "insert" "Res" '(53 -23) 1 1 0 )
(command "insert" "Res" '(61 -24) 1 1 0 )
(command "insert" "Res" '(67 -23) 1 1 0 )
(command "insert" "Res" '(47 -21) 1 1 0 )
(command "insert" "Res" '(95 -15) 1 1 0 )
(command "insert" "Res" '(44 -19) 1 1 0 )
(command "insert" "Res" '(83 -24) 1 1 0 )
(command "insert" "Res" '(70 -23) 1 1 0 )
(command "insert" "Res" '(94 -16) 1 1 0 )
(command "insert" "Res" '(84 -19) 1 1 0 )
(command "insert" "Res" '(71 -22) 1 1 0 )
(command "insert" "Res" '(104 -16) 1 1 0 )
(command "insert" "Res" '(85 -18) 1 1 0 )
(command "insert" "Res" '(84 -14) 1 1 0 )
(command "insert" "Res" '(107 -13) 1 1 0 )
(command "insert" "Res" '(61 -28) 1 1 0 )
(command "insert" "Res" '(85 -15) 1 1 0 )
(command "insert" "Res" '(108 -14) 1 1 0 )
(command "insert" "Res" '(82 -25) 1 1 0 )
(command "insert" "Res" '(72 -12) 1 1 0 )
(command "insert" "Res" '(86 -12) 1 1 0 )
(command "insert" "Res" '(45 -28) 1 1 0 )
(command "insert" "Res" '(62 -22) 1 1 0 )
(command "insert" "Res" '(45 -27) 1 1 0 )
(command "insert" "Res" '(74 -14) 1 1 0 )
(command "insert" "Res" '(48 -21) 1 1 0 )
(command "insert" "Res" '(63 -23) 1 1 0 )
(command "insert" "Res" '(78 -21) 1 1 0 )
(command "insert" "Res" '(75 -15) 1 1 0 )
(command "insert" "Res" '(48 -24) 1 1 0 )
(command "insert" "Res" '(79 -16) 1 1 0 )
(command "insert" "Res" '(50 -28) 1 1 0 )
(command "insert" "Res" '(50 -23) 1 1 0 )
(command "insert" "Res" '(65 -21) 1 1 0 )
(command "insert" "Res" '(73 -13) 1 1 0 )
(command "insert" "Res" '(77 -26) 1 1 0 )
(command "insert" "Res" '(85 -17) 1 1 0 )
(command "insert" "Res" '(46 -27) 1 1 0 )
(command "insert" "Res" '(56 -23) 1 1 0 )
(command "insert" "Res" '(61 -25) 1 1 0 )
(command "insert" "Res" '(43 -18) 1 1 0 )
(command "insert" "Res" '(42 -22) 1 1 0 )
(command "insert" "Res" '(57 -22) 1 1 0 )
(command "insert" "Res" '(77 -20) 1 1 0 )
(command "insert" "Res" '(105 -12) 1 1 0 )
(command "insert" "Res" '(44 -21) 1 1 0 )
(command "insert" "Res" '(59 -23) 1 1 0 )
(command "insert" "Res" '(58 -21) 1 1 0 )
(command "insert" "Res" '(71 -15) 1 1 0 )
(command "insert" "Res" '(95 -18) 1 1 0 )
(command "insert" "Res" '(85 -27) 1 1 0 )
(command "insert" "Res" '(80 -29) 1 1 0 )
(command "insert" "Res" '(86 -16) 1 1 0 )
(command "insert" "Res" '(110 -13) 1 1 0 )
(command "insert" "Res" '(81 -24) 1 1 0 )
(command "insert" "Res" '(87 -21) 1 1 0 )
(command "insert" "Res" '(71 -16) 1 1 0 )
(command "insert" "Res" '(62 -25) 1 1 0 )
(command "insert" "Res" '(45 -29) 1 1 0 )
(command "insert" "Res" '(72 -25) 1 1 0 )
(command "insert" "Res" '(78 -28) 1 1 0 )
(command "insert" "Res" '(52 -23) 1 1 0 )
(command "insert" "Res" '(85 -16) 1 1 0 )
(command "insert" "Res" '(79 -25) 1 1 0 )
(command "insert" "Res" '(53 -22) 1 1 0 )
(command "insert" "Res" '(99 -20) 1 1 0 )
(command "insert" "Res" '(55 -23) 1 1 0 )
(command "insert" "Res" '(76 -18) 1 1 0 )
(command "insert" "Res" '(75 -26) 1 1 0 )
(command "insert" "Res" '(77 -19) 1 1 0 )
(command "insert" "Res" '(113 -14) 1 1 0 )
(command "insert" "Res" '(93 -16) 1 1 0 )
(command "insert" "Res" '(79 -28) 1 1 0 )
(command "insert" "Res" '(94 -15) 1 1 0 )
(command "insert" "Res" '(62 -21) 1 1 0 )
(command "insert" "Res" '(67 -22) 1 1 0 )
(command "insert" "Res" '(83 -27) 1 1 0 )
(command "insert" "Res" '(77 -21) 1 1 0 )
(command "insert" "Res" '(50 -21) 1 1 0 )
(command "insert" "Res" '(94 -17) 1 1 0 )
(command "insert" "Res" '(84 -28) 1 1 0 )
(command "insert" "Res" '(80 -20) 1 1 0 )
(command "insert" "Res" '(95 -20) 1 1 0 )
(command "insert" "Res" '(60 -26) 1 1 0 )
(command "insert" "Res" '(84 -15) 1 1 0 )
(command "insert" "Res" '(107 -12) 1 1 0 )
(command "insert" "Res" '(47 -27) 1 1 0 )
(command "insert" "Res" '(106 -14) 1 1 0 )
(command "insert" "Res" '(49 -25) 1 1 0 )
(command "insert" "Res" '(85 -14) 1 1 0 )
(command "insert" "Res" '(107 -17) 1 1 0 )
(command "insert" "Res" '(72 -13) 1 1 0 )
(command "insert" "Res" '(86 -13) 1 1 0 )
(command "insert" "Res" '(46 -28) 1 1 0 )
(command "insert" "Res" '(109 -14) 1 1 0 )
(command "insert" "Res" '(71 -17) 1 1 0 )
(command "insert" "Res" '(62 -23) 1 1 0 )
(command "insert" "Res" '(104 -17) 1 1 0 )
(command "insert" "Res" '(63 -22) 1 1 0 )
(command "insert" "Res" '(78 -26) 1 1 0 )
(command "insert" "Res" '(49 -23) 1 1 0 )
(command "insert" "Res" '(98 -15) 1 1 0 )
(command "insert" "Res" '(79 -19) 1 1 0 )
(command "insert" "Res" '(75 -19) 1 1 0 )
(command "insert" "Res" '(89 -23) 1 1 0 )
(command "insert" "Res" '(76 -20) 1 1 0 )
(command "insert" "Res" '(91 -20) 1 1 0 )
(command "insert" "Res" '(90 -20) 1 1 0 )
(command "insert" "Res" '(49 -21) 1 1 0 )
(command "insert" "Res" '(77 -25) 1 1 0 )
(command "insert" "Res" '(47 -29) 1 1 0 )
(command "insert" "Res" '(43 -21) 1 1 0 )
(command "insert" "Res" '(42 -23) 1 1 0 )
(command "insert" "Res" '(57 -21) 1 1 0 )
(command "insert" "Res" '(61 -27) 1 1 0 )
(command "insert" "Res" '(70 -15) 1 1 0 )
(command "insert" "Res" '(44 -22) 1 1 0 )
(command "insert" "Res" '(84 -27) 1 1 0 )
(command "insert" "Res" '(69 -21) 1 1 0 )
(command "insert" "Res" '(102 -19) 1 1 0 )
(command "insert" "Res" '(45 -23) 1 1 0 )
(command "insert" "Res" '(86 -17) 1 1 0 )
(command "insert" "Res" '(60 -28) 1 1 0 )
(command "insert" "Res" '(96 -17) 1 1 0 )
(command "insert" "Res" '(82 -28) 1 1 0 )
(command "insert" "Res" '(51 -23) 1 1 0 )
(command "insert" "Res" '(72 -26) 1 1 0 )
(command "insert" "Res" '(78 -29) 1 1 0 )
(command "insert" "Res" '(79 -24) 1 1 0 )
(command "insert" "Res" '(53 -21) 1 1 0 )
(command "insert" "Res" '(60 -25) 1 1 0 )
(command "insert" "Res" '(55 -22) 1 1 0 )
(command "insert" "Res" '(79 -21) 1 1 0 )
(command "insert" "Res" '(76 -19) 1 1 0 )
(command "insert" "Res" '(50 -26) 1 1 0 )
(command "insert" "Res" '(77 -18) 1 1 0 )
(command "insert" "Res" '(113 -13) 1 1 0 )
(command "insert" "Res" '(46 -22) 1 1 0 )
(command "insert" "Res" '(47 -23) 1 1 0 )
(command "insert" "Res" '(83 -26) 1 1 0 )
(command "insert" "Res" '(70 -21) 1 1 0 )
(command "insert" "Res" '(84 -29) 1 1 0 )
(command "insert" "Res" '(94 -19) 1 1 0 )
(command "insert" "Res" '(77 -23) 1 1 0 )
(command "insert" "Res" '(80 -21) 1 1 0 )
(command "insert" "Res" '(104 -18) 1 1 0 )
(command "insert" "Res" '(60 -27) 1 1 0 )
(command "insert" "Res" '(96 -16) 1 1 0 )
(command "insert" "Res" '(107 -15) 1 1 0 )
(command "insert" "Res" '(80 -24) 1 1 0 )
(command "insert" "Res" '(61 -26) 1 1 0 )
(command "insert" "Res" '(85 -13) 1 1 0 )
(command "insert" "Res" '(107 -16) 1 1 0 )
(command "insert" "Res" '(72 -14) 1 1 0 )
(command "insert" "Res" '(111 -13) 1 1 0 )
(command "insert" "Res" '(109 -13) 1 1 0 )
(command "insert" "Res" '(48 -22) 1 1 0 )
(command "insert" "Res" '(76 -25) 1 1 0 )
(command "insert" "Res" '(74 -12) 1 1 0 )
(command "insert" "Res" '(48 -23) 1 1 0 )
(command "insert" "Res" '(97 -15) 1 1 0 )
(command "insert" "Res" '(78 -27) 1 1 0 )
(command "insert" "Res" '(49 -29) 1 1 0 )
(command "insert" "Res" '(49 -22) 1 1 0 )
(command "insert" "Res" '(48 -26) 1 1 0 )
(command "insert" "Res" '(88 -23) 1 1 0 )
(command "insert" "Res" '(75 -18) 1 1 0 )
(command "insert" "Res" '(49 -27) 1 1 0 )
(command "insert" "Res" '(89 -22) 1 1 0 )
(command "insert" "Res" '(79 -15) 1 1 0 )
(command "layer" "m" "ped" "" )
(command "insert" "ped" '(295 -99) 1 1 0 )
(command "insert" "ped" '(299 -100) 1 1 0 )
(command "insert" "ped" '(298 -100) 1 1 0 )
(command "insert" "ped" '(299 -105) 1 1 0 )
(command "insert" "ped" '(299 -99) 1 1 0 )
(command "insert" "ped" '(297 -106) 1 1 0 )
(command "insert" "ped" '(297 -102) 1 1 0 )
(command "insert" "ped" '(299 -103) 1 1 0 )
(command "insert" "ped" '(296 -99) 1 1 0 )
(command "insert" "ped" '(298 -106) 1 1 0 )
(command "insert" "ped" '(299 -104) 1 1 0 )
(command "insert" "ped" '(298 -99) 1 1 0 )
(command "insert" "ped" '(297 -105) 1 1 0 )
(command "insert" "ped" '(294 -99) 1 1 0 )
(command "insert" "ped" '(297 -101) 1 1 0 )
(command "insert" "ped" '(299 -102) 1 1 0 )
(command "insert" "ped" '(296 -100) 1 1 0 )
(command "insert" "ped" '(294 -100) 1 1 0 )
(command "insert" "ped" '(297 -99) 1 1 0 )
(command "insert" "ped" '(298 -107) 1 1 0 )
(command "insert" "ped" '(299 -107) 1 1 0 )
(command "insert" "ped" '(297 -104) 1 1 0 )
(command "insert" "ped" '(298 -102) 1 1 0 )
(command "insert" "ped" '(298 -101) 1 1 0 )
(command "insert" "ped" '(295 -101) 1 1 0 )
(command "insert" "ped" '(297 -100) 1 1 0 )
(command "insert" "ped" '(296 -101) 1 1 0 )
(command "insert" "ped" '(294 -101) 1 1 0 )
(command "insert" "ped" '(298 -104) 1 1 0 )
(command "insert" "ped" '(299 -106) 1 1 0 )
(command "insert" "ped" '(299 -101) 1 1 0 )
(command "insert" "ped" '(298 -103) 1 1 0 )
(command "insert" "ped" '(295 -100) 1 1 0 )
(command "insert" "ped" '(297 -107) 1 1 0 )
(command "insert" "ped" '(298 -105) 1 1 0 )
(command "insert" "ped" '(297 -103) 1 1 0 )
(command "layer" "m" "Res" "" )
(command "insert" "Res" '(286 -53) 1 1 0 )
(command "insert" "Res" '(285 -51) 1 1 0 )
(command "insert" "Res" '(286 -52) 1 1 0 )
(command "insert" "Res" '(285 -52) 1 1 0 )
(command "insert" "Res" '(285 -53) 1 1 0 )
(command "insert" "Res" '(287 -52) 1 1 0 )
(command "insert" "Res" '(287 -51) 1 1 0 )
(command "insert" "Res" '(286 -51) 1 1 0 )
(command "insert" "Res" '(287 -53) 1 1 0 )
(command "layer" "m" "ped" "" )
(command "insert" "ped" '(216 -73) 1 1 0 )
(command "insert" "ped" '(217 -74) 1 1 0 )
(command "insert" "ped" '(216 -72) 1 1 0 )
(command "insert" "ped" '(218 -73) 1 1 0 )
(command "insert" "ped" '(217 -73) 1 1 0 )
(command "insert" "ped" '(218 -72) 1 1 0 )
(command "insert" "ped" '(218 -74) 1 1 0 )
(command "insert" "ped" '(217 -72) 1 1 0 )
(command "insert" "ped" '(216 -74) 1 1 0 )
(command "layer" "m" "Res" "" )
(command "insert" "Res" '(187 -55) 1 1 0 )
(command "insert" "Res" '(183 -63) 1 1 0 )
(command "insert" "Res" '(187 -56) 1 1 0 )
(command "insert" "Res" '(178 -56) 1 1 0 )
(command "insert" "Res" '(193 -59) 1 1 0 )
(command "insert" "Res" '(184 -69) 1 1 0 )
(command "insert" "Res" '(179 -54) 1 1 0 )
(command "insert" "Res" '(190 -57) 1 1 0 )
(command "insert" "Res" '(185 -60) 1 1 0 )
(command "insert" "Res" '(192 -58) 1 1 0 )
(command "insert" "Res" '(186 -54) 1 1 0 )
(command "insert" "Res" '(189 -56) 1 1 0 )
(command "insert" "Res" '(184 -62) 1 1 0 )
(command "insert" "Res" '(190 -58) 1 1 0 )
(command "insert" "Res" '(180 -54) 1 1 0 )
(command "insert" "Res" '(185 -63) 1 1 0 )
(command "insert" "Res" '(200 -54) 1 1 0 )
(command "insert" "Res" '(181 -55) 1 1 0 )
(command "insert" "Res" '(177 -57) 1 1 0 )
(command "insert" "Res" '(194 -59) 1 1 0 )
(command "insert" "Res" '(189 -59) 1 1 0 )
(command "insert" "Res" '(180 -56) 1 1 0 )
(command "insert" "Res" '(185 -69) 1 1 0 )
(command "insert" "Res" '(181 -66) 1 1 0 )
(command "insert" "Res" '(181 -61) 1 1 0 )
(command "insert" "Res" '(192 -57) 1 1 0 )
(command "insert" "Res" '(191 -54) 1 1 0 )
(command "insert" "Res" '(198 -55) 1 1 0 )
(command "insert" "Res" '(177 -55) 1 1 0 )
(command "insert" "Res" '(199 -54) 1 1 0 )
(command "insert" "Res" '(190 -55) 1 1 0 )
(command "insert" "Res" '(179 -58) 1 1 0 )
(command "insert" "Res" '(180 -61) 1 1 0 )
(command "insert" "Res" '(196 -58) 1 1 0 )
(command "insert" "Res" '(185 -64) 1 1 0 )
(command "insert" "Res" '(184 -56) 1 1 0 )
(command "insert" "Res" '(191 -56) 1 1 0 )
(command "insert" "Res" '(197 -59) 1 1 0 )
(command "insert" "Res" '(183 -70) 1 1 0 )
(command "insert" "Res" '(187 -54) 1 1 0 )
(command "insert" "Res" '(183 -62) 1 1 0 )
(command "insert" "Res" '(178 -57) 1 1 0 )
(command "insert" "Res" '(193 -58) 1 1 0 )
(command "insert" "Res" '(184 -70) 1 1 0 )
(command "insert" "Res" '(182 -68) 1 1 0 )
(command "insert" "Res" '(179 -57) 1 1 0 )
(command "insert" "Res" '(186 -56) 1 1 0 )
(command "insert" "Res" '(183 -69) 1 1 0 )
(command "insert" "Res" '(182 -56) 1 1 0 )
(command "insert" "Res" '(186 -55) 1 1 0 )
(command "insert" "Res" '(183 -61) 1 1 0 )
(command "insert" "Res" '(199 -56) 1 1 0 )
(command "insert" "Res" '(188 -54) 1 1 0 )
(command "insert" "Res" '(178 -58) 1 1 0 )
(command "insert" "Res" '(189 -55) 1 1 0 )
(command "insert" "Res" '(190 -54) 1 1 0 )
(command "insert" "Res" '(195 -59) 1 1 0 )
(command "insert" "Res" '(184 -63) 1 1 0 )
(command "insert" "Res" '(190 -59) 1 1 0 )
(command "insert" "Res" '(180 -55) 1 1 0 )
(command "insert" "Res" '(185 -62) 1 1 0 )
(command "insert" "Res" '(200 -55) 1 1 0 )
(command "insert" "Res" '(182 -54) 1 1 0 )
(command "insert" "Res" '(181 -54) 1 1 0 )
(command "insert" "Res" '(183 -55) 1 1 0 )
(command "insert" "Res" '(177 -56) 1 1 0 )
(command "insert" "Res" '(184 -64) 1 1 0 )
(command "insert" "Res" '(189 -58) 1 1 0 )
(command "insert" "Res" '(182 -66) 1 1 0 )
(command "insert" "Res" '(184 -60) 1 1 0 )
(command "insert" "Res" '(181 -60) 1 1 0 )
(command "insert" "Res" '(177 -54) 1 1 0 )
(command "insert" "Res" '(177 -59) 1 1 0 )
(command "insert" "Res" '(188 -56) 1 1 0 )
(command "insert" "Res" '(180 -62) 1 1 0 )
(command "insert" "Res" '(196 -59) 1 1 0 )
(command "insert" "Res" '(185 -71) 1 1 0 )
(command "insert" "Res" '(191 -59) 1 1 0 )
(command "insert" "Res" '(181 -68) 1 1 0 )
(command "insert" "Res" '(197 -58) 1 1 0 )
(command "insert" "Res" '(183 -65) 1 1 0 )
(command "insert" "Res" '(182 -60) 1 1 0 )
(command "insert" "Res" '(178 -54) 1 1 0 )
(command "insert" "Res" '(193 -57) 1 1 0 )
(command "insert" "Res" '(184 -71) 1 1 0 )
(command "insert" "Res" '(180 -66) 1 1 0 )
(command "insert" "Res" '(179 -56) 1 1 0 )
(command "insert" "Res" '(184 -54) 1 1 0 )
(command "insert" "Res" '(185 -55) 1 1 0 )
(command "insert" "Res" '(183 -60) 1 1 0 )
(command "insert" "Res" '(188 -55) 1 1 0 )
(command "insert" "Res" '(178 -59) 1 1 0 )
(command "insert" "Res" '(189 -54) 1 1 0 )
(command "insert" "Res" '(179 -55) 1 1 0 )
(command "insert" "Res" '(195 -58) 1 1 0 )
(command "insert" "Res" '(190 -56) 1 1 0 )
(command "insert" "Res" '(181 -56) 1 1 0 )
(command "insert" "Res" '(185 -61) 1 1 0 )
(command "insert" "Res" '(200 -56) 1 1 0 )
(command "insert" "Res" '(182 -55) 1 1 0 )
(command "insert" "Res" '(183 -54) 1 1 0 )
(command "insert" "Res" '(194 -57) 1 1 0 )
(command "insert" "Res" '(184 -65) 1 1 0 )
(command "insert" "Res" '(189 -57) 1 1 0 )
(command "insert" "Res" '(180 -68) 1 1 0 )
(command "insert" "Res" '(182 -67) 1 1 0 )
(command "insert" "Res" '(195 -57) 1 1 0 )
(command "insert" "Res" '(184 -61) 1 1 0 )
(command "insert" "Res" '(185 -56) 1 1 0 )
(command "insert" "Res" '(198 -56) 1 1 0 )
(command "insert" "Res" '(177 -58) 1 1 0 )
(command "insert" "Res" '(194 -58) 1 1 0 )
(command "insert" "Res" '(185 -70) 1 1 0 )
(command "insert" "Res" '(192 -59) 1 1 0 )
(command "insert" "Res" '(191 -58) 1 1 0 )
(command "insert" "Res" '(181 -67) 1 1 0 )
(command "insert" "Res" '(181 -62) 1 1 0 )
(command "insert" "Res" '(197 -57) 1 1 0 )
(command "insert" "Res" '(183 -64) 1 1 0 )
(command "insert" "Res" '(191 -55) 1 1 0 )
(command "insert" "Res" '(182 -61) 1 1 0 )
(command "insert" "Res" '(198 -54) 1 1 0 )
(command "insert" "Res" '(183 -56) 1 1 0 )
(command "insert" "Res" '(199 -55) 1 1 0 )
(command "insert" "Res" '(178 -55) 1 1 0 )
(command "insert" "Res" '(180 -67) 1 1 0 )
(command "insert" "Res" '(179 -59) 1 1 0 )
(command "insert" "Res" '(180 -60) 1 1 0 )
(command "insert" "Res" '(196 -57) 1 1 0 )
(command "insert" "Res" '(185 -65) 1 1 0 )
(command "insert" "Res" '(184 -55) 1 1 0 )
(command "insert" "Res" '(191 -57) 1 1 0 )
(command "insert" "Res" '(185 -54) 1 1 0 )
(command "insert" "Res" '(183 -71) 1 1 0 )
(command "insert" "Res" '(182 -62) 1 1 0 )
(command "layer" "m" "alley" "" )
(command "insert" "alley" '(119 -42) 1 1 0 )
(command "insert" "alley" '(123 -44) 1 1 0 )
(command "insert" "alley" '(121 -44) 1 1 0 )
(command "insert" "alley" '(116 -42) 1 1 0 )
(command "insert" "alley" '(122 -43) 1 1 0 )
(command "insert" "alley" '(123 -43) 1 1 0 )
(command "insert" "alley" '(117 -43) 1 1 0 )
(command "insert" "alley" '(118 -43) 1 1 0 )
(command "insert" "alley" '(114 -40) 1 1 0 )
(command "insert" "alley" '(124 -44) 1 1 0 )
(command "insert" "alley" '(111 -44) 1 1 0 )
(command "insert" "alley" '(117 -44) 1 1 0 )
(command "insert" "alley" '(115 -41) 1 1 0 )
(command "insert" "alley" '(112 -42) 1 1 0 )
(command "insert" "alley" '(118 -44) 1 1 0 )
(command "insert" "alley" '(113 -43) 1 1 0 )
(command "insert" "alley" '(123 -42) 1 1 0 )
(command "insert" "alley" '(116 -43) 1 1 0 )
(command "insert" "alley" '(111 -43) 1 1 0 )
(command "insert" "alley" '(125 -44) 1 1 0 )
(command "insert" "alley" '(115 -44) 1 1 0 )
(command "insert" "alley" '(114 -41) 1 1 0 )
(command "insert" "alley" '(117 -42) 1 1 0 )
(command "insert" "alley" '(114 -42) 1 1 0 )
(command "insert" "alley" '(114 -44) 1 1 0 )
(command "insert" "alley" '(120 -42) 1 1 0 )
(command "insert" "alley" '(115 -40) 1 1 0 )
(command "insert" "alley" '(112 -43) 1 1 0 )
(command "insert" "alley" '(121 -43) 1 1 0 )
(command "insert" "alley" '(113 -42) 1 1 0 )
(command "insert" "alley" '(124 -42) 1 1 0 )
(command "insert" "alley" '(120 -44) 1 1 0 )
(command "insert" "alley" '(111 -42) 1 1 0 )
(command "insert" "alley" '(125 -43) 1 1 0 )
(command "insert" "alley" '(116 -39) 1 1 0 )
(command "insert" "alley" '(116 -40) 1 1 0 )
(command "insert" "alley" '(119 -44) 1 1 0 )
(command "insert" "alley" '(120 -43) 1 1 0 )
(command "insert" "alley" '(115 -43) 1 1 0 )
(command "insert" "alley" '(112 -44) 1 1 0 )
(command "insert" "alley" '(121 -42) 1 1 0 )
(command "insert" "alley" '(116 -44) 1 1 0 )
(command "insert" "alley" '(124 -43) 1 1 0 )
(command "insert" "alley" '(115 -39) 1 1 0 )
(command "insert" "alley" '(125 -42) 1 1 0 )
(command "insert" "alley" '(122 -44) 1 1 0 )
(command "insert" "alley" '(114 -39) 1 1 0 )
(command "insert" "alley" '(116 -41) 1 1 0 )
(command "insert" "alley" '(113 -44) 1 1 0 )
(command "insert" "alley" '(122 -42) 1 1 0 )
(command "insert" "alley" '(115 -42) 1 1 0 )
(command "insert" "alley" '(118 -42) 1 1 0 )
(command "insert" "alley" '(114 -43) 1 1 0 )
(command "insert" "alley" '(119 -43) 1 1 0 )
(command "layer" "m" "Commmer" "" )
(command "insert" "Commmer" '(162 -48) 1 1 0 )
(command "insert" "Commmer" '(177 -51) 1 1 0 )
(command "insert" "Commmer" '(168 -45) 1 1 0 )
(command "insert" "Commmer" '(163 -45) 1 1 0 )
(command "insert" "Commmer" '(164 -46) 1 1 0 )
(command "insert" "Commmer" '(170 -47) 1 1 0 )
(command "insert" "Commmer" '(168 -51) 1 1 0 )
(command "insert" "Commmer" '(163 -51) 1 1 0 )
(command "insert" "Commmer" '(171 -46) 1 1 0 )
(command "insert" "Commmer" '(169 -50) 1 1 0 )
(command "insert" "Commmer" '(174 -52) 1 1 0 )
(command "insert" "Commmer" '(164 -52) 1 1 0 )
(command "insert" "Commmer" '(180 -49) 1 1 0 )
(command "insert" "Commmer" '(175 -49) 1 1 0 )
(command "insert" "Commmer" '(166 -51) 1 1 0 )
(command "insert" "Commmer" '(182 -52) 1 1 0 )
(command "insert" "Commmer" '(181 -52) 1 1 0 )
(command "insert" "Commmer" '(162 -53) 1 1 0 )
(command "insert" "Commmer" '(162 -47) 1 1 0 )
(command "insert" "Commmer" '(168 -48) 1 1 0 )
(command "insert" "Commmer" '(171 -45) 1 1 0 )
(command "insert" "Commmer" '(167 -52) 1 1 0 )
(command "insert" "Commmer" '(174 -49) 1 1 0 )
(command "insert" "Commmer" '(172 -46) 1 1 0 )
(command "insert" "Commmer" '(175 -52) 1 1 0 )
(command "insert" "Commmer" '(182 -49) 1 1 0 )
(command "insert" "Commmer" '(173 -47) 1 1 0 )
(command "insert" "Commmer" '(177 -52) 1 1 0 )
(command "insert" "Commmer" '(183 -52) 1 1 0 )
(command "insert" "Commmer" '(178 -51) 1 1 0 )
(command "insert" "Commmer" '(164 -51) 1 1 0 )
(command "insert" "Commmer" '(170 -48) 1 1 0 )
(command "insert" "Commmer" '(174 -50) 1 1 0 )
(command "insert" "Commmer" '(165 -50) 1 1 0 )
(command "insert" "Commmer" '(167 -51) 1 1 0 )
(command "insert" "Commmer" '(182 -50) 1 1 0 )
(command "insert" "Commmer" '(173 -50) 1 1 0 )
(command "insert" "Commmer" '(178 -52) 1 1 0 )
(command "insert" "Commmer" '(164 -48) 1 1 0 )
(command "insert" "Commmer" '(170 -53) 1 1 0 )
(command "insert" "Commmer" '(167 -53) 1 1 0 )
(command "insert" "Commmer" '(165 -53) 1 1 0 )
(command "insert" "Commmer" '(181 -48) 1 1 0 )
(command "insert" "Commmer" '(172 -48) 1 1 0 )
(command "insert" "Commmer" '(185 -53) 1 1 0 )
(command "insert" "Commmer" '(176 -51) 1 1 0 )
(command "insert" "Commmer" '(162 -49) 1 1 0 )
(command "insert" "Commmer" '(168 -46) 1 1 0 )
(command "insert" "Commmer" '(169 -47) 1 1 0 )
(command "insert" "Commmer" '(164 -47) 1 1 0 )
(command "insert" "Commmer" '(168 -52) 1 1 0 )
(command "insert" "Commmer" '(163 -50) 1 1 0 )
(command "insert" "Commmer" '(169 -49) 1 1 0 )
(command "insert" "Commmer" '(174 -53) 1 1 0 )
(command "insert" "Commmer" '(164 -53) 1 1 0 )
(command "insert" "Commmer" '(180 -50) 1 1 0 )
(command "insert" "Commmer" '(171 -50) 1 1 0 )
(command "insert" "Commmer" '(184 -52) 1 1 0 )
(command "insert" "Commmer" '(175 -48) 1 1 0 )
(command "insert" "Commmer" '(166 -48) 1 1 0 )
(command "insert" "Commmer" '(182 -53) 1 1 0 )
(command "insert" "Commmer" '(181 -51) 1 1 0 )
(command "insert" "Commmer" '(176 -48) 1 1 0 )
(command "insert" "Commmer" '(162 -50) 1 1 0 )
(command "insert" "Commmer" '(168 -49) 1 1 0 )
(command "insert" "Commmer" '(163 -49) 1 1 0 )
(command "insert" "Commmer" '(179 -52) 1 1 0 )
(command "insert" "Commmer" '(172 -47) 1 1 0 )
(command "insert" "Commmer" '(171 -49) 1 1 0 )
(command "insert" "Commmer" '(173 -46) 1 1 0 )
(command "insert" "Commmer" '(185 -51) 1 1 0 )
(command "insert" "Commmer" '(167 -48) 1 1 0 )
(command "insert" "Commmer" '(179 -51) 1 1 0 )
(command "insert" "Commmer" '(170 -49) 1 1 0 )
(command "insert" "Commmer" '(174 -51) 1 1 0 )
(command "insert" "Commmer" '(165 -49) 1 1 0 )
(command "insert" "Commmer" '(180 -52) 1 1 0 )
(command "insert" "Commmer" '(167 -50) 1 1 0 )
(command "insert" "Commmer" '(182 -51) 1 1 0 )
(command "insert" "Commmer" '(173 -49) 1 1 0 )
(command "insert" "Commmer" '(178 -53) 1 1 0 )
(command "insert" "Commmer" '(173 -45) 1 1 0 )
(command "insert" "Commmer" '(169 -53) 1 1 0 )
(command "insert" "Commmer" '(164 -49) 1 1 0 )
(command "insert" "Commmer" '(170 -50) 1 1 0 )
(command "insert" "Commmer" '(166 -52) 1 1 0 )
(command "insert" "Commmer" '(165 -52) 1 1 0 )
(command "insert" "Commmer" '(172 -49) 1 1 0 )
(command "insert" "Commmer" '(185 -52) 1 1 0 )
(command "insert" "Commmer" '(167 -49) 1 1 0 )
(command "insert" "Commmer" '(168 -47) 1 1 0 )
(command "insert" "Commmer" '(163 -47) 1 1 0 )
(command "insert" "Commmer" '(169 -46) 1 1 0 )
(command "insert" "Commmer" '(170 -45) 1 1 0 )
(command "insert" "Commmer" '(176 -52) 1 1 0 )
(command "insert" "Commmer" '(168 -53) 1 1 0 )
(command "insert" "Commmer" '(163 -53) 1 1 0 )
(command "insert" "Commmer" '(169 -48) 1 1 0 )
(command "insert" "Commmer" '(180 -51) 1 1 0 )
(command "insert" "Commmer" '(175 -51) 1 1 0 )
(command "insert" "Commmer" '(166 -49) 1 1 0 )
(command "insert" "Commmer" '(181 -50) 1 1 0 )
(command "insert" "Commmer" '(176 -49) 1 1 0 )
(command "insert" "Commmer" '(183 -51) 1 1 0 )
(command "insert" "Commmer" '(162 -51) 1 1 0 )
(command "insert" "Commmer" '(164 -45) 1 1 0 )
(command "insert" "Commmer" '(162 -45) 1 1 0 )
(command "insert" "Commmer" '(170 -46) 1 1 0 )
(command "insert" "Commmer" '(168 -50) 1 1 0 )
(command "insert" "Commmer" '(163 -48) 1 1 0 )
(command "insert" "Commmer" '(171 -47) 1 1 0 )
(command "insert" "Commmer" '(169 -51) 1 1 0 )
(command "insert" "Commmer" '(180 -48) 1 1 0 )
(command "insert" "Commmer" '(171 -48) 1 1 0 )
(command "insert" "Commmer" '(184 -51) 1 1 0 )
(command "insert" "Commmer" '(166 -50) 1 1 0 )
(command "insert" "Commmer" '(181 -53) 1 1 0 )
(command "insert" "Commmer" '(162 -52) 1 1 0 )
(command "insert" "Commmer" '(162 -46) 1 1 0 )
(command "insert" "Commmer" '(174 -48) 1 1 0 )
(command "insert" "Commmer" '(165 -48) 1 1 0 )
(command "insert" "Commmer" '(172 -45) 1 1 0 )
(command "insert" "Commmer" '(175 -53) 1 1 0 )
(command "insert" "Commmer" '(182 -48) 1 1 0 )
(command "insert" "Commmer" '(173 -48) 1 1 0 )
(command "insert" "Commmer" '(177 -53) 1 1 0 )
(command "insert" "Commmer" '(183 -53) 1 1 0 )
(command "insert" "Commmer" '(169 -52) 1 1 0 )
(command "insert" "Commmer" '(164 -50) 1 1 0 )
(command "insert" "Commmer" '(170 -51) 1 1 0 )
(command "insert" "Commmer" '(166 -53) 1 1 0 )
(command "insert" "Commmer" '(165 -51) 1 1 0 )
(command "insert" "Commmer" '(172 -50) 1 1 0 )
(command "insert" "Commmer" '(176 -53) 1 1 0 )
(command "insert" "Commmer" '(181 -49) 1 1 0 )
(command "insert" "Commmer" '(163 -46) 1 1 0 )
(command "insert" "Commmer" '(169 -45) 1 1 0 )
(command "insert" "Commmer" '(163 -52) 1 1 0 )
(command "insert" "Commmer" '(180 -53) 1 1 0 )
(command "insert" "Commmer" '(184 -53) 1 1 0 )
(command "insert" "Commmer" '(170 -52) 1 1 0 )
(command "insert" "Commmer" '(175 -50) 1 1 0 )
(command "insert" "Commmer" '(179 -53) 1 1 0 )
(command "insert" "Commmer" '(176 -50) 1 1 0 )
(command "layer" "m" "ped" "" )
(command "insert" "ped" '(4 -41) 1 1 0 )
(command "insert" "ped" '(30 -41) 1 1 0 )
(command "insert" "ped" '(4 -36) 1 1 0 )
(command "insert" "ped" '(28 -41) 1 1 0 )
(command "insert" "ped" '(9 -41) 1 1 0 )
(command "insert" "ped" '(33 -36) 1 1 0 )
(command "insert" "ped" '(23 -41) 1 1 0 )
(command "insert" "ped" '(6 -35) 1 1 0 )
(command "insert" "ped" '(26 -41) 1 1 0 )
(command "insert" "ped" '(12 -40) 1 1 0 )
(command "insert" "ped" '(19 -40) 1 1 0 )
(command "insert" "ped" '(8 -41) 1 1 0 )
(command "insert" "ped" '(32 -38) 1 1 0 )
(command "insert" "ped" '(22 -41) 1 1 0 )
(command "insert" "ped" '(9 -36) 1 1 0 )
(command "insert" "ped" '(32 -41) 1 1 0 )
(command "insert" "ped" '(35 -36) 1 1 0 )
(command "insert" "ped" '(34 -36) 1 1 0 )
(command "insert" "ped" '(17 -36) 1 1 0 )
(command "insert" "ped" '(7 -41) 1 1 0 )
(command "insert" "ped" '(17 -41) 1 1 0 )
(command "insert" "ped" '(15 -34) 1 1 0 )
(command "insert" "ped" '(16 -38) 1 1 0 )
(command "insert" "ped" '(19 -39) 1 1 0 )
(command "insert" "ped" '(25 -38) 1 1 0 )
(command "insert" "ped" '(6 -41) 1 1 0 )
(command "insert" "ped" '(21 -40) 1 1 0 )
(command "insert" "ped" '(3 -40) 1 1 0 )
(command "insert" "ped" '(27 -39) 1 1 0 )
(command "insert" "ped" '(26 -37) 1 1 0 )
(command "insert" "ped" '(22 -39) 1 1 0 )
(command "insert" "ped" '(21 -37) 1 1 0 )
(command "insert" "ped" '(27 -40) 1 1 0 )
(command "insert" "ped" '(8 -38) 1 1 0 )
(command "insert" "ped" '(23 -38) 1 1 0 )
(command "insert" "ped" '(30 -39) 1 1 0 )
(command "insert" "ped" '(10 -41) 1 1 0 )
(command "insert" "ped" '(9 -39) 1 1 0 )
(command "insert" "ped" '(7 -35) 1 1 0 )
(command "insert" "ped" '(31 -38) 1 1 0 )
(command "insert" "ped" '(11 -36) 1 1 0 )
(command "insert" "ped" '(10 -36) 1 1 0 )
(command "insert" "ped" '(17 -39) 1 1 0 )
(command "insert" "ped" '(16 -41) 1 1 0 )
(command "insert" "ped" '(12 -39) 1 1 0 )
(command "insert" "ped" '(11 -41) 1 1 0 )
(command "insert" "ped" '(18 -36) 1 1 0 )
(command "insert" "ped" '(15 -33) 1 1 0 )
(command "insert" "ped" '(1 -38) 1 1 0 )
(command "insert" "ped" '(20 -37) 1 1 0 )
(command "insert" "ped" '(3 -39) 1 1 0 )
(command "insert" "ped" '(2 -37) 1 1 0 )
(command "insert" "ped" '(26 -38) 1 1 0 )
(command "insert" "ped" '(5 -40) 1 1 0 )
(command "insert" "ped" '(8 -35) 1 1 0 )
(command "insert" "ped" '(23 -37) 1 1 0 )
(command "insert" "ped" '(6 -39) 1 1 0 )
(command "insert" "ped" '(5 -37) 1 1 0 )
(command "insert" "ped" '(29 -40) 1 1 0 )
(command "insert" "ped" '(16 -35) 1 1 0 )
(command "insert" "ped" '(31 -37) 1 1 0 )
(command "insert" "ped" '(17 -34) 1 1 0 )
(command "insert" "ped" '(18 -41) 1 1 0 )
(command "insert" "ped" '(15 -36) 1 1 0 )
(command "insert" "ped" '(13 -41) 1 1 0 )
(command "insert" "ped" '(24 -36) 1 1 0 )
(command "insert" "ped" '(6 -40) 1 1 0 )
(command "insert" "ped" '(2 -38) 1 1 0 )
(command "insert" "ped" '(4 -37) 1 1 0 )
(command "insert" "ped" '(9 -40) 1 1 0 )
(command "insert" "ped" '(23 -40) 1 1 0 )
(command "insert" "ped" '(7 -37) 1 1 0 )
(command "insert" "ped" '(12 -41) 1 1 0 )
(command "insert" "ped" '(32 -39) 1 1 0 )
(command "insert" "ped" '(33 -38) 1 1 0 )
(command "insert" "ped" '(34 -37) 1 1 0 )
(command "insert" "ped" '(7 -40) 1 1 0 )
(command "insert" "ped" '(14 -40) 1 1 0 )
(command "insert" "ped" '(17 -40) 1 1 0 )
(command "insert" "ped" '(24 -40) 1 1 0 )
(command "insert" "ped" '(19 -38) 1 1 0 )
(command "insert" "ped" '(25 -37) 1 1 0 )
(command "insert" "ped" '(16 -36) 1 1 0 )
(command "insert" "ped" '(22 -36) 1 1 0 )
(command "insert" "ped" '(21 -36) 1 1 0 )
(command "insert" "ped" '(8 -39) 1 1 0 )
(command "insert" "ped" '(32 -36) 1 1 0 )
(command "insert" "ped" '(30 -36) 1 1 0 )
(command "insert" "ped" '(9 -38) 1 1 0 )
(command "insert" "ped" '(7 -34) 1 1 0 )
(command "insert" "ped" '(11 -39) 1 1 0 )
(command "insert" "ped" '(10 -37) 1 1 0 )
(command "insert" "ped" '(34 -38) 1 1 0 )
(command "insert" "ped" '(17 -38) 1 1 0 )
(command "insert" "ped" '(11 -40) 1 1 0 )
(command "insert" "ped" '(18 -37) 1 1 0 )
(command "insert" "ped" '(24 -37) 1 1 0 )
(command "insert" "ped" '(19 -37) 1 1 0 )
(command "insert" "ped" '(26 -40) 1 1 0 )
(command "insert" "ped" '(20 -38) 1 1 0 )
(command "insert" "ped" '(3 -38) 1 1 0 )
(command "insert" "ped" '(26 -39) 1 1 0 )
(command "insert" "ped" '(31 -40) 1 1 0 )
(command "insert" "ped" '(21 -39) 1 1 0 )
(command "insert" "ped" '(8 -36) 1 1 0 )
(command "insert" "ped" '(23 -36) 1 1 0 )
(command "insert" "ped" '(6 -36) 1 1 0 )
(command "insert" "ped" '(5 -36) 1 1 0 )
(command "insert" "ped" '(29 -39) 1 1 0 )
(command "insert" "ped" '(7 -33) 1 1 0 )
(command "insert" "ped" '(31 -36) 1 1 0 )
(command "insert" "ped" '(10 -38) 1 1 0 )
(command "insert" "ped" '(17 -33) 1 1 0 )
(command "insert" "ped" '(18 -38) 1 1 0 )
(command "insert" "ped" '(15 -39) 1 1 0 )
(command "insert" "ped" '(13 -40) 1 1 0 )
(command "insert" "ped" '(20 -40) 1 1 0 )
(command "insert" "ped" '(7 -38) 1 1 0 )
(command "insert" "ped" '(3 -37) 1 1 0 )
(command "insert" "ped" '(4 -38) 1 1 0 )
(command "insert" "ped" '(5 -41) 1 1 0 )
(command "insert" "ped" '(8 -33) 1 1 0 )
(command "insert" "ped" '(6 -33) 1 1 0 )
(command "insert" "ped" '(5 -39) 1 1 0 )
(command "insert" "ped" '(7 -36) 1 1 0 )
(command "insert" "ped" '(15 -41) 1 1 0 )
(command "insert" "ped" '(25 -41) 1 1 0 )
(command "insert" "ped" '(4 -40) 1 1 0 )
(command "insert" "ped" '(6 -38) 1 1 0 )
(command "insert" "ped" '(30 -40) 1 1 0 )
(command "insert" "ped" '(28 -40) 1 1 0 )
(command "insert" "ped" '(33 -37) 1 1 0 )
(command "insert" "ped" '(6 -34) 1 1 0 )
(command "insert" "ped" '(35 -38) 1 1 0 )
(command "insert" "ped" '(14 -41) 1 1 0 )
(command "insert" "ped" '(24 -41) 1 1 0 )
(command "insert" "ped" '(19 -41) 1 1 0 )
(command "insert" "ped" '(25 -36) 1 1 0 )
(command "insert" "ped" '(22 -37) 1 1 0 )
(command "insert" "ped" '(7 -39) 1 1 0 )
(command "insert" "ped" '(8 -40) 1 1 0 )
(command "insert" "ped" '(32 -37) 1 1 0 )
(command "insert" "ped" '(22 -40) 1 1 0 )
(command "insert" "ped" '(30 -37) 1 1 0 )
(command "insert" "ped" '(9 -37) 1 1 0 )
(command "insert" "ped" '(32 -40) 1 1 0 )
(command "insert" "ped" '(1 -37) 1 1 0 )
(command "insert" "ped" '(11 -38) 1 1 0 )
(command "insert" "ped" '(35 -37) 1 1 0 )
(command "insert" "ped" '(17 -37) 1 1 0 )
(command "insert" "ped" '(24 -39) 1 1 0 )
(command "insert" "ped" '(15 -35) 1 1 0 )
(command "insert" "ped" '(19 -36) 1 1 0 )
(command "insert" "ped" '(1 -36) 1 1 0 )
(command "insert" "ped" '(25 -39) 1 1 0 )
(command "insert" "ped" '(21 -41) 1 1 0 )
(command "insert" "ped" '(20 -39) 1 1 0 )
(command "insert" "ped" '(3 -41) 1 1 0 )
(command "insert" "ped" '(26 -36) 1 1 0 )
(command "insert" "ped" '(22 -38) 1 1 0 )
(command "insert" "ped" '(21 -38) 1 1 0 )
(command "insert" "ped" '(28 -39) 1 1 0 )
(command "insert" "ped" '(27 -41) 1 1 0 )
(command "insert" "ped" '(8 -37) 1 1 0 )
(command "insert" "ped" '(23 -39) 1 1 0 )
(command "insert" "ped" '(6 -37) 1 1 0 )
(command "insert" "ped" '(30 -38) 1 1 0 )
(command "insert" "ped" '(10 -40) 1 1 0 )
(command "insert" "ped" '(16 -37) 1 1 0 )
(command "insert" "ped" '(31 -39) 1 1 0 )
(command "insert" "ped" '(11 -37) 1 1 0 )
(command "insert" "ped" '(10 -39) 1 1 0 )
(command "insert" "ped" '(16 -40) 1 1 0 )
(command "insert" "ped" '(14 -39) 1 1 0 )
(command "insert" "ped" '(18 -39) 1 1 0 )
(command "insert" "ped" '(15 -38) 1 1 0 )
(command "insert" "ped" '(13 -39) 1 1 0 )
(command "insert" "ped" '(20 -41) 1 1 0 )
(command "insert" "ped" '(20 -36) 1 1 0 )
(command "insert" "ped" '(3 -36) 1 1 0 )
(command "insert" "ped" '(2 -36) 1 1 0 )
(command "insert" "ped" '(16 -33) 1 1 0 )
(command "insert" "ped" '(4 -39) 1 1 0 )
(command "insert" "ped" '(8 -34) 1 1 0 )
(command "insert" "ped" '(31 -41) 1 1 0 )
(command "insert" "ped" '(5 -38) 1 1 0 )
(command "insert" "ped" '(29 -41) 1 1 0 )
(command "insert" "ped" '(16 -34) 1 1 0 )
(command "insert" "ped" '(17 -35) 1 1 0 )
(command "insert" "ped" '(15 -40) 1 1 0 )
(command "insert" "ped" '(16 -39) 1 1 0 )
(command "insert" "ped" '(24 -38) 1 1 0 )
(command "insert" "ped" '(18 -40) 1 1 0 )
(command "insert" "ped" '(25 -40) 1 1 0 )
(command "insert" "ped" '(15 -37) 1 1 0 )
(command "layer" "m" "Commmer" "" )
(command "insert" "Commmer" '(259 -77) 1 1 0 )
(command "insert" "Commmer" '(285 -75) 1 1 0 )
(command "insert" "Commmer" '(284 -78) 1 1 0 )
(command "insert" "Commmer" '(263 -75) 1 1 0 )
(command "insert" "Commmer" '(273 -77) 1 1 0 )
(command "insert" "Commmer" '(279 -73) 1 1 0 )
(command "insert" "Commmer" '(275 -84) 1 1 0 )
(command "insert" "Commmer" '(276 -78) 1 1 0 )
(command "insert" "Commmer" '(273 -82) 1 1 0 )
(command "insert" "Commmer" '(264 -76) 1 1 0 )
(command "insert" "Commmer" '(277 -86) 1 1 0 )
(command "insert" "Commmer" '(274 -78) 1 1 0 )
(command "insert" "Commmer" '(266 -78) 1 1 0 )
(command "insert" "Commmer" '(270 -72) 1 1 0 )
(command "insert" "Commmer" '(292 -75) 1 1 0 )
(command "insert" "Commmer" '(272 -81) 1 1 0 )
(command "insert" "Commmer" '(281 -80) 1 1 0 )
(command "insert" "Commmer" '(267 -75) 1 1 0 )
(command "insert" "Commmer" '(260 -76) 1 1 0 )
(command "insert" "Commmer" '(282 -75) 1 1 0 )
(command "insert" "Commmer" '(258 -76) 1 1 0 )
(command "insert" "Commmer" '(286 -77) 1 1 0 )
(command "insert" "Commmer" '(276 -90) 1 1 0 )
(command "insert" "Commmer" '(276 -85) 1 1 0 )
(command "insert" "Commmer" '(273 -75) 1 1 0 )
(command "insert" "Commmer" '(261 -82) 1 1 0 )
(command "insert" "Commmer" '(278 -80) 1 1 0 )
(command "insert" "Commmer" '(275 -78) 1 1 0 )
(command "insert" "Commmer" '(263 -83) 1 1 0 )
(command "insert" "Commmer" '(273 -88) 1 1 0 )
(command "insert" "Commmer" '(278 -74) 1 1 0 )
(command "insert" "Commmer" '(274 -84) 1 1 0 )
(command "insert" "Commmer" '(270 -92) 1 1 0 )
(command "insert" "Commmer" '(265 -78) 1 1 0 )
(command "insert" "Commmer" '(279 -74) 1 1 0 )
(command "insert" "Commmer" '(270 -83) 1 1 0 )
(command "insert" "Commmer" '(293 -76) 1 1 0 )
(command "insert" "Commmer" '(291 -75) 1 1 0 )
(command "insert" "Commmer" '(292 -77) 1 1 0 )
(command "insert" "Commmer" '(265 -80) 1 1 0 )
(command "insert" "Commmer" '(272 -80) 1 1 0 )
(command "insert" "Commmer" '(281 -78) 1 1 0 )
(command "insert" "Commmer" '(267 -85) 1 1 0 )
(command "insert" "Commmer" '(271 -78) 1 1 0 )
(command "insert" "Commmer" '(260 -75) 1 1 0 )
(command "insert" "Commmer" '(282 -82) 1 1 0 )
(command "insert" "Commmer" '(284 -81) 1 1 0 )
(command "insert" "Commmer" '(286 -75) 1 1 0 )
(command "insert" "Commmer" '(262 -84) 1 1 0 )
(command "insert" "Commmer" '(284 -79) 1 1 0 )
(command "insert" "Commmer" '(276 -92) 1 1 0 )
(command "insert" "Commmer" '(273 -76) 1 1 0 )
(command "insert" "Commmer" '(275 -87) 1 1 0 )
(command "insert" "Commmer" '(276 -79) 1 1 0 )
(command "insert" "Commmer" '(273 -81) 1 1 0 )
(command "insert" "Commmer" '(263 -85) 1 1 0 )
(command "insert" "Commmer" '(264 -77) 1 1 0 )
(command "insert" "Commmer" '(277 -85) 1 1 0 )
(command "insert" "Commmer" '(274 -79) 1 1 0 )
(command "insert" "Commmer" '(274 -90) 1 1 0 )
(command "insert" "Commmer" '(266 -79) 1 1 0 )
(command "insert" "Commmer" '(270 -90) 1 1 0 )
(command "insert" "Commmer" '(270 -73) 1 1 0 )
(command "insert" "Commmer" '(271 -90) 1 1 0 )
(command "insert" "Commmer" '(268 -84) 1 1 0 )
(command "insert" "Commmer" '(269 -80) 1 1 0 )
(command "insert" "Commmer" '(260 -77) 1 1 0 )
(command "insert" "Commmer" '(258 -77) 1 1 0 )
(command "insert" "Commmer" '(276 -91) 1 1 0 )
(command "insert" "Commmer" '(262 -82) 1 1 0 )
(command "insert" "Commmer" '(275 -92) 1 1 0 )
(command "insert" "Commmer" '(276 -86) 1 1 0 )
(command "insert" "Commmer" '(261 -81) 1 1 0 )
(command "insert" "Commmer" '(275 -81) 1 1 0 )
(command "insert" "Commmer" '(263 -82) 1 1 0 )
(command "insert" "Commmer" '(272 -90) 1 1 0 )
(command "insert" "Commmer" '(274 -85) 1 1 0 )
(command "insert" "Commmer" '(265 -77) 1 1 0 )
(command "insert" "Commmer" '(270 -80) 1 1 0 )
(command "insert" "Commmer" '(293 -75) 1 1 0 )
(command "insert" "Commmer" '(266 -80) 1 1 0 )
(command "insert" "Commmer" '(271 -92) 1 1 0 )
(command "insert" "Commmer" '(267 -84) 1 1 0 )
(command "insert" "Commmer" '(271 -73) 1 1 0 )
(command "insert" "Commmer" '(282 -83) 1 1 0 )
(command "insert" "Commmer" '(289 -80) 1 1 0 )
(command "insert" "Commmer" '(269 -86) 1 1 0 )
(command "insert" "Commmer" '(284 -82) 1 1 0 )
(command "insert" "Commmer" '(282 -78) 1 1 0 )
(command "insert" "Commmer" '(261 -77) 1 1 0 )
(command "insert" "Commmer" '(262 -85) 1 1 0 )
(command "insert" "Commmer" '(275 -86) 1 1 0 )
(command "insert" "Commmer" '(276 -72) 1 1 0 )
(command "insert" "Commmer" '(272 -78) 1 1 0 )
(command "insert" "Commmer" '(273 -80) 1 1 0 )
(command "insert" "Commmer" '(275 -75) 1 1 0 )
(command "insert" "Commmer" '(263 -84) 1 1 0 )
(command "insert" "Commmer" '(264 -78) 1 1 0 )
(command "insert" "Commmer" '(277 -84) 1 1 0 )
(command "insert" "Commmer" '(274 -76) 1 1 0 )
(command "insert" "Commmer" '(274 -91) 1 1 0 )
(command "insert" "Commmer" '(266 -76) 1 1 0 )
(command "insert" "Commmer" '(289 -79) 1 1 0 )
(command "insert" "Commmer" '(270 -91) 1 1 0 )
(command "insert" "Commmer" '(265 -75) 1 1 0 )
(command "insert" "Commmer" '(279 -79) 1 1 0 )
(command "insert" "Commmer" '(270 -78) 1 1 0 )
(command "insert" "Commmer" '(267 -77) 1 1 0 )
(command "insert" "Commmer" '(268 -85) 1 1 0 )
(command "insert" "Commmer" '(271 -91) 1 1 0 )
(command "insert" "Commmer" '(269 -79) 1 1 0 )
(command "insert" "Commmer" '(283 -77) 1 1 0 )
(command "insert" "Commmer" '(262 -76) 1 1 0 )
(command "insert" "Commmer" '(262 -83) 1 1 0 )
(command "insert" "Commmer" '(278 -86) 1 1 0 )
(command "insert" "Commmer" '(275 -80) 1 1 0 )
(command "insert" "Commmer" '(263 -77) 1 1 0 )
(command "insert" "Commmer" '(272 -73) 1 1 0 )
(command "insert" "Commmer" '(272 -91) 1 1 0 )
(command "insert" "Commmer" '(277 -74) 1 1 0 )
(command "insert" "Commmer" '(278 -72) 1 1 0 )
(command "insert" "Commmer" '(274 -82) 1 1 0 )
(command "insert" "Commmer" '(265 -76) 1 1 0 )
(command "insert" "Commmer" '(270 -81) 1 1 0 )
(command "insert" "Commmer" '(268 -76) 1 1 0 )
(command "insert" "Commmer" '(290 -75) 1 1 0 )
(command "insert" "Commmer" '(283 -81) 1 1 0 )
(command "insert" "Commmer" '(271 -72) 1 1 0 )
(command "insert" "Commmer" '(282 -80) 1 1 0 )
(command "insert" "Commmer" '(269 -85) 1 1 0 )
(command "insert" "Commmer" '(284 -83) 1 1 0 )
(command "insert" "Commmer" '(282 -79) 1 1 0 )
(command "insert" "Commmer" '(264 -80) 1 1 0 )
(command "insert" "Commmer" '(261 -76) 1 1 0 )
(command "insert" "Commmer" '(275 -89) 1 1 0 )
(command "insert" "Commmer" '(276 -73) 1 1 0 )
(command "insert" "Commmer" '(272 -79) 1 1 0 )
(command "insert" "Commmer" '(273 -87) 1 1 0 )
(command "insert" "Commmer" '(261 -86) 1 1 0 )
(command "insert" "Commmer" '(278 -92) 1 1 0 )
(command "insert" "Commmer" '(272 -82) 1 1 0 )
(command "insert" "Commmer" '(264 -79) 1 1 0 )
(command "insert" "Commmer" '(283 -75) 1 1 0 )
(command "insert" "Commmer" '(274 -77) 1 1 0 )
(command "insert" "Commmer" '(272 -72) 1 1 0 )
(command "insert" "Commmer" '(279 -80) 1 1 0 )
(command "insert" "Commmer" '(283 -76) 1 1 0 )
(command "insert" "Commmer" '(274 -88) 1 1 0 )
(command "insert" "Commmer" '(266 -77) 1 1 0 )
(command "insert" "Commmer" '(289 -78) 1 1 0 )
(command "insert" "Commmer" '(279 -78) 1 1 0 )
(command "insert" "Commmer" '(270 -79) 1 1 0 )
(command "insert" "Commmer" '(268 -75) 1 1 0 )
(command "insert" "Commmer" '(267 -76) 1 1 0 )
(command "insert" "Commmer" '(268 -86) 1 1 0 )
(command "insert" "Commmer" '(271 -81) 1 1 0 )
(command "insert" "Commmer" '(281 -74) 1 1 0 )
(command "insert" "Commmer" '(269 -78) 1 1 0 )
(command "insert" "Commmer" '(258 -75) 1 1 0 )
(command "insert" "Commmer" '(262 -77) 1 1 0 )
(command "insert" "Commmer" '(276 -80) 1 1 0 )
(command "insert" "Commmer" '(275 -83) 1 1 0 )
(command "insert" "Commmer" '(263 -76) 1 1 0 )
(command "insert" "Commmer" '(277 -92) 1 1 0 )
(command "insert" "Commmer" '(278 -90) 1 1 0 )
(command "insert" "Commmer" '(272 -92) 1 1 0 )
(command "insert" "Commmer" '(277 -73) 1 1 0 )
(command "insert" "Commmer" '(278 -73) 1 1 0 )
(command "insert" "Commmer" '(274 -83) 1 1 0 )
(command "insert" "Commmer" '(271 -74) 1 1 0 )
(command "insert" "Commmer" '(284 -80) 1 1 0 )
(command "insert" "Commmer" '(268 -77) 1 1 0 )
(command "insert" "Commmer" '(267 -86) 1 1 0 )
(command "insert" "Commmer" '(283 -80) 1 1 0 )
(command "insert" "Commmer" '(280 -78) 1 1 0 )
(command "insert" "Commmer" '(282 -81) 1 1 0 )
(command "insert" "Commmer" '(269 -84) 1 1 0 )
(command "insert" "Commmer" '(282 -76) 1 1 0 )
(command "insert" "Commmer" '(287 -75) 1 1 0 )
(command "insert" "Commmer" '(261 -75) 1 1 0 )
(command "insert" "Commmer" '(262 -75) 1 1 0 )
(command "insert" "Commmer" '(275 -88) 1 1 0 )
(command "insert" "Commmer" '(276 -74) 1 1 0 )
(command "insert" "Commmer" '(288 -75) 1 1 0 )
(command "insert" "Commmer" '(273 -86) 1 1 0 )
(command "insert" "Commmer" '(261 -85) 1 1 0 )
(command "insert" "Commmer" '(275 -77) 1 1 0 )
(command "insert" "Commmer" '(263 -86) 1 1 0 )
(command "insert" "Commmer" '(273 -91) 1 1 0 )
(command "insert" "Commmer" '(277 -79) 1 1 0 )
(command "insert" "Commmer" '(274 -89) 1 1 0 )
(command "insert" "Commmer" '(291 -77) 1 1 0 )
(command "insert" "Commmer" '(289 -77) 1 1 0 )
(command "insert" "Commmer" '(288 -76) 1 1 0 )
(command "insert" "Commmer" '(267 -79) 1 1 0 )
(command "insert" "Commmer" '(290 -78) 1 1 0 )
(command "insert" "Commmer" '(271 -80) 1 1 0 )
(command "insert" "Commmer" '(281 -73) 1 1 0 )
(command "insert" "Commmer" '(267 -80) 1 1 0 )
(command "insert" "Commmer" '(280 -72) 1 1 0 )
(command "insert" "Commmer" '(269 -77) 1 1 0 )
(command "insert" "Commmer" '(290 -80) 1 1 0 )
(command "insert" "Commmer" '(283 -79) 1 1 0 )
(command "insert" "Commmer" '(259 -75) 1 1 0 )
(command "insert" "Commmer" '(287 -77) 1 1 0 )
(command "insert" "Commmer" '(285 -77) 1 1 0 )
(command "insert" "Commmer" '(262 -81) 1 1 0 )
(command "insert" "Commmer" '(284 -76) 1 1 0 )
(command "insert" "Commmer" '(273 -79) 1 1 0 )
(command "insert" "Commmer" '(278 -84) 1 1 0 )
(command "insert" "Commmer" '(275 -82) 1 1 0 )
(command "insert" "Commmer" '(272 -74) 1 1 0 )
(command "insert" "Commmer" '(273 -92) 1 1 0 )
(command "insert" "Commmer" '(277 -91) 1 1 0 )
(command "insert" "Commmer" '(278 -91) 1 1 0 )
(command "insert" "Commmer" '(277 -72) 1 1 0 )
(command "insert" "Commmer" '(278 -78) 1 1 0 )
(command "insert" "Commmer" '(274 -80) 1 1 0 )
(command "insert" "Commmer" '(288 -80) 1 1 0 )
(command "insert" "Commmer" '(289 -75) 1 1 0 )
(command "insert" "Commmer" '(270 -74) 1 1 0 )
(command "insert" "Commmer" '(268 -78) 1 1 0 )
(command "insert" "Commmer" '(283 -83) 1 1 0 )
(command "insert" "Commmer" '(280 -79) 1 1 0 )
(command "insert" "Commmer" '(282 -77) 1 1 0 )
(command "insert" "Commmer" '(288 -79) 1 1 0 )
(command "insert" "Commmer" '(284 -75) 1 1 0 )
(command "insert" "Commmer" '(275 -91) 1 1 0 )
(command "insert" "Commmer" '(273 -85) 1 1 0 )
(command "insert" "Commmer" '(261 -84) 1 1 0 )
(command "insert" "Commmer" '(275 -76) 1 1 0 )
(command "insert" "Commmer" '(263 -81) 1 1 0 )
(command "insert" "Commmer" '(273 -90) 1 1 0 )
(command "insert" "Commmer" '(274 -75) 1 1 0 )
(command "insert" "Commmer" '(277 -78) 1 1 0 )
(command "insert" "Commmer" '(274 -86) 1 1 0 )
(command "insert" "Commmer" '(266 -75) 1 1 0 )
(command "insert" "Commmer" '(289 -76) 1 1 0 )
(command "insert" "Commmer" '(279 -72) 1 1 0 )
(command "insert" "Commmer" '(267 -78) 1 1 0 )
(command "insert" "Commmer" '(268 -80) 1 1 0 )
(command "insert" "Commmer" '(290 -79) 1 1 0 )
(command "insert" "Commmer" '(271 -83) 1 1 0 )
(command "insert" "Commmer" '(281 -72) 1 1 0 )
(command "insert" "Commmer" '(280 -73) 1 1 0 )
(command "insert" "Commmer" '(269 -76) 1 1 0 )
(command "insert" "Commmer" '(283 -78) 1 1 0 )
(command "insert" "Commmer" '(290 -77) 1 1 0 )
(command "insert" "Commmer" '(287 -76) 1 1 0 )
(command "insert" "Commmer" '(285 -76) 1 1 0 )
(command "insert" "Commmer" '(262 -86) 1 1 0 )
(command "insert" "Commmer" '(284 -77) 1 1 0 )
(command "insert" "Commmer" '(273 -78) 1 1 0 )
(command "insert" "Commmer" '(278 -85) 1 1 0 )
(command "insert" "Commmer" '(275 -85) 1 1 0 )
(command "insert" "Commmer" '(273 -83) 1 1 0 )
(command "insert" "Commmer" '(277 -90) 1 1 0 )
(command "insert" "Commmer" '(264 -75) 1 1 0 )
(command "insert" "Commmer" '(278 -79) 1 1 0 )
(command "insert" "Commmer" '(274 -81) 1 1 0 )
(command "insert" "Commmer" '(274 -92) 1 1 0 )
(command "insert" "Commmer" '(291 -76) 1 1 0 )
(command "insert" "Commmer" '(272 -83) 1 1 0 )
(command "insert" "Commmer" '(268 -79) 1 1 0 )
(command "insert" "Commmer" '(283 -82) 1 1 0 )
(command "insert" "Commmer" '(280 -80) 1 1 0 )
(command "insert" "Commmer" '(286 -76) 1 1 0 )
(command "insert" "Commmer" '(288 -77) 1 1 0 )
(command "insert" "Commmer" '(275 -90) 1 1 0 )
(command "insert" "Commmer" '(276 -84) 1 1 0 )
(command "insert" "Commmer" '(273 -84) 1 1 0 )
(command "insert" "Commmer" '(261 -83) 1 1 0 )
(command "insert" "Commmer" '(275 -79) 1 1 0 )
(command "insert" "Commmer" '(273 -89) 1 1 0 )
(command "insert" "Commmer" '(277 -80) 1 1 0 )
(command "insert" "Commmer" '(259 -76) 1 1 0 )
(command "insert" "Commmer" '(274 -87) 1 1 0 )
(command "insert" "Commmer" '(265 -79) 1 1 0 )
(command "insert" "Commmer" '(288 -78) 1 1 0 )
(command "insert" "Commmer" '(270 -82) 1 1 0 )
(command "insert" "Commmer" '(293 -77) 1 1 0 )
(command "insert" "Commmer" '(280 -74) 1 1 0 )
(command "insert" "Commmer" '(292 -76) 1 1 0 )
(command "insert" "Commmer" '(290 -76) 1 1 0 )
(command "insert" "Commmer" '(271 -82) 1 1 0 )
(command "insert" "Commmer" '(281 -79) 1 1 0 )
(command "insert" "Commmer" '(271 -79) 1 1 0 )
(command "insert" "Commmer" '(269 -75) 1 1 0 )
(command "layer" "m" "Commmer" "" )
(command "insert" "Commmer" '(291 -88) 1 1 0 )
(command "insert" "Commmer" '(283 -87) 1 1 0 )
(command "insert" "Commmer" '(288 -85) 1 1 0 )
(command "insert" "Commmer" '(289 -89) 1 1 0 )
(command "insert" "Commmer" '(283 -88) 1 1 0 )
(command "insert" "Commmer" '(288 -88) 1 1 0 )
(command "insert" "Commmer" '(291 -84) 1 1 0 )
(command "insert" "Commmer" '(290 -87) 1 1 0 )
(command "insert" "Commmer" '(293 -89) 1 1 0 )
(command "insert" "Commmer" '(292 -87) 1 1 0 )
(command "insert" "Commmer" '(287 -88) 1 1 0 )
(command "insert" "Commmer" '(292 -88) 1 1 0 )
(command "insert" "Commmer" '(293 -86) 1 1 0 )
(command "insert" "Commmer" '(285 -89) 1 1 0 )
(command "insert" "Commmer" '(286 -89) 1 1 0 )
(command "insert" "Commmer" '(284 -88) 1 1 0 )
(command "insert" "Commmer" '(288 -86) 1 1 0 )
(command "insert" "Commmer" '(289 -88) 1 1 0 )
(command "insert" "Commmer" '(289 -87) 1 1 0 )
(command "insert" "Commmer" '(288 -89) 1 1 0 )
(command "insert" "Commmer" '(291 -87) 1 1 0 )
(command "insert" "Commmer" '(290 -84) 1 1 0 )
(command "insert" "Commmer" '(293 -88) 1 1 0 )
(command "insert" "Commmer" '(292 -89) 1 1 0 )
(command "insert" "Commmer" '(293 -85) 1 1 0 )
(command "insert" "Commmer" '(285 -88) 1 1 0 )
(command "insert" "Commmer" '(290 -88) 1 1 0 )
(command "insert" "Commmer" '(292 -84) 1 1 0 )
(command "insert" "Commmer" '(284 -89) 1 1 0 )
(command "insert" "Commmer" '(288 -87) 1 1 0 )
(command "insert" "Commmer" '(282 -88) 1 1 0 )
(command "insert" "Commmer" '(289 -86) 1 1 0 )
(command "insert" "Commmer" '(291 -86) 1 1 0 )
(command "insert" "Commmer" '(282 -87) 1 1 0 )
(command "insert" "Commmer" '(290 -85) 1 1 0 )
(command "insert" "Commmer" '(293 -84) 1 1 0 )
(command "insert" "Commmer" '(285 -87) 1 1 0 )
(command "insert" "Commmer" '(287 -87) 1 1 0 )
(command "insert" "Commmer" '(290 -89) 1 1 0 )
(command "insert" "Commmer" '(292 -85) 1 1 0 )
(command "insert" "Commmer" '(282 -89) 1 1 0 )
(command "insert" "Commmer" '(289 -85) 1 1 0 )
(command "insert" "Commmer" '(291 -89) 1 1 0 )
(command "insert" "Commmer" '(288 -84) 1 1 0 )
(command "insert" "Commmer" '(284 -87) 1 1 0 )
(command "insert" "Commmer" '(283 -89) 1 1 0 )
(command "insert" "Commmer" '(286 -87) 1 1 0 )
(command "insert" "Commmer" '(291 -85) 1 1 0 )
(command "insert" "Commmer" '(290 -86) 1 1 0 )
(command "insert" "Commmer" '(292 -86) 1 1 0 )
(command "insert" "Commmer" '(287 -89) 1 1 0 )
(command "insert" "Commmer" '(293 -87) 1 1 0 )
(command "insert" "Commmer" '(286 -88) 1 1 0 )
(command "insert" "Commmer" '(289 -84) 1 1 0 )
(command "layer" "m" "Idust" "" )
(command "insert" "Idust" '(194 -39) 1 1 0 )
(command "insert" "Idust" '(191 -43) 1 1 0 )
(command "insert" "Idust" '(203 -42) 1 1 0 )
(command "insert" "Idust" '(189 -39) 1 1 0 )
(command "insert" "Idust" '(197 -42) 1 1 0 )
(command "insert" "Idust" '(202 -44) 1 1 0 )
(command "insert" "Idust" '(193 -40) 1 1 0 )
(command "insert" "Idust" '(190 -42) 1 1 0 )
(command "insert" "Idust" '(199 -44) 1 1 0 )
(command "insert" "Idust" '(194 -40) 1 1 0 )
(command "insert" "Idust" '(200 -43) 1 1 0 )
(command "insert" "Idust" '(189 -42) 1 1 0 )
(command "insert" "Idust" '(192 -39) 1 1 0 )
(command "insert" "Idust" '(201 -42) 1 1 0 )
(command "insert" "Idust" '(187 -39) 1 1 0 )
(command "insert" "Idust" '(192 -42) 1 1 0 )
(command "insert" "Idust" '(187 -40) 1 1 0 )
(command "insert" "Idust" '(199 -43) 1 1 0 )
(command "insert" "Idust" '(193 -43) 1 1 0 )
(command "insert" "Idust" '(190 -39) 1 1 0 )
(command "insert" "Idust" '(202 -42) 1 1 0 )
(command "insert" "Idust" '(195 -42) 1 1 0 )
(command "insert" "Idust" '(198 -42) 1 1 0 )
(command "insert" "Idust" '(190 -40) 1 1 0 )
(command "insert" "Idust" '(188 -40) 1 1 0 )
(command "insert" "Idust" '(196 -42) 1 1 0 )
(command "insert" "Idust" '(191 -40) 1 1 0 )
(command "insert" "Idust" '(203 -43) 1 1 0 )
(command "insert" "Idust" '(189 -40) 1 1 0 )
(command "insert" "Idust" '(197 -43) 1 1 0 )
(command "insert" "Idust" '(203 -44) 1 1 0 )
(command "insert" "Idust" '(192 -44) 1 1 0 )
(command "insert" "Idust" '(193 -41) 1 1 0 )
(command "insert" "Idust" '(195 -44) 1 1 0 )
(command "insert" "Idust" '(193 -44) 1 1 0 )
(command "insert" "Idust" '(194 -43) 1 1 0 )
(command "insert" "Idust" '(200 -42) 1 1 0 )
(command "insert" "Idust" '(186 -41) 1 1 0 )
(command "insert" "Idust" '(189 -43) 1 1 0 )
(command "insert" "Idust" '(201 -43) 1 1 0 )
(command "insert" "Idust" '(193 -39) 1 1 0 )
(command "insert" "Idust" '(192 -41) 1 1 0 )
(command "insert" "Idust" '(188 -39) 1 1 0 )
(command "insert" "Idust" '(187 -41) 1 1 0 )
(command "insert" "Idust" '(191 -42) 1 1 0 )
(command "insert" "Idust" '(191 -39) 1 1 0 )
(command "insert" "Idust" '(200 -44) 1 1 0 )
(command "insert" "Idust" '(195 -43) 1 1 0 )
(command "insert" "Idust" '(190 -43) 1 1 0 )
(command "insert" "Idust" '(196 -44) 1 1 0 )
(command "insert" "Idust" '(194 -44) 1 1 0 )
(command "insert" "Idust" '(190 -44) 1 1 0 )
(command "insert" "Idust" '(194 -41) 1 1 0 )
(command "insert" "Idust" '(191 -41) 1 1 0 )
(command "insert" "Idust" '(189 -41) 1 1 0 )
(command "insert" "Idust" '(197 -44) 1 1 0 )
(command "insert" "Idust" '(192 -43) 1 1 0 )
(command "insert" "Idust" '(199 -42) 1 1 0 )
(command "insert" "Idust" '(193 -42) 1 1 0 )
(command "insert" "Idust" '(201 -44) 1 1 0 )
(command "insert" "Idust" '(202 -43) 1 1 0 )
(command "insert" "Idust" '(198 -43) 1 1 0 )
(command "insert" "Idust" '(190 -41) 1 1 0 )
(command "insert" "Idust" '(188 -41) 1 1 0 )
(command "insert" "Idust" '(194 -42) 1 1 0 )
(command "insert" "Idust" '(191 -44) 1 1 0 )
(command "insert" "Idust" '(186 -40) 1 1 0 )
(command "insert" "Idust" '(189 -44) 1 1 0 )
(command "insert" "Idust" '(186 -39) 1 1 0 )
(command "insert" "Idust" '(198 -44) 1 1 0 )
(command "insert" "Idust" '(192 -40) 1 1 0 )
(command "insert" "Idust" '(196 -43) 1 1 0 )
(command "layer" "m" "Commmer" "" )
(command "insert" "Commmer" '(228 -93) 1 1 0 )
(command "insert" "Commmer" '(219 -90) 1 1 0 )
(command "insert" "Commmer" '(224 -96) 1 1 0 )
(command "insert" "Commmer" '(222 -96) 1 1 0 )
(command "insert" "Commmer" '(211 -90) 1 1 0 )
(command "insert" "Commmer" '(230 -95) 1 1 0 )
(command "insert" "Commmer" '(227 -98) 1 1 0 )
(command "insert" "Commmer" '(210 -90) 1 1 0 )
(command "insert" "Commmer" '(227 -93) 1 1 0 )
(command "insert" "Commmer" '(223 -94) 1 1 0 )
(command "insert" "Commmer" '(225 -94) 1 1 0 )
(command "insert" "Commmer" '(207 -90) 1 1 0 )
(command "insert" "Commmer" '(221 -91) 1 1 0 )
(command "insert" "Commmer" '(229 -95) 1 1 0 )
(command "insert" "Commmer" '(209 -92) 1 1 0 )
(command "insert" "Commmer" '(230 -96) 1 1 0 )
(command "insert" "Commmer" '(224 -93) 1 1 0 )
(command "insert" "Commmer" '(230 -97) 1 1 0 )
(command "insert" "Commmer" '(227 -97) 1 1 0 )
(command "insert" "Commmer" '(212 -94) 1 1 0 )
(command "insert" "Commmer" '(213 -87) 1 1 0 )
(command "insert" "Commmer" '(217 -90) 1 1 0 )
(command "insert" "Commmer" '(226 -96) 1 1 0 )
(command "insert" "Commmer" '(220 -91) 1 1 0 )
(command "insert" "Commmer" '(210 -95) 1 1 0 )
(command "insert" "Commmer" '(228 -95) 1 1 0 )
(command "insert" "Commmer" '(228 -96) 1 1 0 )
(command "insert" "Commmer" '(219 -92) 1 1 0 )
(command "insert" "Commmer" '(224 -98) 1 1 0 )
(command "insert" "Commmer" '(212 -91) 1 1 0 )
(command "insert" "Commmer" '(223 -93) 1 1 0 )
(command "insert" "Commmer" '(211 -92) 1 1 0 )
(command "insert" "Commmer" '(230 -93) 1 1 0 )
(command "insert" "Commmer" '(216 -92) 1 1 0 )
(command "insert" "Commmer" '(216 -90) 1 1 0 )
(command "insert" "Commmer" '(227 -95) 1 1 0 )
(command "insert" "Commmer" '(230 -98) 1 1 0 )
(command "insert" "Commmer" '(208 -90) 1 1 0 )
(command "insert" "Commmer" '(221 -89) 1 1 0 )
(command "insert" "Commmer" '(208 -92) 1 1 0 )
(command "insert" "Commmer" '(215 -88) 1 1 0 )
(command "insert" "Commmer" '(229 -93) 1 1 0 )
(command "insert" "Commmer" '(220 -88) 1 1 0 )
(command "insert" "Commmer" '(225 -98) 1 1 0 )
(command "insert" "Commmer" '(213 -89) 1 1 0 )
(command "insert" "Commmer" '(214 -89) 1 1 0 )
(command "insert" "Commmer" '(218 -91) 1 1 0 )
(command "insert" "Commmer" '(219 -91) 1 1 0 )
(command "insert" "Commmer" '(226 -95) 1 1 0 )
(command "insert" "Commmer" '(221 -90) 1 1 0 )
(command "insert" "Commmer" '(215 -87) 1 1 0 )
(command "insert" "Commmer" '(230 -94) 1 1 0 )
(command "insert" "Commmer" '(207 -92) 1 1 0 )
(command "insert" "Commmer" '(229 -96) 1 1 0 )
(command "insert" "Commmer" '(210 -93) 1 1 0 )
(command "insert" "Commmer" '(221 -87) 1 1 0 )
(command "insert" "Commmer" '(209 -90) 1 1 0 )
(command "insert" "Commmer" '(223 -95) 1 1 0 )
(command "insert" "Commmer" '(211 -94) 1 1 0 )
(command "insert" "Commmer" '(225 -95) 1 1 0 )
(command "insert" "Commmer" '(222 -93) 1 1 0 )
(command "insert" "Commmer" '(207 -91) 1 1 0 )
(command "insert" "Commmer" '(221 -92) 1 1 0 )
(command "insert" "Commmer" '(214 -87) 1 1 0 )
(command "insert" "Commmer" '(218 -92) 1 1 0 )
(command "insert" "Commmer" '(211 -91) 1 1 0 )
(command "insert" "Commmer" '(212 -93) 1 1 0 )
(command "insert" "Commmer" '(217 -91) 1 1 0 )
(command "insert" "Commmer" '(222 -95) 1 1 0 )
(command "insert" "Commmer" '(224 -95) 1 1 0 )
(command "insert" "Commmer" '(228 -98) 1 1 0 )
(command "insert" "Commmer" '(220 -90) 1 1 0 )
(command "insert" "Commmer" '(225 -96) 1 1 0 )
(command "insert" "Commmer" '(210 -94) 1 1 0 )
(command "insert" "Commmer" '(223 -96) 1 1 0 )
(command "insert" "Commmer" '(228 -94) 1 1 0 )
(command "insert" "Commmer" '(224 -97) 1 1 0 )
(command "insert" "Commmer" '(212 -90) 1 1 0 )
(command "insert" "Commmer" '(222 -97) 1 1 0 )
(command "insert" "Commmer" '(211 -93) 1 1 0 )
(command "insert" "Commmer" '(216 -91) 1 1 0 )
(command "insert" "Commmer" '(210 -91) 1 1 0 )
(command "insert" "Commmer" '(219 -88) 1 1 0 )
(command "insert" "Commmer" '(211 -95) 1 1 0 )
(command "insert" "Commmer" '(225 -93) 1 1 0 )
(command "insert" "Commmer" '(229 -98) 1 1 0 )
(command "insert" "Commmer" '(215 -89) 1 1 0 )
(command "insert" "Commmer" '(229 -94) 1 1 0 )
(command "insert" "Commmer" '(219 -87) 1 1 0 )
(command "insert" "Commmer" '(226 -94) 1 1 0 )
(command "insert" "Commmer" '(214 -88) 1 1 0 )
(command "insert" "Commmer" '(218 -90) 1 1 0 )
(command "insert" "Commmer" '(227 -96) 1 1 0 )
(command "insert" "Commmer" '(212 -95) 1 1 0 )
(command "insert" "Commmer" '(222 -98) 1 1 0 )
(command "insert" "Commmer" '(226 -93) 1 1 0 )
(command "insert" "Commmer" '(226 -97) 1 1 0 )
(command "insert" "Commmer" '(210 -92) 1 1 0 )
(command "insert" "Commmer" '(223 -98) 1 1 0 )
(command "insert" "Commmer" '(209 -91) 1 1 0 )
(command "insert" "Commmer" '(217 -92) 1 1 0 )
(command "insert" "Commmer" '(222 -94) 1 1 0 )
(command "insert" "Commmer" '(219 -89) 1 1 0 )
(command "insert" "Commmer" '(229 -97) 1 1 0 )
(command "insert" "Commmer" '(228 -97) 1 1 0 )
(command "insert" "Commmer" '(220 -92) 1 1 0 )
(command "insert" "Commmer" '(227 -94) 1 1 0 )
(command "insert" "Commmer" '(220 -87) 1 1 0 )
(command "insert" "Commmer" '(208 -91) 1 1 0 )
(command "insert" "Commmer" '(212 -92) 1 1 0 )
(command "insert" "Commmer" '(221 -88) 1 1 0 )
(command "insert" "Commmer" '(226 -98) 1 1 0 )
(command "insert" "Commmer" '(224 -94) 1 1 0 )
(command "insert" "Commmer" '(220 -89) 1 1 0 )
(command "insert" "Commmer" '(225 -97) 1 1 0 )
(command "insert" "Commmer" '(213 -88) 1 1 0 )
(command "insert" "Commmer" '(223 -97) 1 1 0 )
(command "layer" "m" "alley" "" )
(command "insert" "alley" '(36 -42) 1 1 0 )
(command "insert" "alley" '(35 -34) 1 1 0 )
(command "insert" "alley" '(41 -33) 1 1 0 )
(command "insert" "alley" '(37 -43) 1 1 0 )
(command "insert" "alley" '(36 -37) 1 1 0 )
(command "insert" "alley" '(47 -35) 1 1 0 )
(command "insert" "alley" '(43 -34) 1 1 0 )
(command "insert" "alley" '(35 -41) 1 1 0 )
(command "insert" "alley" '(34 -35) 1 1 0 )
(command "insert" "alley" '(33 -41) 1 1 0 )
(command "insert" "alley" '(41 -36) 1 1 0 )
(command "insert" "alley" '(27 -37) 1 1 0 )
(command "insert" "alley" '(36 -34) 1 1 0 )
(command "insert" "alley" '(46 -34) 1 1 0 )
(command "insert" "alley" '(42 -35) 1 1 0 )
(command "insert" "alley" '(28 -38) 1 1 0 )
(command "insert" "alley" '(38 -37) 1 1 0 )
(command "insert" "alley" '(37 -35) 1 1 0 )
(command "insert" "alley" '(32 -33) 1 1 0 )
(command "insert" "alley" '(35 -40) 1 1 0 )
(command "insert" "alley" '(30 -33) 1 1 0 )
(command "insert" "alley" '(35 -44) 1 1 0 )
(command "insert" "alley" '(38 -40) 1 1 0 )
(command "insert" "alley" '(33 -44) 1 1 0 )
(command "insert" "alley" '(45 -35) 1 1 0 )
(command "insert" "alley" '(40 -33) 1 1 0 )
(command "insert" "alley" '(35 -33) 1 1 0 )
(command "insert" "alley" '(34 -43) 1 1 0 )
(command "insert" "alley" '(28 -35) 1 1 0 )
(command "insert" "alley" '(43 -33) 1 1 0 )
(command "insert" "alley" '(29 -34) 1 1 0 )
(command "insert" "alley" '(33 -39) 1 1 0 )
(command "insert" "alley" '(40 -38) 1 1 0 )
(command "insert" "alley" '(37 -41) 1 1 0 )
(command "insert" "alley" '(36 -39) 1 1 0 )
(command "insert" "alley" '(38 -38) 1 1 0 )
(command "insert" "alley" '(37 -38) 1 1 0 )
(command "insert" "alley" '(30 -34) 1 1 0 )
(command "insert" "alley" '(35 -43) 1 1 0 )
(command "insert" "alley" '(34 -33) 1 1 0 )
(command "insert" "alley" '(36 -44) 1 1 0 )
(command "insert" "alley" '(34 -44) 1 1 0 )
(command "insert" "alley" '(42 -33) 1 1 0 )
(command "insert" "alley" '(31 -35) 1 1 0 )
(command "insert" "alley" '(37 -33) 1 1 0 )
(command "insert" "alley" '(32 -35) 1 1 0 )
(command "insert" "alley" '(29 -37) 1 1 0 )
(command "insert" "alley" '(39 -34) 1 1 0 )
(command "insert" "alley" '(33 -34) 1 1 0 )
(command "insert" "alley" '(45 -33) 1 1 0 )
(command "insert" "alley" '(40 -35) 1 1 0 )
(command "insert" "alley" '(36 -41) 1 1 0 )
(command "insert" "alley" '(35 -35) 1 1 0 )
(command "insert" "alley" '(34 -41) 1 1 0 )
(command "insert" "alley" '(41 -34) 1 1 0 )
(command "insert" "alley" '(37 -44) 1 1 0 )
(command "insert" "alley" '(36 -36) 1 1 0 )
(command "insert" "alley" '(43 -35) 1 1 0 )
(command "insert" "alley" '(38 -35) 1 1 0 )
(command "insert" "alley" '(39 -37) 1 1 0 )
(command "insert" "alley" '(34 -34) 1 1 0 )
(command "insert" "alley" '(33 -42) 1 1 0 )
(command "insert" "alley" '(41 -37) 1 1 0 )
(command "insert" "alley" '(27 -34) 1 1 0 )
(command "insert" "alley" '(36 -33) 1 1 0 )
(command "insert" "alley" '(35 -42) 1 1 0 )
(command "insert" "alley" '(42 -34) 1 1 0 )
(command "insert" "alley" '(28 -37) 1 1 0 )
(command "insert" "alley" '(38 -36) 1 1 0 )
(command "insert" "alley" '(37 -36) 1 1 0 )
(command "insert" "alley" '(44 -33) 1 1 0 )
(command "insert" "alley" '(39 -33) 1 1 0 )
(command "insert" "alley" '(38 -43) 1 1 0 )
(command "insert" "alley" '(34 -42) 1 1 0 )
(command "insert" "alley" '(28 -34) 1 1 0 )
(command "insert" "alley" '(29 -35) 1 1 0 )
(command "insert" "alley" '(38 -44) 1 1 0 )
(command "insert" "alley" '(40 -37) 1 1 0 )
(command "insert" "alley" '(36 -43) 1 1 0 )
(command "insert" "alley" '(34 -39) 1 1 0 )
(command "insert" "alley" '(27 -33) 1 1 0 )
(command "insert" "alley" '(37 -42) 1 1 0 )
(command "insert" "alley" '(36 -38) 1 1 0 )
(command "insert" "alley" '(47 -34) 1 1 0 )
(command "insert" "alley" '(38 -33) 1 1 0 )
(command "insert" "alley" '(37 -39) 1 1 0 )
(command "insert" "alley" '(39 -36) 1 1 0 )
(command "insert" "alley" '(33 -40) 1 1 0 )
(command "insert" "alley" '(27 -36) 1 1 0 )
(command "insert" "alley" '(36 -35) 1 1 0 )
(command "insert" "alley" '(46 -35) 1 1 0 )
(command "insert" "alley" '(37 -34) 1 1 0 )
(command "insert" "alley" '(32 -34) 1 1 0 )
(command "insert" "alley" '(44 -35) 1 1 0 )
(command "insert" "alley" '(29 -38) 1 1 0 )
(command "insert" "alley" '(39 -35) 1 1 0 )
(command "insert" "alley" '(38 -41) 1 1 0 )
(command "insert" "alley" '(33 -35) 1 1 0 )
(command "insert" "alley" '(45 -34) 1 1 0 )
(command "insert" "alley" '(40 -34) 1 1 0 )
(command "insert" "alley" '(36 -40) 1 1 0 )
(command "insert" "alley" '(34 -40) 1 1 0 )
(command "insert" "alley" '(41 -35) 1 1 0 )
(command "insert" "alley" '(47 -33) 1 1 0 )
(command "insert" "alley" '(29 -33) 1 1 0 )
(command "insert" "alley" '(38 -34) 1 1 0 )
(command "insert" "alley" '(31 -34) 1 1 0 )
(command "insert" "alley" '(35 -39) 1 1 0 )
(command "insert" "alley" '(33 -43) 1 1 0 )
(command "insert" "alley" '(41 -38) 1 1 0 )
(command "insert" "alley" '(27 -35) 1 1 0 )
(command "insert" "alley" '(37 -40) 1 1 0 )
(command "insert" "alley" '(28 -36) 1 1 0 )
(command "insert" "alley" '(38 -39) 1 1 0 )
(command "insert" "alley" '(37 -37) 1 1 0 )
(command "insert" "alley" '(30 -35) 1 1 0 )
(command "insert" "alley" '(39 -38) 1 1 0 )
(command "insert" "alley" '(38 -42) 1 1 0 )
(command "insert" "alley" '(27 -38) 1 1 0 )
(command "insert" "alley" '(46 -33) 1 1 0 )
(command "insert" "alley" '(28 -33) 1 1 0 )
(command "insert" "alley" '(44 -34) 1 1 0 )
(command "insert" "alley" '(29 -36) 1 1 0 )
(command "insert" "alley" '(31 -33) 1 1 0 )
(command "insert" "alley" '(33 -33) 1 1 0 )
(command "insert" "alley" '(40 -36) 1 1 0 )
(command "layer" "m" "Commmer" "" )
(command "insert" "Commmer" '(211 -63) 1 1 0 )
(command "insert" "Commmer" '(210 -64) 1 1 0 )
(command "insert" "Commmer" '(212 -63) 1 1 0 )
(command "insert" "Commmer" '(212 -65) 1 1 0 )
(command "insert" "Commmer" '(212 -64) 1 1 0 )
(command "insert" "Commmer" '(211 -64) 1 1 0 )
(command "insert" "Commmer" '(210 -63) 1 1 0 )
(command "insert" "Commmer" '(211 -65) 1 1 0 )
(command "insert" "Commmer" '(210 -65) 1 1 0 )
(command "layer" "m" "Res" "" )
(command "insert" "Res" '(236 -97) 1 1 0 )
(command "insert" "Res" '(233 -97) 1 1 0 )
(command "insert" "Res" '(231 -97) 1 1 0 )
(command "insert" "Res" '(235 -98) 1 1 0 )
(command "insert" "Res" '(232 -96) 1 1 0 )
(command "insert" "Res" '(232 -95) 1 1 0 )
(command "insert" "Res" '(235 -93) 1 1 0 )
(command "insert" "Res" '(231 -94) 1 1 0 )
(command "insert" "Res" '(233 -94) 1 1 0 )
(command "insert" "Res" '(236 -94) 1 1 0 )
(command "insert" "Res" '(234 -93) 1 1 0 )
(command "insert" "Res" '(237 -95) 1 1 0 )
(command "insert" "Res" '(236 -98) 1 1 0 )
(command "insert" "Res" '(233 -96) 1 1 0 )
(command "insert" "Res" '(231 -96) 1 1 0 )
(command "insert" "Res" '(238 -94) 1 1 0 )
(command "insert" "Res" '(232 -97) 1 1 0 )
(command "insert" "Res" '(239 -95) 1 1 0 )
(command "insert" "Res" '(233 -93) 1 1 0 )
(command "insert" "Res" '(236 -95) 1 1 0 )
(command "insert" "Res" '(235 -97) 1 1 0 )
(command "insert" "Res" '(237 -94) 1 1 0 )
(command "insert" "Res" '(234 -96) 1 1 0 )
(command "insert" "Res" '(231 -93) 1 1 0 )
(command "insert" "Res" '(234 -94) 1 1 0 )
(command "insert" "Res" '(238 -95) 1 1 0 )
(command "insert" "Res" '(232 -98) 1 1 0 )
(command "insert" "Res" '(235 -95) 1 1 0 )
(command "insert" "Res" '(239 -94) 1 1 0 )
(command "insert" "Res" '(235 -96) 1 1 0 )
(command "insert" "Res" '(232 -93) 1 1 0 )
(command "insert" "Res" '(237 -93) 1 1 0 )
(command "insert" "Res" '(234 -97) 1 1 0 )
(command "insert" "Res" '(231 -98) 1 1 0 )
(command "insert" "Res" '(234 -95) 1 1 0 )
(command "insert" "Res" '(235 -94) 1 1 0 )
(command "insert" "Res" '(236 -96) 1 1 0 )
(command "insert" "Res" '(233 -98) 1 1 0 )
(command "insert" "Res" '(232 -94) 1 1 0 )
(command "insert" "Res" '(239 -93) 1 1 0 )
(command "insert" "Res" '(231 -95) 1 1 0 )
(command "insert" "Res" '(233 -95) 1 1 0 )
(command "insert" "Res" '(236 -93) 1 1 0 )
(command "insert" "Res" '(238 -93) 1 1 0 )
(command "insert" "Res" '(234 -98) 1 1 0 )
(command "layer" "m" "Res" "" )
(command "insert" "Res" '(291 -79) 1 1 0 )
(command "insert" "Res" '(293 -80) 1 1 0 )
(command "insert" "Res" '(292 -79) 1 1 0 )
(command "insert" "Res" '(292 -78) 1 1 0 )
(command "insert" "Res" '(292 -80) 1 1 0 )
(command "insert" "Res" '(293 -78) 1 1 0 )
(command "insert" "Res" '(293 -79) 1 1 0 )
(command "insert" "Res" '(291 -80) 1 1 0 )
(command "insert" "Res" '(291 -78) 1 1 0 )
(command "layer" "m" "edge" "" )
(command "insert" "edge" '(277 -46) 1 1 0 )
(command "insert" "edge" '(277 -47) 1 1 0 )
(command "insert" "edge" '(280 -50) 1 1 0 )
(command "insert" "edge" '(279 -49) 1 1 0 )
(command "insert" "edge" '(280 -48) 1 1 0 )
(command "insert" "edge" '(278 -48) 1 1 0 )
(command "insert" "edge" '(278 -46) 1 1 0 )
(command "insert" "edge" '(278 -50) 1 1 0 )
(command "insert" "edge" '(276 -50) 1 1 0 )
(command "insert" "edge" '(277 -49) 1 1 0 )
(command "insert" "edge" '(276 -47) 1 1 0 )
(command "insert" "edge" '(279 -50) 1 1 0 )
(command "insert" "edge" '(281 -49) 1 1 0 )
(command "insert" "edge" '(276 -45) 1 1 0 )
(command "insert" "edge" '(281 -48) 1 1 0 )
(command "insert" "edge" '(279 -48) 1 1 0 )
(command "insert" "edge" '(278 -45) 1 1 0 )
(command "insert" "edge" '(280 -49) 1 1 0 )
(command "insert" "edge" '(277 -50) 1 1 0 )
(command "insert" "edge" '(278 -49) 1 1 0 )
(command "insert" "edge" '(278 -47) 1 1 0 )
(command "insert" "edge" '(277 -45) 1 1 0 )
(command "insert" "edge" '(281 -50) 1 1 0 )
(command "insert" "edge" '(277 -48) 1 1 0 )
(command "insert" "edge" '(276 -48) 1 1 0 )
(command "insert" "edge" '(276 -49) 1 1 0 )
(command "insert" "edge" '(276 -46) 1 1 0 )
(command "layer" "m" "Commmer" "" )
(command "insert" "Commmer" '(193 -54) 1 1 0 )
(command "insert" "Commmer" '(193 -60) 1 1 0 )
(command "insert" "Commmer" '(199 -58) 1 1 0 )
(command "insert" "Commmer" '(197 -70) 1 1 0 )
(command "insert" "Commmer" '(203 -66) 1 1 0 )
(command "insert" "Commmer" '(200 -64) 1 1 0 )
(command "insert" "Commmer" '(198 -66) 1 1 0 )
(command "insert" "Commmer" '(195 -61) 1 1 0 )
(command "insert" "Commmer" '(196 -62) 1 1 0 )
(command "insert" "Commmer" '(200 -57) 1 1 0 )
(command "insert" "Commmer" '(197 -63) 1 1 0 )
(command "insert" "Commmer" '(186 -59) 1 1 0 )
(command "insert" "Commmer" '(182 -59) 1 1 0 )
(command "insert" "Commmer" '(198 -60) 1 1 0 )
(command "insert" "Commmer" '(196 -70) 1 1 0 )
(command "insert" "Commmer" '(177 -62) 1 1 0 )
(command "insert" "Commmer" '(199 -57) 1 1 0 )
(command "insert" "Commmer" '(178 -61) 1 1 0 )
(command "insert" "Commmer" '(194 -54) 1 1 0 )
(command "insert" "Commmer" '(180 -59) 1 1 0 )
(command "insert" "Commmer" '(195 -56) 1 1 0 )
(command "insert" "Commmer" '(181 -58) 1 1 0 )
(command "insert" "Commmer" '(187 -62) 1 1 0 )
(command "insert" "Commmer" '(190 -66) 1 1 0 )
(command "insert" "Commmer" '(186 -60) 1 1 0 )
(command "insert" "Commmer" '(198 -57) 1 1 0 )
(command "insert" "Commmer" '(191 -66) 1 1 0 )
(command "insert" "Commmer" '(191 -67) 1 1 0 )
(command "insert" "Commmer" '(199 -60) 1 1 0 )
(command "insert" "Commmer" '(188 -58) 1 1 0 )
(command "insert" "Commmer" '(178 -62) 1 1 0 )
(command "insert" "Commmer" '(195 -55) 1 1 0 )
(command "insert" "Commmer" '(184 -59) 1 1 0 )
(command "insert" "Commmer" '(197 -56) 1 1 0 )
(command "insert" "Commmer" '(185 -58) 1 1 0 )
(command "insert" "Commmer" '(192 -70) 1 1 0 )
(command "insert" "Commmer" '(192 -62) 1 1 0 )
(command "insert" "Commmer" '(189 -68) 1 1 0 )
(command "insert" "Commmer" '(198 -58) 1 1 0 )
(command "insert" "Commmer" '(187 -60) 1 1 0 )
(command "insert" "Commmer" '(200 -68) 1 1 0 )
(command "insert" "Commmer" '(199 -67) 1 1 0 )
(command "insert" "Commmer" '(196 -71) 1 1 0 )
(command "insert" "Commmer" '(197 -71) 1 1 0 )
(command "insert" "Commmer" '(194 -60) 1 1 0 )
(command "insert" "Commmer" '(189 -62) 1 1 0 )
(command "insert" "Commmer" '(190 -61) 1 1 0 )
(command "insert" "Commmer" '(200 -61) 1 1 0 )
(command "insert" "Commmer" '(195 -71) 1 1 0 )
(command "insert" "Commmer" '(187 -59) 1 1 0 )
(command "insert" "Commmer" '(200 -65) 1 1 0 )
(command "insert" "Commmer" '(188 -60) 1 1 0 )
(command "insert" "Commmer" '(198 -67) 1 1 0 )
(command "insert" "Commmer" '(195 -60) 1 1 0 )
(command "insert" "Commmer" '(190 -62) 1 1 0 )
(command "insert" "Commmer" '(196 -63) 1 1 0 )
(command "insert" "Commmer" '(200 -58) 1 1 0 )
(command "insert" "Commmer" '(197 -62) 1 1 0 )
(command "insert" "Commmer" '(191 -60) 1 1 0 )
(command "insert" "Commmer" '(201 -67) 1 1 0 )
(command "insert" "Commmer" '(198 -61) 1 1 0 )
(command "insert" "Commmer" '(177 -61) 1 1 0 )
(command "insert" "Commmer" '(192 -56) 1 1 0 )
(command "insert" "Commmer" '(200 -62) 1 1 0 )
(command "insert" "Commmer" '(194 -55) 1 1 0 )
(command "insert" "Commmer" '(183 -59) 1 1 0 )
(command "insert" "Commmer" '(179 -60) 1 1 0 )
(command "insert" "Commmer" '(181 -57) 1 1 0 )
(command "insert" "Commmer" '(196 -60) 1 1 0 )
(command "insert" "Commmer" '(190 -67) 1 1 0 )
(command "insert" "Commmer" '(186 -61) 1 1 0 )
(command "insert" "Commmer" '(195 -65) 1 1 0 )
(command "insert" "Commmer" '(198 -62) 1 1 0 )
(command "insert" "Commmer" '(199 -63) 1 1 0 )
(command "insert" "Commmer" '(188 -59) 1 1 0 )
(command "insert" "Commmer" '(194 -56) 1 1 0 )
(command "insert" "Commmer" '(179 -62) 1 1 0 )
(command "insert" "Commmer" '(202 -66) 1 1 0 )
(command "insert" "Commmer" '(193 -56) 1 1 0 )
(command "insert" "Commmer" '(180 -57) 1 1 0 )
(command "insert" "Commmer" '(195 -54) 1 1 0 )
(command "insert" "Commmer" '(185 -57) 1 1 0 )
(command "insert" "Commmer" '(192 -71) 1 1 0 )
(command "insert" "Commmer" '(186 -62) 1 1 0 )
(command "insert" "Commmer" '(201 -68) 1 1 0 )
(command "insert" "Commmer" '(189 -67) 1 1 0 )
(command "insert" "Commmer" '(198 -59) 1 1 0 )
(command "insert" "Commmer" '(197 -65) 1 1 0 )
(command "insert" "Commmer" '(194 -69) 1 1 0 )
(command "insert" "Commmer" '(193 -62) 1 1 0 )
(command "insert" "Commmer" '(199 -66) 1 1 0 )
(command "insert" "Commmer" '(196 -64) 1 1 0 )
(command "insert" "Commmer" '(194 -61) 1 1 0 )
(command "insert" "Commmer" '(189 -61) 1 1 0 )
(command "insert" "Commmer" '(179 -61) 1 1 0 )
(command "insert" "Commmer" '(200 -59) 1 1 0 )
(command "insert" "Commmer" '(184 -57) 1 1 0 )
(command "insert" "Commmer" '(193 -69) 1 1 0 )
(command "insert" "Commmer" '(196 -54) 1 1 0 )
(command "insert" "Commmer" '(195 -70) 1 1 0 )
(command "insert" "Commmer" '(197 -55) 1 1 0 )
(command "insert" "Commmer" '(192 -60) 1 1 0 )
(command "insert" "Commmer" '(187 -58) 1 1 0 )
(command "insert" "Commmer" '(194 -70) 1 1 0 )
(command "insert" "Commmer" '(203 -68) 1 1 0 )
(command "insert" "Commmer" '(200 -66) 1 1 0 )
(command "insert" "Commmer" '(199 -65) 1 1 0 )
(command "insert" "Commmer" '(188 -61) 1 1 0 )
(command "insert" "Commmer" '(194 -62) 1 1 0 )
(command "insert" "Commmer" '(198 -64) 1 1 0 )
(command "insert" "Commmer" '(195 -63) 1 1 0 )
(command "insert" "Commmer" '(196 -56) 1 1 0 )
(command "insert" "Commmer" '(191 -62) 1 1 0 )
(command "insert" "Commmer" '(197 -61) 1 1 0 )
(command "insert" "Commmer" '(186 -57) 1 1 0 )
(command "insert" "Commmer" '(195 -69) 1 1 0 )
(command "insert" "Commmer" '(192 -54) 1 1 0 )
(command "insert" "Commmer" '(182 -57) 1 1 0 )
(command "insert" "Commmer" '(190 -60) 1 1 0 )
(command "insert" "Commmer" '(177 -60) 1 1 0 )
(command "insert" "Commmer" '(193 -55) 1 1 0 )
(command "insert" "Commmer" '(201 -66) 1 1 0 )
(command "insert" "Commmer" '(199 -59) 1 1 0 )
(command "insert" "Commmer" '(187 -57) 1 1 0 )
(command "insert" "Commmer" '(203 -67) 1 1 0 )
(command "insert" "Commmer" '(199 -68) 1 1 0 )
(command "insert" "Commmer" '(193 -70) 1 1 0 )
(command "insert" "Commmer" '(183 -57) 1 1 0 )
(command "insert" "Commmer" '(196 -61) 1 1 0 )
(command "insert" "Commmer" '(191 -61) 1 1 0 )
(command "insert" "Commmer" '(186 -58) 1 1 0 )
(command "insert" "Commmer" '(195 -64) 1 1 0 )
(command "insert" "Commmer" '(182 -58) 1 1 0 )
(command "insert" "Commmer" '(198 -63) 1 1 0 )
(command "insert" "Commmer" '(199 -62) 1 1 0 )
(command "insert" "Commmer" '(178 -60) 1 1 0 )
(command "insert" "Commmer" '(202 -67) 1 1 0 )
(command "insert" "Commmer" '(180 -58) 1 1 0 )
(command "insert" "Commmer" '(181 -59) 1 1 0 )
(command "insert" "Commmer" '(196 -69) 1 1 0 )
(command "insert" "Commmer" '(189 -66) 1 1 0 )
(command "insert" "Commmer" '(197 -64) 1 1 0 )
(command "insert" "Commmer" '(193 -61) 1 1 0 )
(command "insert" "Commmer" '(199 -61) 1 1 0 )
(command "insert" "Commmer" '(188 -57) 1 1 0 )
(command "insert" "Commmer" '(198 -68) 1 1 0 )
(command "insert" "Commmer" '(189 -60) 1 1 0 )
(command "insert" "Commmer" '(183 -58) 1 1 0 )
(command "insert" "Commmer" '(202 -68) 1 1 0 )
(command "insert" "Commmer" '(196 -65) 1 1 0 )
(command "insert" "Commmer" '(184 -58) 1 1 0 )
(command "insert" "Commmer" '(200 -63) 1 1 0 )
(command "insert" "Commmer" '(196 -55) 1 1 0 )
(command "insert" "Commmer" '(185 -59) 1 1 0 )
(command "insert" "Commmer" '(192 -69) 1 1 0 )
(command "insert" "Commmer" '(193 -71) 1 1 0 )
(command "insert" "Commmer" '(197 -54) 1 1 0 )
(command "insert" "Commmer" '(192 -61) 1 1 0 )
(command "insert" "Commmer" '(197 -69) 1 1 0 )
(command "insert" "Commmer" '(194 -71) 1 1 0 )
(command "insert" "Commmer" '(200 -67) 1 1 0 )
(command "insert" "Commmer" '(199 -64) 1 1 0 )
(command "insert" "Commmer" '(188 -62) 1 1 0 )
(command "insert" "Commmer" '(198 -65) 1 1 0 )
(command "insert" "Commmer" '(195 -62) 1 1 0 )
(command "insert" "Commmer" '(191 -68) 1 1 0 )
(command "insert" "Commmer" '(187 -61) 1 1 0 )
(command "insert" "Commmer" '(200 -60) 1 1 0 )
(command "insert" "Commmer" '(190 -68) 1 1 0 )
(command "insert" "Commmer" '(197 -60) 1 1 0 )
(command "insert" "Commmer" '(192 -55) 1 1 0 )
(command "layer" "m" "edge" "" )
(command "insert" "edge" '(8 -44) 1 1 0 )
(command "insert" "edge" '(22 -44) 1 1 0 )
(command "insert" "edge" '(26 -42) 1 1 0 )
(command "insert" "edge" '(20 -43) 1 1 0 )
(command "insert" "edge" '(32 -44) 1 1 0 )
(command "insert" "edge" '(31 -44) 1 1 0 )
(command "insert" "edge" '(29 -44) 1 1 0 )
(command "insert" "edge" '(21 -42) 1 1 0 )
(command "insert" "edge" '(15 -50) 1 1 0 )
(command "insert" "edge" '(17 -46) 1 1 0 )
(command "insert" "edge" '(24 -42) 1 1 0 )
(command "insert" "edge" '(9 -44) 1 1 0 )
(command "insert" "edge" '(31 -43) 1 1 0 )
(command "insert" "edge" '(18 -45) 1 1 0 )
(command "insert" "edge" '(25 -43) 1 1 0 )
(command "insert" "edge" '(10 -43) 1 1 0 )
(command "insert" "edge" '(6 -43) 1 1 0 )
(command "insert" "edge" '(15 -48) 1 1 0 )
(command "insert" "edge" '(19 -47) 1 1 0 )
(command "insert" "edge" '(30 -42) 1 1 0 )
(command "insert" "edge" '(23 -44) 1 1 0 )
(command "insert" "edge" '(6 -44) 1 1 0 )
(command "insert" "edge" '(15 -49) 1 1 0 )
(command "insert" "edge" '(14 -43) 1 1 0 )
(command "insert" "edge" '(11 -42) 1 1 0 )
(command "insert" "edge" '(28 -43) 1 1 0 )
(command "insert" "edge" '(15 -47) 1 1 0 )
(command "insert" "edge" '(23 -43) 1 1 0 )
(command "insert" "edge" '(18 -46) 1 1 0 )
(command "insert" "edge" '(29 -42) 1 1 0 )
(command "insert" "edge" '(10 -44) 1 1 0 )
(command "insert" "edge" '(14 -44) 1 1 0 )
(command "insert" "edge" '(15 -45) 1 1 0 )
(command "insert" "edge" '(20 -47) 1 1 0 )
(command "insert" "edge" '(24 -44) 1 1 0 )
(command "insert" "edge" '(12 -42) 1 1 0 )
(command "insert" "edge" '(19 -42) 1 1 0 )
(command "insert" "edge" '(22 -42) 1 1 0 )
(command "insert" "edge" '(18 -43) 1 1 0 )
(command "insert" "edge" '(17 -49) 1 1 0 )
(command "insert" "edge" '(13 -43) 1 1 0 )
(command "insert" "edge" '(20 -45) 1 1 0 )
(command "insert" "edge" '(7 -44) 1 1 0 )
(command "insert" "edge" '(8 -43) 1 1 0 )
(command "insert" "edge" '(25 -44) 1 1 0 )
(command "insert" "edge" '(9 -42) 1 1 0 )
(command "insert" "edge" '(20 -42) 1 1 0 )
(command "insert" "edge" '(32 -43) 1 1 0 )
(command "insert" "edge" '(26 -43) 1 1 0 )
(command "insert" "edge" '(21 -43) 1 1 0 )
(command "insert" "edge" '(7 -43) 1 1 0 )
(command "insert" "edge" '(11 -44) 1 1 0 )
(command "insert" "edge" '(17 -47) 1 1 0 )
(command "insert" "edge" '(16 -49) 1 1 0 )
(command "insert" "edge" '(25 -42) 1 1 0 )
(command "insert" "edge" '(18 -44) 1 1 0 )
(command "insert" "edge" '(10 -42) 1 1 0 )
(command "insert" "edge" '(6 -42) 1 1 0 )
(command "insert" "edge" '(16 -50) 1 1 0 )
(command "insert" "edge" '(27 -42) 1 1 0 )
(command "insert" "edge" '(19 -44) 1 1 0 )
(command "insert" "edge" '(16 -47) 1 1 0 )
(command "insert" "edge" '(26 -44) 1 1 0 )
(command "insert" "edge" '(14 -42) 1 1 0 )
(command "insert" "edge" '(11 -43) 1 1 0 )
(command "insert" "edge" '(28 -42) 1 1 0 )
(command "insert" "edge" '(12 -44) 1 1 0 )
(command "insert" "edge" '(29 -43) 1 1 0 )
(command "insert" "edge" '(17 -45) 1 1 0 )
(command "insert" "edge" '(7 -42) 1 1 0 )
(command "insert" "edge" '(19 -43) 1 1 0 )
(command "insert" "edge" '(31 -42) 1 1 0 )
(command "insert" "edge" '(18 -42) 1 1 0 )
(command "insert" "edge" '(17 -50) 1 1 0 )
(command "insert" "edge" '(13 -44) 1 1 0 )
(command "insert" "edge" '(20 -44) 1 1 0 )
(command "insert" "edge" '(24 -43) 1 1 0 )
(command "insert" "edge" '(27 -44) 1 1 0 )
(command "insert" "edge" '(8 -42) 1 1 0 )
(command "insert" "edge" '(19 -46) 1 1 0 )
(command "insert" "edge" '(30 -43) 1 1 0 )
(command "insert" "edge" '(9 -43) 1 1 0 )
(command "insert" "edge" '(32 -42) 1 1 0 )
(command "insert" "edge" '(16 -46) 1 1 0 )
(command "insert" "edge" '(21 -44) 1 1 0 )
(command "insert" "edge" '(16 -45) 1 1 0 )
(command "insert" "edge" '(30 -44) 1 1 0 )
(command "insert" "edge" '(16 -48) 1 1 0 )
(command "insert" "edge" '(23 -42) 1 1 0 )
(command "insert" "edge" '(15 -46) 1 1 0 )
(command "insert" "edge" '(18 -47) 1 1 0 )
(command "insert" "edge" '(27 -43) 1 1 0 )
(command "insert" "edge" '(12 -43) 1 1 0 )
(command "insert" "edge" '(19 -45) 1 1 0 )
(command "insert" "edge" '(22 -43) 1 1 0 )
(command "insert" "edge" '(17 -48) 1 1 0 )
(command "insert" "edge" '(28 -44) 1 1 0 )
(command "insert" "edge" '(13 -42) 1 1 0 )
(command "insert" "edge" '(20 -46) 1 1 0 )
(command "layer" "m" "Res" "" )
(command "insert" "Res" '(103 -35) 1 1 0 )
(command "insert" "Res" '(113 -40) 1 1 0 )
(command "insert" "Res" '(107 -36) 1 1 0 )
(command "insert" "Res" '(106 -36) 1 1 0 )
(command "insert" "Res" '(113 -39) 1 1 0 )
(command "insert" "Res" '(112 -41) 1 1 0 )
(command "insert" "Res" '(108 -39) 1 1 0 )
(command "insert" "Res" '(102 -34) 1 1 0 )
(command "insert" "Res" '(111 -40) 1 1 0 )
(command "insert" "Res" '(110 -41) 1 1 0 )
(command "insert" "Res" '(105 -38) 1 1 0 )
(command "insert" "Res" '(112 -39) 1 1 0 )
(command "insert" "Res" '(104 -34) 1 1 0 )
(command "insert" "Res" '(104 -35) 1 1 0 )
(command "insert" "Res" '(102 -35) 1 1 0 )
(command "insert" "Res" '(103 -34) 1 1 0 )
(command "insert" "Res" '(105 -37) 1 1 0 )
(command "insert" "Res" '(107 -38) 1 1 0 )
(command "insert" "Res" '(108 -40) 1 1 0 )
(command "insert" "Res" '(103 -33) 1 1 0 )
(command "insert" "Res" '(106 -38) 1 1 0 )
(command "insert" "Res" '(106 -37) 1 1 0 )
(command "insert" "Res" '(111 -39) 1 1 0 )
(command "insert" "Res" '(105 -36) 1 1 0 )
(command "insert" "Res" '(109 -41) 1 1 0 )
(command "insert" "Res" '(108 -41) 1 1 0 )
(command "insert" "Res" '(113 -41) 1 1 0 )
(command "insert" "Res" '(107 -37) 1 1 0 )
(command "insert" "Res" '(104 -33) 1 1 0 )
(command "insert" "Res" '(102 -33) 1 1 0 )
(command "insert" "Res" '(112 -40) 1 1 0 )
(command "insert" "Res" '(110 -39) 1 1 0 )
(command "insert" "Res" '(109 -39) 1 1 0 )
(command "insert" "Res" '(109 -40) 1 1 0 )
(command "insert" "Res" '(111 -41) 1 1 0 )
(command "insert" "Res" '(110 -40) 1 1 0 )
(command "layer" "m" "Res" "" )
(command "insert" "Res" '(293 -94) 1 1 0 )
(command "insert" "Res" '(298 -94) 1 1 0 )
(command "insert" "Res" '(294 -93) 1 1 0 )
(command "insert" "Res" '(291 -96) 1 1 0 )
(command "insert" "Res" '(299 -95) 1 1 0 )
(command "insert" "Res" '(293 -91) 1 1 0 )
(command "insert" "Res" '(299 -96) 1 1 0 )
(command "insert" "Res" '(291 -95) 1 1 0 )
(command "insert" "Res" '(296 -93) 1 1 0 )
(command "insert" "Res" '(298 -97) 1 1 0 )
(command "insert" "Res" '(295 -92) 1 1 0 )
(command "insert" "Res" '(293 -97) 1 1 0 )
(command "insert" "Res" '(293 -93) 1 1 0 )
(command "insert" "Res" '(292 -96) 1 1 0 )
(command "insert" "Res" '(298 -95) 1 1 0 )
(command "insert" "Res" '(292 -92) 1 1 0 )
(command "insert" "Res" '(299 -94) 1 1 0 )
(command "insert" "Res" '(297 -98) 1 1 0 )
(command "insert" "Res" '(295 -91) 1 1 0 )
(command "insert" "Res" '(291 -94) 1 1 0 )
(command "insert" "Res" '(294 -94) 1 1 0 )
(command "insert" "Res" '(296 -94) 1 1 0 )
(command "insert" "Res" '(295 -95) 1 1 0 )
(command "insert" "Res" '(293 -96) 1 1 0 )
(command "insert" "Res" '(297 -95) 1 1 0 )
(command "insert" "Res" '(291 -91) 1 1 0 )
(command "insert" "Res" '(291 -90) 1 1 0 )
(command "insert" "Res" '(294 -90) 1 1 0 )
(command "insert" "Res" '(292 -97) 1 1 0 )
(command "insert" "Res" '(296 -90) 1 1 0 )
(command "insert" "Res" '(298 -98) 1 1 0 )
(command "insert" "Res" '(292 -93) 1 1 0 )
(command "insert" "Res" '(291 -98) 1 1 0 )
(command "insert" "Res" '(297 -97) 1 1 0 )
(command "insert" "Res" '(295 -90) 1 1 0 )
(command "insert" "Res" '(299 -98) 1 1 0 )
(command "insert" "Res" '(294 -95) 1 1 0 )
(command "insert" "Res" '(296 -95) 1 1 0 )
(command "insert" "Res" '(299 -93) 1 1 0 )
(command "insert" "Res" '(292 -90) 1 1 0 )
(command "insert" "Res" '(295 -94) 1 1 0 )
(command "insert" "Res" '(297 -94) 1 1 0 )
(command "insert" "Res" '(291 -93) 1 1 0 )
(command "insert" "Res" '(294 -91) 1 1 0 )
(command "insert" "Res" '(292 -98) 1 1 0 )
(command "insert" "Res" '(296 -91) 1 1 0 )
(command "insert" "Res" '(298 -93) 1 1 0 )
(command "insert" "Res" '(293 -92) 1 1 0 )
(command "insert" "Res" '(292 -94) 1 1 0 )
(command "insert" "Res" '(297 -96) 1 1 0 )
(command "insert" "Res" '(293 -95) 1 1 0 )
(command "insert" "Res" '(294 -92) 1 1 0 )
(command "insert" "Res" '(291 -97) 1 1 0 )
(command "insert" "Res" '(292 -91) 1 1 0 )
(command "insert" "Res" '(297 -93) 1 1 0 )
(command "insert" "Res" '(299 -97) 1 1 0 )
(command "insert" "Res" '(291 -92) 1 1 0 )
(command "insert" "Res" '(293 -90) 1 1 0 )
(command "insert" "Res" '(296 -92) 1 1 0 )
(command "insert" "Res" '(298 -96) 1 1 0 )
(command "insert" "Res" '(292 -95) 1 1 0 )
(command "insert" "Res" '(295 -93) 1 1 0 )
(command "insert" "Res" '(293 -98) 1 1 0 )
(command "layer" "m" "edge" "" )
(command "insert" "edge" '(191 -28) 1 1 0 )
(command "insert" "edge" '(186 -27) 1 1 0 )
(command "insert" "edge" '(189 -29) 1 1 0 )
(command "insert" "edge" '(183 -28) 1 1 0 )
(command "insert" "edge" '(184 -29) 1 1 0 )
(command "insert" "edge" '(188 -28) 1 1 0 )
(command "insert" "edge" '(179 -27) 1 1 0 )
(command "insert" "edge" '(191 -27) 1 1 0 )
(command "insert" "edge" '(178 -29) 1 1 0 )
(command "insert" "edge" '(180 -28) 1 1 0 )
(command "insert" "edge" '(182 -28) 1 1 0 )
(command "insert" "edge" '(183 -27) 1 1 0 )
(command "insert" "edge" '(187 -27) 1 1 0 )
(command "insert" "edge" '(189 -28) 1 1 0 )
(command "insert" "edge" '(194 -28) 1 1 0 )
(command "insert" "edge" '(188 -29) 1 1 0 )
(command "insert" "edge" '(177 -29) 1 1 0 )
(command "insert" "edge" '(181 -28) 1 1 0 )
(command "insert" "edge" '(193 -27) 1 1 0 )
(command "insert" "edge" '(186 -28) 1 1 0 )
(command "insert" "edge" '(179 -29) 1 1 0 )
(command "insert" "edge" '(180 -29) 1 1 0 )
(command "insert" "edge" '(185 -27) 1 1 0 )
(command "insert" "edge" '(189 -27) 1 1 0 )
(command "insert" "edge" '(186 -29) 1 1 0 )
(command "insert" "edge" '(187 -29) 1 1 0 )
(command "insert" "edge" '(190 -27) 1 1 0 )
(command "insert" "edge" '(192 -27) 1 1 0 )
(command "insert" "edge" '(193 -28) 1 1 0 )
(command "insert" "edge" '(177 -28) 1 1 0 )
(command "insert" "edge" '(181 -27) 1 1 0 )
(command "insert" "edge" '(182 -27) 1 1 0 )
(command "insert" "edge" '(184 -27) 1 1 0 )
(command "insert" "edge" '(178 -27) 1 1 0 )
(command "insert" "edge" '(181 -29) 1 1 0 )
(command "insert" "edge" '(190 -28) 1 1 0 )
(command "insert" "edge" '(188 -27) 1 1 0 )
(command "insert" "edge" '(193 -29) 1 1 0 )
(command "insert" "edge" '(187 -28) 1 1 0 )
(command "insert" "edge" '(180 -27) 1 1 0 )
(command "insert" "edge" '(192 -28) 1 1 0 )
(command "insert" "edge" '(185 -29) 1 1 0 )
(command "insert" "edge" '(191 -29) 1 1 0 )
(command "insert" "edge" '(179 -28) 1 1 0 )
(command "insert" "edge" '(184 -28) 1 1 0 )
(command "insert" "edge" '(194 -29) 1 1 0 )
(command "insert" "edge" '(192 -29) 1 1 0 )
(command "insert" "edge" '(183 -29) 1 1 0 )
(command "insert" "edge" '(190 -29) 1 1 0 )
(command "insert" "edge" '(178 -28) 1 1 0 )
(command "insert" "edge" '(182 -29) 1 1 0 )
(command "insert" "edge" '(177 -27) 1 1 0 )
(command "insert" "edge" '(194 -27) 1 1 0 )
(command "insert" "edge" '(185 -28) 1 1 0 )
(command "layer" "m" "mroads" "" )
(command "insert" "mroads" '(5 -31) 1 1 0 )
(command "insert" "mroads" '(66 -31) 1 1 0 )
(command "insert" "mroads" '(6 -28) 1 1 0 )
(command "insert" "mroads" '(67 -30) 1 1 0 )
(command "insert" "mroads" '(7 -25) 1 1 0 )
(command "insert" "mroads" '(22 -19) 1 1 0 )
(command "insert" "mroads" '(18 -19) 1 1 0 )
(command "insert" "mroads" '(38 -21) 1 1 0 )
(command "insert" "mroads" '(114 -31) 1 1 0 )
(command "insert" "mroads" '(13 -32) 1 1 0 )
(command "insert" "mroads" '(35 -15) 1 1 0 )
(command "insert" "mroads" '(14 -31) 1 1 0 )
(command "insert" "mroads" '(15 -30) 1 1 0 )
(command "insert" "mroads" '(35 -21) 1 1 0 )
(command "insert" "mroads" '(12 -17) 1 1 0 )
(command "insert" "mroads" '(36 -22) 1 1 0 )
(command "insert" "mroads" '(1 -28) 1 1 0 )
(command "insert" "mroads" '(40 -22) 1 1 0 )
(command "insert" "mroads" '(39 -16) 1 1 0 )
(command "insert" "mroads" '(63 -30) 1 1 0 )
(command "insert" "mroads" '(37 -23) 1 1 0 )
(command "insert" "mroads" '(2 -27) 1 1 0 )
(command "insert" "mroads" '(109 -32) 1 1 0 )
(command "insert" "mroads" '(29 -17) 1 1 0 )
(command "insert" "mroads" '(31 -15) 1 1 0 )
(command "insert" "mroads" '(5 -24) 1 1 0 )
(command "insert" "mroads" '(20 -32) 1 1 0 )
(command "insert" "mroads" '(6 -23) 1 1 0 )
(command "insert" "mroads" '(30 -16) 1 1 0 )
(command "insert" "mroads" '(28 -32) 1 1 0 )
(command "insert" "mroads" '(7 -22) 1 1 0 )
(command "insert" "mroads" '(41 -23) 1 1 0 )
(command "insert" "mroads" '(42 -31) 1 1 0 )
(command "insert" "mroads" '(23 -19) 1 1 0 )
(command "insert" "mroads" '(21 -15) 1 1 0 )
(command "insert" "mroads" '(43 -30) 1 1 0 )
(command "insert" "mroads" '(116 -32) 1 1 0 )
(command "insert" "mroads" '(8 -18) 1 1 0 )
(command "insert" "mroads" '(11 -15) 1 1 0 )
(command "insert" "mroads" '(35 -26) 1 1 0 )
(command "insert" "mroads" '(9 -19) 1 1 0 )
(command "insert" "mroads" '(36 -29) 1 1 0 )
(command "insert" "mroads" '(1 -21) 1 1 0 )
(command "insert" "mroads" '(25 -16) 1 1 0 )
(command "insert" "mroads" '(29 -20) 1 1 0 )
(command "insert" "mroads" '(37 -16) 1 1 0 )
(command "insert" "mroads" '(98 -30) 1 1 0 )
(command "insert" "mroads" '(38 -31) 1 1 0 )
(command "insert" "mroads" '(99 -31) 1 1 0 )
(command "insert" "mroads" '(39 -30) 1 1 0 )
(command "insert" "mroads" '(3 -17) 1 1 0 )
(command "insert" "mroads" '(19 -18) 1 1 0 )
(command "insert" "mroads" '(7 -15) 1 1 0 )
(command "insert" "mroads" '(31 -18) 1 1 0 )
(command "insert" "mroads" '(46 -30) 1 1 0 )
(command "insert" "mroads" '(6 -32) 1 1 0 )
(command "insert" "mroads" '(34 -32) 1 1 0 )
(command "insert" "mroads" '(32 -16) 1 1 0 )
(command "insert" "mroads" '(94 -30) 1 1 0 )
(command "insert" "mroads" '(18 -31) 1 1 0 )
(command "insert" "mroads" '(42 -32) 1 1 0 )
(command "insert" "mroads" '(86 -32) 1 1 0 )
(command "insert" "mroads" '(34 -26) 1 1 0 )
(command "insert" "mroads" '(8 -25) 1 1 0 )
(command "insert" "mroads" '(94 -32) 1 1 0 )
(command "insert" "mroads" '(9 -20) 1 1 0 )
(command "insert" "mroads" '(10 -19) 1 1 0 )
(command "insert" "mroads" '(37 -25) 1 1 0 )
(command "insert" "mroads" '(26 -30) 1 1 0 )
(command "insert" "mroads" '(41 -28) 1 1 0 )
(command "insert" "mroads" '(38 -22) 1 1 0 )
(command "insert" "mroads" '(27 -31) 1 1 0 )
(command "insert" "mroads" '(6 -30) 1 1 0 )
(command "insert" "mroads" '(39 -23) 1 1 0 )
(command "insert" "mroads" '(88 -31) 1 1 0 )
(command "insert" "mroads" '(74 -30) 1 1 0 )
(command "insert" "mroads" '(89 -30) 1 1 0 )
(command "insert" "mroads" '(3 -22) 1 1 0 )
(command "insert" "mroads" '(75 -31) 1 1 0 )
(command "insert" "mroads" '(4 -17) 1 1 0 )
(command "insert" "mroads" '(5 -20) 1 1 0 )
(command "insert" "mroads" '(6 -27) 1 1 0 )
(command "insert" "mroads" '(21 -17) 1 1 0 )
(command "insert" "mroads" '(17 -17) 1 1 0 )
(command "insert" "mroads" '(22 -30) 1 1 0 )
(command "insert" "mroads" '(33 -22) 1 1 0 )
(command "insert" "mroads" '(23 -31) 1 1 0 )
(command "insert" "mroads" '(12 -32) 1 1 0 )
(command "insert" "mroads" '(34 -21) 1 1 0 )
(command "insert" "mroads" '(70 -30) 1 1 0 )
(command "insert" "mroads" '(85 -30) 1 1 0 )
(command "insert" "mroads" '(48 -32) 1 1 0 )
(command "insert" "mroads" '(71 -31) 1 1 0 )
(command "insert" "mroads" '(34 -15) 1 1 0 )
(command "insert" "mroads" '(11 -19) 1 1 0 )
(command "insert" "mroads" '(100 -32) 1 1 0 )
(command "insert" "mroads" '(27 -20) 1 1 0 )
(command "insert" "mroads" '(1 -25) 1 1 0 )
(command "insert" "mroads" '(108 -32) 1 1 0 )
(command "insert" "mroads" '(2 -30) 1 1 0 )
(command "insert" "mroads" '(3 -31) 1 1 0 )
(command "insert" "mroads" '(64 -31) 1 1 0 )
(command "insert" "mroads" '(4 -24) 1 1 0 )
(command "insert" "mroads" '(19 -32) 1 1 0 )
(command "insert" "mroads" '(62 -31) 1 1 0 )
(command "insert" "mroads" '(50 -30) 1 1 0 )
(command "insert" "mroads" '(65 -30) 1 1 0 )
(command "insert" "mroads" '(5 -29) 1 1 0 )
(command "insert" "mroads" '(27 -32) 1 1 0 )
(command "insert" "mroads" '(6 -18) 1 1 0 )
(command "insert" "mroads" '(101 -32) 1 1 0 )
(command "insert" "mroads" '(112 -31) 1 1 0 )
(command "insert" "mroads" '(41 -21) 1 1 0 )
(command "insert" "mroads" '(22 -17) 1 1 0 )
(command "insert" "mroads" '(25 -15) 1 1 0 )
(command "insert" "mroads" '(79 -32) 1 1 0 )
(command "insert" "mroads" '(18 -17) 1 1 0 )
(command "insert" "mroads" '(23 -20) 1 1 0 )
(command "insert" "mroads" '(6 -21) 1 1 0 )
(command "insert" "mroads" '(115 -32) 1 1 0 )
(command "insert" "mroads" '(60 -31) 1 1 0 )
(command "insert" "mroads" '(61 -30) 1 1 0 )
(command "insert" "mroads" '(35 -23) 1 1 0 )
(command "insert" "mroads" '(24 -16) 1 1 0 )
(command "insert" "mroads" '(36 -16) 1 1 0 )
(command "insert" "mroads" '(108 -31) 1 1 0 )
(command "insert" "mroads" '(37 -21) 1 1 0 )
(command "insert" "mroads" '(2 -25) 1 1 0 )
(command "insert" "mroads" '(109 -30) 1 1 0 )
(command "insert" "mroads" '(41 -30) 1 1 0 )
(command "insert" "mroads" '(38 -26) 1 1 0 )
(command "insert" "mroads" '(40 -18) 1 1 0 )
(command "insert" "mroads" '(114 -32) 1 1 0 )
(command "insert" "mroads" '(116 -30) 1 1 0 )
(command "insert" "mroads" '(40 -31) 1 1 0 )
(command "insert" "mroads" '(111 -31) 1 1 0 )
(command "insert" "mroads" '(19 -15) 1 1 0 )
(command "insert" "mroads" '(7 -16) 1 1 0 )
(command "insert" "mroads" '(5 -32) 1 1 0 )
(command "insert" "mroads" '(33 -32) 1 1 0 )
(command "insert" "mroads" '(41 -32) 1 1 0 )
(command "insert" "mroads" '(41 -19) 1 1 0 )
(command "insert" "mroads" '(85 -32) 1 1 0 )
(command "insert" "mroads" '(9 -15) 1 1 0 )
(command "insert" "mroads" '(33 -26) 1 1 0 )
(command "insert" "mroads" '(22 -31) 1 1 0 )
(command "insert" "mroads" '(93 -32) 1 1 0 )
(command "insert" "mroads" '(8 -20) 1 1 0 )
(command "insert" "mroads" '(80 -32) 1 1 0 )
(command "insert" "mroads" '(35 -28) 1 1 0 )
(command "insert" "mroads" '(9 -17) 1 1 0 )
(command "insert" "mroads" '(96 -30) 1 1 0 )
(command "insert" "mroads" '(36 -31) 1 1 0 )
(command "insert" "mroads" '(15 -15) 1 1 0 )
(command "insert" "mroads" '(97 -31) 1 1 0 )
(command "insert" "mroads" '(37 -30) 1 1 0 )
(command "insert" "mroads" '(38 -29) 1 1 0 )
(command "insert" "mroads" '(83 -31) 1 1 0 )
(command "insert" "mroads" '(39 -24) 1 1 0 )
(command "insert" "mroads" '(5 -15) 1 1 0 )
(command "insert" "mroads" '(3 -19) 1 1 0 )
(command "insert" "mroads" '(4 -20) 1 1 0 )
(command "insert" "mroads" '(19 -20) 1 1 0 )
(command "insert" "mroads" '(92 -30) 1 1 0 )
(command "insert" "mroads" '(16 -31) 1 1 0 )
(command "insert" "mroads" '(93 -31) 1 1 0 )
(command "insert" "mroads" '(17 -30) 1 1 0 )
(command "insert" "mroads" '(32 -18) 1 1 0 )
(command "insert" "mroads" '(11 -32) 1 1 0 )
(command "insert" "mroads" '(33 -19) 1 1 0 )
(command "insert" "mroads" '(40 -29) 1 1 0 )
(command "insert" "mroads" '(8 -27) 1 1 0 )
(command "insert" "mroads" '(63 -32) 1 1 0 )
(command "insert" "mroads" '(46 -32) 1 1 0 )
(command "insert" "mroads" '(24 -30) 1 1 0 )
(command "insert" "mroads" '(14 -17) 1 1 0 )
(command "insert" "mroads" '(71 -32) 1 1 0 )
(command "insert" "mroads" '(10 -17) 1 1 0 )
(command "insert" "mroads" '(25 -31) 1 1 0 )
(command "insert" "mroads" '(99 -32) 1 1 0 )
(command "insert" "mroads" '(70 -31) 1 1 0 )
(command "insert" "mroads" '(107 -32) 1 1 0 )
(command "insert" "mroads" '(38 -20) 1 1 0 )
(command "insert" "mroads" '(12 -31) 1 1 0 )
(command "insert" "mroads" '(27 -17) 1 1 0 )
(command "insert" "mroads" '(39 -17) 1 1 0 )
(command "insert" "mroads" '(13 -30) 1 1 0 )
(command "insert" "mroads" '(41 -24) 1 1 0 )
(command "insert" "mroads" '(3 -24) 1 1 0 )
(command "insert" "mroads" '(56 -32) 1 1 0 )
(command "insert" "mroads" '(4 -19) 1 1 0 )
(command "insert" "mroads" '(26 -32) 1 1 0 )
(command "insert" "mroads" '(5 -18) 1 1 0 )
(command "insert" "mroads" '(20 -30) 1 1 0 )
(command "insert" "mroads" '(40 -19) 1 1 0 )
(command "insert" "mroads" '(21 -31) 1 1 0 )
(command "insert" "mroads" '(78 -32) 1 1 0 )
(command "insert" "mroads" '(7 -28) 1 1 0 )
(command "insert" "mroads" '(18 -20) 1 1 0 )
(command "insert" "mroads" '(33 -20) 1 1 0 )
(command "insert" "mroads" '(69 -31) 1 1 0 )
(command "insert" "mroads" '(34 -19) 1 1 0 )
(command "insert" "mroads" '(32 -15) 1 1 0 )
(command "insert" "mroads" '(49 -30) 1 1 0 )
(command "insert" "mroads" '(64 -32) 1 1 0 )
(command "insert" "mroads" '(35 -16) 1 1 0 )
(command "insert" "mroads" '(38 -15) 1 1 0 )
(command "insert" "mroads" '(77 -32) 1 1 0 )
(command "insert" "mroads" '(1 -31) 1 1 0 )
(command "insert" "mroads" '(28 -17) 1 1 0 )
(command "insert" "mroads" '(2 -28) 1 1 0 )
(command "insert" "mroads" '(48 -30) 1 1 0 )
(command "insert" "mroads" '(113 -32) 1 1 0 )
(command "insert" "mroads" '(49 -31) 1 1 0 )
(command "insert" "mroads" '(4 -26) 1 1 0 )
(command "insert" "mroads" '(28 -15) 1 1 0 )
(command "insert" "mroads" '(5 -27) 1 1 0 )
(command "insert" "mroads" '(40 -26) 1 1 0 )
(command "insert" "mroads" '(4 -32) 1 1 0 )
(command "insert" "mroads" '(7 -21) 1 1 0 )
(command "insert" "mroads" '(18 -15) 1 1 0 )
(command "insert" "mroads" '(40 -32) 1 1 0 )
(command "insert" "mroads" '(84 -30) 1 1 0 )
(command "insert" "mroads" '(58 -31) 1 1 0 )
(command "insert" "mroads" '(44 -30) 1 1 0 )
(command "insert" "mroads" '(59 -30) 1 1 0 )
(command "insert" "mroads" '(92 -32) 1 1 0 )
(command "insert" "mroads" '(45 -31) 1 1 0 )
(command "insert" "mroads" '(6 -17) 1 1 0 )
(command "insert" "mroads" '(106 -31) 1 1 0 )
(command "insert" "mroads" '(35 -25) 1 1 0 )
(command "insert" "mroads" '(24 -18) 1 1 0 )
(command "insert" "mroads" '(107 -30) 1 1 0 )
(command "insert" "mroads" '(36 -18) 1 1 0 )
(command "insert" "mroads" '(25 -19) 1 1 0 )
(command "insert" "mroads" '(13 -16) 1 1 0 )
(command "insert" "mroads" '(37 -19) 1 1 0 )
(command "insert" "mroads" '(2 -23) 1 1 0 )
(command "insert" "mroads" '(38 -24) 1 1 0 )
(command "insert" "mroads" '(39 -29) 1 1 0 )
(command "insert" "mroads" '(54 -31) 1 1 0 )
(command "insert" "mroads" '(115 -31) 1 1 0 )
(command "insert" "mroads" '(55 -30) 1 1 0 )
(command "insert" "mroads" '(22 -20) 1 1 0 )
(command "insert" "mroads" '(30 -20) 1 1 0 )
(command "insert" "mroads" '(19 -17) 1 1 0 )
(command "insert" "mroads" '(102 -31) 1 1 0 )
(command "insert" "mroads" '(7 -18) 1 1 0 )
(command "insert" "mroads" '(31 -17) 1 1 0 )
(command "insert" "mroads" '(103 -30) 1 1 0 )
(command "insert" "mroads" '(10 -32) 1 1 0 )
(command "insert" "mroads" '(22 -32) 1 1 0 )
(command "insert" "mroads" '(18 -32) 1 1 0 )
(command "insert" "mroads" '(33 -24) 1 1 0 )
(command "insert" "mroads" '(62 -32) 1 1 0 )
(command "insert" "mroads" '(110 -30) 1 1 0 )
(command "insert" "mroads" '(34 -31) 1 1 0 )
(command "insert" "mroads" '(8 -22) 1 1 0 )
(command "insert" "mroads" '(57 -31) 1 1 0 )
(command "insert" "mroads" '(70 -32) 1 1 0 )
(command "insert" "mroads" '(35 -30) 1 1 0 )
(command "insert" "mroads" '(98 -32) 1 1 0 )
(command "insert" "mroads" '(36 -25) 1 1 0 )
(command "insert" "mroads" '(10 -20) 1 1 0 )
(command "insert" "mroads" '(25 -20) 1 1 0 )
(command "insert" "mroads" '(82 -31) 1 1 0 )
(command "insert" "mroads" '(106 -32) 1 1 0 )
(command "insert" "mroads" '(37 -28) 1 1 0 )
(command "insert" "mroads" '(26 -19) 1 1 0 )
(command "insert" "mroads" '(38 -19) 1 1 0 )
(command "insert" "mroads" '(3 -15) 1 1 0 )
(command "insert" "mroads" '(39 -26) 1 1 0 )
(command "insert" "mroads" '(51 -31) 1 1 0 )
(command "insert" "mroads" '(7 -20) 1 1 0 )
(command "insert" "mroads" '(3 -21) 1 1 0 )
(command "insert" "mroads" '(25 -32) 1 1 0 )
(command "insert" "mroads" '(90 -30) 1 1 0 )
(command "insert" "mroads" '(30 -31) 1 1 0 )
(command "insert" "mroads" '(4 -22) 1 1 0 )
(command "insert" "mroads" '(91 -31) 1 1 0 )
(command "insert" "mroads" '(31 -30) 1 1 0 )
(command "insert" "mroads" '(5 -23) 1 1 0 )
(command "insert" "mroads" '(20 -17) 1 1 0 )
(command "insert" "mroads" '(16 -17) 1 1 0 )
(command "insert" "mroads" '(21 -20) 1 1 0 )
(command "insert" "mroads" '(32 -20) 1 1 0 )
(command "insert" "mroads" '(33 -17) 1 1 0 )
(command "insert" "mroads" '(34 -22) 1 1 0 )
(command "insert" "mroads" '(8 -29) 1 1 0 )
(command "insert" "mroads" '(86 -30) 1 1 0 )
(command "insert" "mroads" '(10 -31) 1 1 0 )
(command "insert" "mroads" '(40 -25) 1 1 0 )
(command "insert" "mroads" '(87 -31) 1 1 0 )
(command "insert" "mroads" '(11 -30) 1 1 0 )
(command "insert" "mroads" '(76 -32) 1 1 0 )
(command "insert" "mroads" '(27 -19) 1 1 0 )
(command "insert" "mroads" '(39 -19) 1 1 0 )
(command "insert" "mroads" '(28 -20) 1 1 0 )
(command "insert" "mroads" '(3 -26) 1 1 0 )
(command "insert" "mroads" '(40 -15) 1 1 0 )
(command "insert" "mroads" '(4 -29) 1 1 0 )
(command "insert" "mroads" '(19 -31) 1 1 0 )
(command "insert" "mroads" '(7 -26) 1 1 0 )
(command "insert" "mroads" '(5 -16) 1 1 0 )
(command "insert" "mroads" '(3 -32) 1 1 0 )
(command "insert" "mroads" '(66 -30) 1 1 0 )
(command "insert" "mroads" '(40 -21) 1 1 0 )
(command "insert" "mroads" '(67 -31) 1 1 0 )
(command "insert" "mroads" '(7 -30) 1 1 0 )
(command "insert" "mroads" '(22 -18) 1 1 0 )
(command "insert" "mroads" '(55 -32) 1 1 0 )
(command "insert" "mroads" '(18 -18) 1 1 0 )
(command "insert" "mroads" '(83 -32) 1 1 0 )
(command "insert" "mroads" '(114 -30) 1 1 0 )
(command "insert" "mroads" '(34 -17) 1 1 0 )
(command "insert" "mroads" '(91 -32) 1 1 0 )
(command "insert" "mroads" '(14 -30) 1 1 0 )
(command "insert" "mroads" '(36 -15) 1 1 0 )
(command "insert" "mroads" '(15 -31) 1 1 0 )
(command "insert" "mroads" '(35 -18) 1 1 0 )
(command "insert" "mroads" '(12 -16) 1 1 0 )
(command "insert" "mroads" '(36 -21) 1 1 0 )
(command "insert" "mroads" '(1 -29) 1 1 0 )
(command "insert" "mroads" '(63 -31) 1 1 0 )
(command "insert" "mroads" '(28 -19) 1 1 0 )
(command "insert" "mroads" '(2 -26) 1 1 0 )
(command "insert" "mroads" '(26 -15) 1 1 0 )
(command "insert" "mroads" '(12 -15) 1 1 0 )
(command "insert" "mroads" '(29 -18) 1 1 0 )
(command "insert" "mroads" '(5 -25) 1 1 0 )
(command "insert" "mroads" '(16 -15) 1 1 0 )
(command "insert" "mroads" '(6 -22) 1 1 0 )
(command "insert" "mroads" '(30 -19) 1 1 0 )
(command "insert" "mroads" '(41 -25) 1 1 0 )
(command "insert" "mroads" '(56 -31) 1 1 0 )
(command "insert" "mroads" '(9 -32) 1 1 0 )
(command "insert" "mroads" '(42 -30) 1 1 0 )
(command "insert" "mroads" '(23 -16) 1 1 0 )
(command "insert" "mroads" '(43 -31) 1 1 0 )
(command "insert" "mroads" '(17 -32) 1 1 0 )
(command "insert" "mroads" '(22 -15) 1 1 0 )
(command "insert" "mroads" '(61 -32) 1 1 0 )
(command "insert" "mroads" '(52 -30) 1 1 0 )
(command "insert" "mroads" '(105 -30) 1 1 0 )
(command "insert" "mroads" '(69 -32) 1 1 0 )
(command "insert" "mroads" '(34 -24) 1 1 0 )
(command "insert" "mroads" '(8 -17) 1 1 0 )
(command "insert" "mroads" '(97 -32) 1 1 0 )
(command "insert" "mroads" '(35 -27) 1 1 0 )
(command "insert" "mroads" '(24 -20) 1 1 0 )
(command "insert" "mroads" '(105 -32) 1 1 0 )
(command "insert" "mroads" '(36 -28) 1 1 0 )
(command "insert" "mroads" '(1 -22) 1 1 0 )
(command "insert" "mroads" '(40 -23) 1 1 0 )
(command "insert" "mroads" '(37 -17) 1 1 0 )
(command "insert" "mroads" '(2 -21) 1 1 0 )
(command "insert" "mroads" '(38 -30) 1 1 0 )
(command "insert" "mroads" '(53 -30) 1 1 0 )
(command "insert" "mroads" '(112 -32) 1 1 0 )
(command "insert" "mroads" '(39 -31) 1 1 0 )
(command "insert" "mroads" '(100 -31) 1 1 0 )
(command "insert" "mroads" '(24 -32) 1 1 0 )
(command "insert" "mroads" '(101 -30) 1 1 0 )
(command "insert" "mroads" '(32 -32) 1 1 0 )
(command "insert" "mroads" '(19 -19) 1 1 0 )
(command "insert" "mroads" '(31 -19) 1 1 0 )
(command "insert" "mroads" '(20 -20) 1 1 0 )
(command "insert" "mroads" '(47 -31) 1 1 0 )
(command "insert" "mroads" '(32 -31) 1 1 0 )
(command "insert" "mroads" '(18 -30) 1 1 0 )
(command "insert" "mroads" '(33 -30) 1 1 0 )
(command "insert" "mroads" '(34 -29) 1 1 0 )
(command "insert" "mroads" '(8 -24) 1 1 0 )
(command "insert" "mroads" '(39 -32) 1 1 0 )
(command "insert" "mroads" '(80 -31) 1 1 0 )
(command "insert" "mroads" '(81 -30) 1 1 0 )
(command "insert" "mroads" '(36 -27) 1 1 0 )
(command "insert" "mroads" '(10 -18) 1 1 0 )
(command "insert" "mroads" '(75 -32) 1 1 0 )
(command "insert" "mroads" '(37 -26) 1 1 0 )
(command "insert" "mroads" '(26 -17) 1 1 0 )
(command "insert" "mroads" '(38 -17) 1 1 0 )
(command "insert" "mroads" '(39 -20) 1 1 0 )
(command "insert" "mroads" '(88 -30) 1 1 0 )
(command "insert" "mroads" '(28 -31) 1 1 0 )
(command "insert" "mroads" '(89 -31) 1 1 0 )
(command "insert" "mroads" '(29 -30) 1 1 0 )
(command "insert" "mroads" '(3 -23) 1 1 0 )
(command "insert" "mroads" '(4 -16) 1 1 0 )
(command "insert" "mroads" '(2 -32) 1 1 0 )
(command "insert" "mroads" '(76 -31) 1 1 0 )
(command "insert" "mroads" '(5 -21) 1 1 0 )
(command "insert" "mroads" '(20 -19) 1 1 0 )
(command "insert" "mroads" '(33 -29) 1 1 0 )
(command "insert" "mroads" '(77 -30) 1 1 0 )
(command "insert" "mroads" '(40 -16) 1 1 0 )
(command "insert" "mroads" '(21 -18) 1 1 0 )
(command "insert" "mroads" '(54 -32) 1 1 0 )
(command "insert" "mroads" '(33 -23) 1 1 0 )
(command "insert" "mroads" '(90 -32) 1 1 0 )
(command "insert" "mroads" '(34 -20) 1 1 0 )
(command "insert" "mroads" '(8 -31) 1 1 0 )
(command "insert" "mroads" '(95 -31) 1 1 0 )
(command "insert" "mroads" '(85 -31) 1 1 0 )
(command "insert" "mroads" '(9 -30) 1 1 0 )
(command "insert" "mroads" '(104 -32) 1 1 0 )
(command "insert" "mroads" '(15 -16) 1 1 0 )
(command "insert" "mroads" '(11 -16) 1 1 0 )
(command "insert" "mroads" '(1 -26) 1 1 0 )
(command "insert" "mroads" '(6 -31) 1 1 0 )
(command "insert" "mroads" '(73 -31) 1 1 0 )
(command "insert" "mroads" '(3 -28) 1 1 0 )
(command "insert" "mroads" '(64 -30) 1 1 0 )
(command "insert" "mroads" '(4 -31) 1 1 0 )
(command "insert" "mroads" '(65 -31) 1 1 0 )
(command "insert" "mroads" '(5 -30) 1 1 0 )
(command "insert" "mroads" '(6 -29) 1 1 0 )
(command "insert" "mroads" '(112 -30) 1 1 0 )
(command "insert" "mroads" '(8 -32) 1 1 0 )
(command "insert" "mroads" '(41 -22) 1 1 0 )
(command "insert" "mroads" '(22 -16) 1 1 0 )
(command "insert" "mroads" '(113 -31) 1 1 0 )
(command "insert" "mroads" '(18 -16) 1 1 0 )
(command "insert" "mroads" '(16 -32) 1 1 0 )
(command "insert" "mroads" '(60 -32) 1 1 0 )
(command "insert" "mroads" '(68 -32) 1 1 0 )
(command "insert" "mroads" '(96 -32) 1 1 0 )
(command "insert" "mroads" '(60 -30) 1 1 0 )
(command "insert" "mroads" '(61 -31) 1 1 0 )
(command "insert" "mroads" '(35 -20) 1 1 0 )
(command "insert" "mroads" '(24 -15) 1 1 0 )
(command "insert" "mroads" '(36 -23) 1 1 0 )
(command "insert" "mroads" '(108 -30) 1 1 0 )
(command "insert" "mroads" '(37 -22) 1 1 0 )
(command "insert" "mroads" '(2 -24) 1 1 0 )
(command "insert" "mroads" '(109 -31) 1 1 0 )
(command "insert" "mroads" '(29 -16) 1 1 0 )
(command "insert" "mroads" '(30 -15) 1 1 0 )
(command "insert" "mroads" '(6 -26) 1 1 0 )
(command "insert" "mroads" '(25 -18) 1 1 0 )
(command "insert" "mroads" '(40 -30) 1 1 0 )
(command "insert" "mroads" '(30 -17) 1 1 0 )
(command "insert" "mroads" '(7 -17) 1 1 0 )
(command "insert" "mroads" '(31 -20) 1 1 0 )
(command "insert" "mroads" '(20 -15) 1 1 0 )
(command "insert" "mroads" '(23 -18) 1 1 0 )
(command "insert" "mroads" '(47 -32) 1 1 0 )
(command "insert" "mroads" '(33 -27) 1 1 0 )
(command "insert" "mroads" '(38 -32) 1 1 0 )
(command "insert" "mroads" '(10 -15) 1 1 0 )
(command "insert" "mroads" '(8 -19) 1 1 0 )
(command "insert" "mroads" '(35 -29) 1 1 0 )
(command "insert" "mroads" '(9 -18) 1 1 0 )
(command "insert" "mroads" '(74 -32) 1 1 0 )
(command "insert" "mroads" '(102 -30) 1 1 0 )
(command "insert" "mroads" '(36 -30) 1 1 0 )
(command "insert" "mroads" '(51 -30) 1 1 0 )
(command "insert" "mroads" '(82 -32) 1 1 0 )
(command "insert" "mroads" '(37 -31) 1 1 0 )
(command "insert" "mroads" '(26 -20) 1 1 0 )
(command "insert" "mroads" '(41 -29) 1 1 0 )
(command "insert" "mroads" '(98 -31) 1 1 0 )
(command "insert" "mroads" '(38 -28) 1 1 0 )
(command "insert" "mroads" '(6 -25) 1 1 0 )
(command "insert" "mroads" '(99 -30) 1 1 0 )
(command "insert" "mroads" '(39 -25) 1 1 0 )
(command "insert" "mroads" '(3 -16) 1 1 0 )
(command "insert" "mroads" '(1 -32) 1 1 0 )
(command "insert" "mroads" '(6 -15) 1 1 0 )
(command "insert" "mroads" '(46 -31) 1 1 0 )
(command "insert" "mroads" '(53 -32) 1 1 0 )
(command "insert" "mroads" '(16 -30) 1 1 0 )
(command "insert" "mroads" '(47 -30) 1 1 0 )
(command "insert" "mroads" '(17 -31) 1 1 0 )
(command "insert" "mroads" '(32 -17) 1 1 0 )
(command "insert" "mroads" '(41 -18) 1 1 0 )
(command "insert" "mroads" '(89 -32) 1 1 0 )
(command "insert" "mroads" '(7 -24) 1 1 0 )
(command "insert" "mroads" '(94 -31) 1 1 0 )
(command "insert" "mroads" '(33 -28) 1 1 0 )
(command "insert" "mroads" '(95 -30) 1 1 0 )
(command "insert" "mroads" '(34 -27) 1 1 0 )
(command "insert" "mroads" '(8 -26) 1 1 0 )
(command "insert" "mroads" '(14 -16) 1 1 0 )
(command "insert" "mroads" '(10 -16) 1 1 0 )
(command "insert" "mroads" '(37 -24) 1 1 0 )
(command "insert" "mroads" '(68 -30) 1 1 0 )
(command "insert" "mroads" '(26 -31) 1 1 0 )
(command "insert" "mroads" '(38 -23) 1 1 0 )
(command "insert" "mroads" '(83 -30) 1 1 0 )
(command "insert" "mroads" '(27 -30) 1 1 0 )
(command "insert" "mroads" '(31 -31) 1 1 0 )
(command "insert" "mroads" '(39 -22) 1 1 0 )
(command "insert" "mroads" '(13 -31) 1 1 0 )
(command "insert" "mroads" '(74 -31) 1 1 0 )
(command "insert" "mroads" '(3 -25) 1 1 0 )
(command "insert" "mroads" '(75 -30) 1 1 0 )
(command "insert" "mroads" '(4 -18) 1 1 0 )
(command "insert" "mroads" '(62 -30) 1 1 0 )
(command "insert" "mroads" '(5 -19) 1 1 0 )
(command "insert" "mroads" '(23 -32) 1 1 0 )
(command "insert" "mroads" '(6 -24) 1 1 0 )
(command "insert" "mroads" '(21 -16) 1 1 0 )
(command "insert" "mroads" '(17 -16) 1 1 0 )
(command "insert" "mroads" '(7 -29) 1 1 0 )
(command "insert" "mroads" '(31 -32) 1 1 0 )
(command "insert" "mroads" '(59 -32) 1 1 0 )
(command "insert" "mroads" '(33 -21) 1 1 0 )
(command "insert" "mroads" '(23 -30) 1 1 0 )
(command "insert" "mroads" '(34 -18) 1 1 0 )
(command "insert" "mroads" '(67 -32) 1 1 0 )
(command "insert" "mroads" '(6 -20) 1 1 0 )
(command "insert" "mroads" '(111 -32) 1 1 0 )
(command "insert" "mroads" '(33 -15) 1 1 0 )
(command "insert" "mroads" '(71 -30) 1 1 0 )
(command "insert" "mroads" '(11 -18) 1 1 0 )
(command "insert" "mroads" '(35 -17) 1 1 0 )
(command "insert" "mroads" '(1 -24) 1 1 0 )
(command "insert" "mroads" '(39 -15) 1 1 0 )
(command "insert" "mroads" '(28 -16) 1 1 0 )
(command "insert" "mroads" '(2 -31) 1 1 0 )
(command "insert" "mroads" '(12 -30) 1 1 0 )
(command "insert" "mroads" '(41 -31) 1 1 0 )
(command "insert" "mroads" '(79 -31) 1 1 0 )
(command "insert" "mroads" '(3 -30) 1 1 0 )
(command "insert" "mroads" '(40 -17) 1 1 0 )
(command "insert" "mroads" '(4 -25) 1 1 0 )
(command "insert" "mroads" '(50 -31) 1 1 0 )
(command "insert" "mroads" '(5 -28) 1 1 0 )
(command "insert" "mroads" '(29 -15) 1 1 0 )
(command "insert" "mroads" '(6 -19) 1 1 0 )
(command "insert" "mroads" '(41 -20) 1 1 0 )
(command "insert" "mroads" '(58 -30) 1 1 0 )
(command "insert" "mroads" '(37 -32) 1 1 0 )
(command "insert" "mroads" '(59 -31) 1 1 0 )
(command "insert" "mroads" '(41 -16) 1 1 0 )
(command "insert" "mroads" '(45 -32) 1 1 0 )
(command "insert" "mroads" '(73 -32) 1 1 0 )
(command "insert" "mroads" '(106 -30) 1 1 0 )
(command "insert" "mroads" '(35 -22) 1 1 0 )
(command "insert" "mroads" '(24 -17) 1 1 0 )
(command "insert" "mroads" '(107 -31) 1 1 0 )
(command "insert" "mroads" '(81 -32) 1 1 0 )
(command "insert" "mroads" '(36 -17) 1 1 0 )
(command "insert" "mroads" '(13 -17) 1 1 0 )
(command "insert" "mroads" '(37 -20) 1 1 0 )
(command "insert" "mroads" '(2 -22) 1 1 0 )
(command "insert" "mroads" '(72 -30) 1 1 0 )
(command "insert" "mroads" '(38 -27) 1 1 0 )
(command "insert" "mroads" '(54 -30) 1 1 0 )
(command "insert" "mroads" '(34 -23) 1 1 0 )
(command "insert" "mroads" '(55 -31) 1 1 0 )
(command "insert" "mroads" '(116 -31) 1 1 0 )
(command "insert" "mroads" '(52 -32) 1 1 0 )
(command "insert" "mroads" '(7 -19) 1 1 0 )
(command "insert" "mroads" '(103 -31) 1 1 0 )
(command "insert" "mroads" '(88 -32) 1 1 0 )
(command "insert" "mroads" '(84 -31) 1 1 0 )
(command "insert" "mroads" '(8 -15) 1 1 0 )
(command "insert" "mroads" '(33 -25) 1 1 0 )
(command "insert" "mroads" '(34 -30) 1 1 0 )
(command "insert" "mroads" '(8 -21) 1 1 0 )
(command "insert" "mroads" '(35 -31) 1 1 0 )
(command "insert" "mroads" '(9 -16) 1 1 0 )
(command "insert" "mroads" '(14 -15) 1 1 0 )
(command "insert" "mroads" '(40 -28) 1 1 0 )
(command "insert" "mroads" '(96 -31) 1 1 0 )
(command "insert" "mroads" '(36 -24) 1 1 0 )
(command "insert" "mroads" '(78 -31) 1 1 0 )
(command "insert" "mroads" '(82 -30) 1 1 0 )
(command "insert" "mroads" '(97 -30) 1 1 0 )
(command "insert" "mroads" '(37 -29) 1 1 0 )
(command "insert" "mroads" '(26 -18) 1 1 0 )
(command "insert" "mroads" '(38 -18) 1 1 0 )
(command "insert" "mroads" '(103 -32) 1 1 0 )
(command "insert" "mroads" '(39 -27) 1 1 0 )
(command "insert" "mroads" '(4 -15) 1 1 0 )
(command "insert" "mroads" '(7 -23) 1 1 0 )
(command "insert" "mroads" '(3 -18) 1 1 0 )
(command "insert" "mroads" '(30 -30) 1 1 0 )
(command "insert" "mroads" '(4 -21) 1 1 0 )
(command "insert" "mroads" '(79 -30) 1 1 0 )
(command "insert" "mroads" '(20 -16) 1 1 0 )
(command "insert" "mroads" '(92 -31) 1 1 0 )
(command "insert" "mroads" '(16 -16) 1 1 0 )
(command "insert" "mroads" '(30 -32) 1 1 0 )
(command "insert" "mroads" '(93 -30) 1 1 0 )
(command "insert" "mroads" '(58 -32) 1 1 0 )
(command "insert" "mroads" '(32 -19) 1 1 0 )
(command "insert" "mroads" '(33 -18) 1 1 0 )
(command "insert" "mroads" '(66 -32) 1 1 0 )
(command "insert" "mroads" '(110 -32) 1 1 0 )
(command "insert" "mroads" '(34 -25) 1 1 0 )
(command "insert" "mroads" '(8 -28) 1 1 0 )
(command "insert" "mroads" '(57 -30) 1 1 0 )
(command "insert" "mroads" '(24 -31) 1 1 0 )
(command "insert" "mroads" '(10 -30) 1 1 0 )
(command "insert" "mroads" '(25 -30) 1 1 0 )
(command "insert" "mroads" '(11 -31) 1 1 0 )
(command "insert" "mroads" '(72 -31) 1 1 0 )
(command "insert" "mroads" '(27 -16) 1 1 0 )
(command "insert" "mroads" '(49 -32) 1 1 0 )
(command "insert" "mroads" '(73 -30) 1 1 0 )
(command "insert" "mroads" '(3 -27) 1 1 0 )
(command "insert" "mroads" '(4 -28) 1 1 0 )
(command "insert" "mroads" '(41 -15) 1 1 0 )
(command "insert" "mroads" '(5 -17) 1 1 0 )
(command "insert" "mroads" '(20 -31) 1 1 0 )
(command "insert" "mroads" '(40 -20) 1 1 0 )
(command "insert" "mroads" '(21 -30) 1 1 0 )
(command "insert" "mroads" '(7 -31) 1 1 0 )
(command "insert" "mroads" '(68 -31) 1 1 0 )
(command "insert" "mroads" '(36 -32) 1 1 0 )
(command "insert" "mroads" '(69 -30) 1 1 0 )
(command "insert" "mroads" '(34 -16) 1 1 0 )
(command "insert" "mroads" '(44 -32) 1 1 0 )
(command "insert" "mroads" '(72 -32) 1 1 0 )
(command "insert" "mroads" '(6 -16) 1 1 0 )
(command "insert" "mroads" '(37 -15) 1 1 0 )
(command "insert" "mroads" '(11 -20) 1 1 0 )
(command "insert" "mroads" '(35 -19) 1 1 0 )
(command "insert" "mroads" '(36 -20) 1 1 0 )
(command "insert" "mroads" '(1 -30) 1 1 0 )
(command "insert" "mroads" '(28 -18) 1 1 0 )
(command "insert" "mroads" '(2 -29) 1 1 0 )
(command "insert" "mroads" '(48 -31) 1 1 0 )
(command "insert" "mroads" '(29 -19) 1 1 0 )
(command "insert" "mroads" '(27 -15) 1 1 0 )
(command "insert" "mroads" '(15 -32) 1 1 0 )
(command "insert" "mroads" '(4 -27) 1 1 0 )
(command "insert" "mroads" '(41 -27) 1 1 0 )
(command "insert" "mroads" '(5 -26) 1 1 0 )
(command "insert" "mroads" '(51 -32) 1 1 0 )
(command "insert" "mroads" '(40 -27) 1 1 0 )
(command "insert" "mroads" '(30 -18) 1 1 0 )
(command "insert" "mroads" '(17 -15) 1 1 0 )
(command "insert" "mroads" '(41 -26) 1 1 0 )
(command "insert" "mroads" '(56 -30) 1 1 0 )
(command "insert" "mroads" '(23 -17) 1 1 0 )
(command "insert" "mroads" '(86 -31) 1 1 0 )
(command "insert" "mroads" '(104 -30) 1 1 0 )
(command "insert" "mroads" '(44 -31) 1 1 0 )
(command "insert" "mroads" '(23 -15) 1 1 0 )
(command "insert" "mroads" '(105 -31) 1 1 0 )
(command "insert" "mroads" '(45 -30) 1 1 0 )
(command "insert" "mroads" '(8 -16) 1 1 0 )
(command "insert" "mroads" '(35 -24) 1 1 0 )
(command "insert" "mroads" '(50 -32) 1 1 0 )
(command "insert" "mroads" '(24 -19) 1 1 0 )
(command "insert" "mroads" '(36 -19) 1 1 0 )
(command "insert" "mroads" '(1 -23) 1 1 0 )
(command "insert" "mroads" '(104 -31) 1 1 0 )
(command "insert" "mroads" '(13 -15) 1 1 0 )
(command "insert" "mroads" '(37 -18) 1 1 0 )
(command "insert" "mroads" '(102 -32) 1 1 0 )
(command "insert" "mroads" '(38 -25) 1 1 0 )
(command "insert" "mroads" '(53 -31) 1 1 0 )
(command "insert" "mroads" '(78 -30) 1 1 0 )
(command "insert" "mroads" '(39 -28) 1 1 0 )
(command "insert" "mroads" '(84 -32) 1 1 0 )
(command "insert" "mroads" '(100 -30) 1 1 0 )
(command "insert" "mroads" '(115 -30) 1 1 0 )
(command "insert" "mroads" '(25 -17) 1 1 0 )
(command "insert" "mroads" '(101 -31) 1 1 0 )
(command "insert" "mroads" '(21 -32) 1 1 0 )
(command "insert" "mroads" '(19 -16) 1 1 0 )
(command "insert" "mroads" '(31 -16) 1 1 0 )
(command "insert" "mroads" '(29 -32) 1 1 0 )
(command "insert" "mroads" '(41 -17) 1 1 0 )
(command "insert" "mroads" '(32 -30) 1 1 0 )
(command "insert" "mroads" '(65 -32) 1 1 0 )
(command "insert" "mroads" '(52 -31) 1 1 0 )
(command "insert" "mroads" '(33 -31) 1 1 0 )
(command "insert" "mroads" '(110 -31) 1 1 0 )
(command "insert" "mroads" '(34 -28) 1 1 0 )
(command "insert" "mroads" '(8 -23) 1 1 0 )
(command "insert" "mroads" '(80 -30) 1 1 0 )
(command "insert" "mroads" '(111 -30) 1 1 0 )
(command "insert" "mroads" '(57 -32) 1 1 0 )
(command "insert" "mroads" '(81 -31) 1 1 0 )
(command "insert" "mroads" '(36 -26) 1 1 0 )
(command "insert" "mroads" '(40 -24) 1 1 0 )
(command "insert" "mroads" '(37 -27) 1 1 0 )
(command "insert" "mroads" '(26 -16) 1 1 0 )
(command "insert" "mroads" '(38 -16) 1 1 0 )
(command "insert" "mroads" '(39 -21) 1 1 0 )
(command "insert" "mroads" '(28 -30) 1 1 0 )
(command "insert" "mroads" '(29 -31) 1 1 0 )
(command "insert" "mroads" '(3 -20) 1 1 0 )
(command "insert" "mroads" '(90 -31) 1 1 0 )
(command "insert" "mroads" '(4 -23) 1 1 0 )
(command "insert" "mroads" '(76 -30) 1 1 0 )
(command "insert" "mroads" '(91 -30) 1 1 0 )
(command "insert" "mroads" '(7 -27) 1 1 0 )
(command "insert" "mroads" '(5 -22) 1 1 0 )
(command "insert" "mroads" '(20 -18) 1 1 0 )
(command "insert" "mroads" '(77 -31) 1 1 0 )
(command "insert" "mroads" '(21 -19) 1 1 0 )
(command "insert" "mroads" '(7 -32) 1 1 0 )
(command "insert" "mroads" '(35 -32) 1 1 0 )
(command "insert" "mroads" '(113 -30) 1 1 0 )
(command "insert" "mroads" '(33 -16) 1 1 0 )
(command "insert" "mroads" '(43 -32) 1 1 0 )
(command "insert" "mroads" '(8 -30) 1 1 0 )
(command "insert" "mroads" '(87 -32) 1 1 0 )
(command "insert" "mroads" '(9 -31) 1 1 0 )
(command "insert" "mroads" '(95 -32) 1 1 0 )
(command "insert" "mroads" '(15 -17) 1 1 0 )
(command "insert" "mroads" '(87 -30) 1 1 0 )
(command "insert" "mroads" '(11 -17) 1 1 0 )
(command "insert" "mroads" '(27 -18) 1 1 0 )
(command "insert" "mroads" '(1 -27) 1 1 0 )
(command "insert" "mroads" '(39 -18) 1 1 0 )
(command "insert" "mroads" '(14 -32) 1 1 0 )
(command "insert" "mroads" '(3 -29) 1 1 0 )
(command "insert" "mroads" '(4 -30) 1 1 0 )
(command "insert" "mroads" '(19 -30) 1 1 0 )
(command "layer" "m" "ped" "" )
(command "insert" "ped" '(265 -81) 1 1 0 )
(command "insert" "ped" '(265 -84) 1 1 0 )
(command "insert" "ped" '(266 -83) 1 1 0 )
(command "insert" "ped" '(264 -85) 1 1 0 )
(command "insert" "ped" '(265 -82) 1 1 0 )
(command "insert" "ped" '(266 -85) 1 1 0 )
(command "insert" "ped" '(264 -81) 1 1 0 )
(command "insert" "ped" '(266 -82) 1 1 0 )
(command "insert" "ped" '(265 -86) 1 1 0 )
(command "insert" "ped" '(266 -86) 1 1 0 )
(command "insert" "ped" '(266 -81) 1 1 0 )
(command "insert" "ped" '(264 -86) 1 1 0 )
(command "insert" "ped" '(264 -83) 1 1 0 )
(command "insert" "ped" '(264 -84) 1 1 0 )
(command "insert" "ped" '(266 -84) 1 1 0 )
(command "insert" "ped" '(265 -85) 1 1 0 )
(command "insert" "ped" '(265 -83) 1 1 0 )
(command "insert" "ped" '(264 -82) 1 1 0 )
(command "layer" "m" "Res" "" )
(command "insert" "Res" '(292 -73) 1 1 0 )
(command "insert" "Res" '(290 -73) 1 1 0 )
(command "insert" "Res" '(273 -74) 1 1 0 )
(command "insert" "Res" '(291 -74) 1 1 0 )
(command "insert" "Res" '(279 -76) 1 1 0 )
(command "insert" "Res" '(286 -74) 1 1 0 )
(command "insert" "Res" '(271 -71) 1 1 0 )
(command "insert" "Res" '(277 -75) 1 1 0 )
(command "insert" "Res" '(278 -75) 1 1 0 )
(command "insert" "Res" '(283 -73) 1 1 0 )
(command "insert" "Res" '(287 -74) 1 1 0 )
(command "insert" "Res" '(272 -76) 1 1 0 )
(command "insert" "Res" '(275 -73) 1 1 0 )
(command "insert" "Res" '(278 -76) 1 1 0 )
(command "insert" "Res" '(270 -71) 1 1 0 )
(command "insert" "Res" '(276 -75) 1 1 0 )
(command "insert" "Res" '(290 -74) 1 1 0 )
(command "insert" "Res" '(281 -77) 1 1 0 )
(command "insert" "Res" '(291 -73) 1 1 0 )
(command "insert" "Res" '(289 -73) 1 1 0 )
(command "insert" "Res" '(280 -76) 1 1 0 )
(command "insert" "Res" '(279 -77) 1 1 0 )
(command "insert" "Res" '(272 -70) 1 1 0 )
(command "insert" "Res" '(273 -72) 1 1 0 )
(command "insert" "Res" '(287 -73) 1 1 0 )
(command "insert" "Res" '(285 -73) 1 1 0 )
(command "insert" "Res" '(286 -72) 1 1 0 )
(command "insert" "Res" '(270 -77) 1 1 0 )
(command "insert" "Res" '(284 -72) 1 1 0 )
(command "insert" "Res" '(271 -76) 1 1 0 )
(command "insert" "Res" '(293 -73) 1 1 0 )
(command "insert" "Res" '(288 -72) 1 1 0 )
(command "insert" "Res" '(270 -69) 1 1 0 )
(command "insert" "Res" '(292 -72) 1 1 0 )
(command "insert" "Res" '(290 -72) 1 1 0 )
(command "insert" "Res" '(271 -75) 1 1 0 )
(command "insert" "Res" '(288 -74) 1 1 0 )
(command "insert" "Res" '(274 -73) 1 1 0 )
(command "insert" "Res" '(277 -76) 1 1 0 )
(command "insert" "Res" '(276 -77) 1 1 0 )
(command "insert" "Res" '(272 -75) 1 1 0 )
(command "insert" "Res" '(281 -75) 1 1 0 )
(command "insert" "Res" '(284 -74) 1 1 0 )
(command "insert" "Res" '(282 -73) 1 1 0 )
(command "insert" "Res" '(270 -70) 1 1 0 )
(command "insert" "Res" '(289 -74) 1 1 0 )
(command "insert" "Res" '(280 -75) 1 1 0 )
(command "insert" "Res" '(274 -74) 1 1 0 )
(command "insert" "Res" '(270 -75) 1 1 0 )
(command "insert" "Res" '(292 -74) 1 1 0 )
(command "insert" "Res" '(272 -69) 1 1 0 )
(command "insert" "Res" '(273 -73) 1 1 0 )
(command "insert" "Res" '(285 -74) 1 1 0 )
(command "insert" "Res" '(270 -76) 1 1 0 )
(command "insert" "Res" '(271 -70) 1 1 0 )
(command "insert" "Res" '(282 -74) 1 1 0 )
(command "insert" "Res" '(283 -72) 1 1 0 )
(command "insert" "Res" '(272 -77) 1 1 0 )
(command "insert" "Res" '(275 -72) 1 1 0 )
(command "insert" "Res" '(271 -77) 1 1 0 )
(command "insert" "Res" '(293 -74) 1 1 0 )
(command "insert" "Res" '(278 -77) 1 1 0 )
(command "insert" "Res" '(281 -76) 1 1 0 )
(command "insert" "Res" '(291 -72) 1 1 0 )
(command "insert" "Res" '(289 -72) 1 1 0 )
(command "insert" "Res" '(280 -77) 1 1 0 )
(command "insert" "Res" '(288 -73) 1 1 0 )
(command "insert" "Res" '(274 -72) 1 1 0 )
(command "insert" "Res" '(271 -69) 1 1 0 )
(command "insert" "Res" '(277 -77) 1 1 0 )
(command "insert" "Res" '(272 -71) 1 1 0 )
(command "insert" "Res" '(276 -76) 1 1 0 )
(command "insert" "Res" '(287 -72) 1 1 0 )
(command "insert" "Res" '(285 -72) 1 1 0 )
(command "insert" "Res" '(279 -75) 1 1 0 )
(command "insert" "Res" '(286 -73) 1 1 0 )
(command "insert" "Res" '(284 -73) 1 1 0 )
(command "insert" "Res" '(282 -72) 1 1 0 )
(command "insert" "Res" '(283 -74) 1 1 0 )
(command "insert" "Res" '(275 -74) 1 1 0 )
(command "insert" "Res" '(293 -72) 1 1 0 )
(command "layer" "m" "Idust" "" )
(command "insert" "Idust" '(204 -34) 1 1 0 )
(command "insert" "Idust" '(210 -35) 1 1 0 )
(command "insert" "Idust" '(197 -32) 1 1 0 )
(command "insert" "Idust" '(205 -35) 1 1 0 )
(command "insert" "Idust" '(224 -36) 1 1 0 )
(command "insert" "Idust" '(192 -30) 1 1 0 )
(command "insert" "Idust" '(193 -31) 1 1 0 )
(command "insert" "Idust" '(216 -39) 1 1 0 )
(command "insert" "Idust" '(214 -31) 1 1 0 )
(command "insert" "Idust" '(216 -36) 1 1 0 )
(command "insert" "Idust" '(211 -34) 1 1 0 )
(command "insert" "Idust" '(217 -33) 1 1 0 )
(command "insert" "Idust" '(222 -30) 1 1 0 )
(command "insert" "Idust" '(212 -37) 1 1 0 )
(command "insert" "Idust" '(219 -34) 1 1 0 )
(command "insert" "Idust" '(218 -38) 1 1 0 )
(command "insert" "Idust" '(223 -31) 1 1 0 )
(command "insert" "Idust" '(196 -32) 1 1 0 )
(command "insert" "Idust" '(220 -37) 1 1 0 )
(command "insert" "Idust" '(200 -35) 1 1 0 )
(command "insert" "Idust" '(215 -37) 1 1 0 )
(command "insert" "Idust" '(223 -40) 1 1 0 )
(command "insert" "Idust" '(222 -32) 1 1 0 )
(command "insert" "Idust" '(221 -40) 1 1 0 )
(command "insert" "Idust" '(201 -34) 1 1 0 )
(command "insert" "Idust" '(208 -35) 1 1 0 )
(command "insert" "Idust" '(223 -37) 1 1 0 )
(command "insert" "Idust" '(203 -35) 1 1 0 )
(command "insert" "Idust" '(209 -34) 1 1 0 )
(command "insert" "Idust" '(216 -31) 1 1 0 )
(command "insert" "Idust" '(202 -30) 1 1 0 )
(command "insert" "Idust" '(217 -30) 1 1 0 )
(command "insert" "Idust" '(219 -39) 1 1 0 )
(command "insert" "Idust" '(203 -31) 1 1 0 )
(command "insert" "Idust" '(207 -35) 1 1 0 )
(command "insert" "Idust" '(223 -33) 1 1 0 )
(command "insert" "Idust" '(218 -33) 1 1 0 )
(command "insert" "Idust" '(213 -33) 1 1 0 )
(command "insert" "Idust" '(212 -31) 1 1 0 )
(command "insert" "Idust" '(224 -39) 1 1 0 )
(command "insert" "Idust" '(198 -30) 1 1 0 )
(command "insert" "Idust" '(213 -30) 1 1 0 )
(command "insert" "Idust" '(221 -33) 1 1 0 )
(command "insert" "Idust" '(199 -31) 1 1 0 )
(command "insert" "Idust" '(223 -34) 1 1 0 )
(command "insert" "Idust" '(202 -32) 1 1 0 )
(command "insert" "Idust" '(224 -35) 1 1 0 )
(command "insert" "Idust" '(204 -35) 1 1 0 )
(command "insert" "Idust" '(210 -32) 1 1 0 )
(command "insert" "Idust" '(205 -34) 1 1 0 )
(command "insert" "Idust" '(223 -30) 1 1 0 )
(command "insert" "Idust" '(192 -31) 1 1 0 )
(command "insert" "Idust" '(193 -30) 1 1 0 )
(command "insert" "Idust" '(208 -38) 1 1 0 )
(command "insert" "Idust" '(207 -32) 1 1 0 )
(command "insert" "Idust" '(216 -37) 1 1 0 )
(command "insert" "Idust" '(211 -37) 1 1 0 )
(command "insert" "Idust" '(218 -40) 1 1 0 )
(command "insert" "Idust" '(217 -32) 1 1 0 )
(command "insert" "Idust" '(222 -31) 1 1 0 )
(command "insert" "Idust" '(212 -38) 1 1 0 )
(command "insert" "Idust" '(219 -37) 1 1 0 )
(command "insert" "Idust" '(218 -39) 1 1 0 )
(command "insert" "Idust" '(214 -33) 1 1 0 )
(command "insert" "Idust" '(220 -38) 1 1 0 )
(command "insert" "Idust" '(215 -36) 1 1 0 )
(command "insert" "Idust" '(222 -33) 1 1 0 )
(command "insert" "Idust" '(221 -39) 1 1 0 )
(command "insert" "Idust" '(201 -33) 1 1 0 )
(command "insert" "Idust" '(208 -36) 1 1 0 )
(command "insert" "Idust" '(223 -36) 1 1 0 )
(command "insert" "Idust" '(203 -34) 1 1 0 )
(command "insert" "Idust" '(209 -33) 1 1 0 )
(command "insert" "Idust" '(210 -38) 1 1 0 )
(command "insert" "Idust" '(202 -31) 1 1 0 )
(command "insert" "Idust" '(203 -30) 1 1 0 )
(command "insert" "Idust" '(206 -35) 1 1 0 )
(command "insert" "Idust" '(199 -32) 1 1 0 )
(command "insert" "Idust" '(207 -33) 1 1 0 )
(command "insert" "Idust" '(217 -41) 1 1 0 )
(command "insert" "Idust" '(199 -33) 1 1 0 )
(command "insert" "Idust" '(187 -32) 1 1 0 )
(command "insert" "Idust" '(211 -31) 1 1 0 )
(command "insert" "Idust" '(224 -38) 1 1 0 )
(command "insert" "Idust" '(213 -32) 1 1 0 )
(command "insert" "Idust" '(195 -32) 1 1 0 )
(command "insert" "Idust" '(198 -31) 1 1 0 )
(command "insert" "Idust" '(222 -40) 1 1 0 )
(command "insert" "Idust" '(221 -32) 1 1 0 )
(command "insert" "Idust" '(220 -40) 1 1 0 )
(command "insert" "Idust" '(199 -30) 1 1 0 )
(command "insert" "Idust" '(198 -34) 1 1 0 )
(command "insert" "Idust" '(202 -33) 1 1 0 )
(command "insert" "Idust" '(224 -30) 1 1 0 )
(command "insert" "Idust" '(210 -33) 1 1 0 )
(command "insert" "Idust" '(224 -33) 1 1 0 )
(command "insert" "Idust" '(206 -30) 1 1 0 )
(command "insert" "Idust" '(188 -32) 1 1 0 )
(command "insert" "Idust" '(207 -31) 1 1 0 )
(command "insert" "Idust" '(220 -30) 1 1 0 )
(command "insert" "Idust" '(216 -38) 1 1 0 )
(command "insert" "Idust" '(221 -31) 1 1 0 )
(command "insert" "Idust" '(211 -36) 1 1 0 )
(command "insert" "Idust" '(216 -35) 1 1 0 )
(command "insert" "Idust" '(218 -41) 1 1 0 )
(command "insert" "Idust" '(217 -39) 1 1 0 )
(command "insert" "Idust" '(189 -30) 1 1 0 )
(command "insert" "Idust" '(186 -30) 1 1 0 )
(command "insert" "Idust" '(219 -36) 1 1 0 )
(command "insert" "Idust" '(218 -36) 1 1 0 )
(command "insert" "Idust" '(214 -38) 1 1 0 )
(command "insert" "Idust" '(213 -38) 1 1 0 )
(command "insert" "Idust" '(187 -31) 1 1 0 )
(command "insert" "Idust" '(220 -39) 1 1 0 )
(command "insert" "Idust" '(219 -41) 1 1 0 )
(command "insert" "Idust" '(191 -32) 1 1 0 )
(command "insert" "Idust" '(224 -34) 1 1 0 )
(command "insert" "Idust" '(222 -38) 1 1 0 )
(command "insert" "Idust" '(221 -38) 1 1 0 )
(command "insert" "Idust" '(201 -32) 1 1 0 )
(command "insert" "Idust" '(208 -37) 1 1 0 )
(command "insert" "Idust" '(223 -39) 1 1 0 )
(command "insert" "Idust" '(209 -32) 1 1 0 )
(command "insert" "Idust" '(214 -32) 1 1 0 )
(command "insert" "Idust" '(200 -30) 1 1 0 )
(command "insert" "Idust" '(224 -32) 1 1 0 )
(command "insert" "Idust" '(201 -31) 1 1 0 )
(command "insert" "Idust" '(188 -30) 1 1 0 )
(command "insert" "Idust" '(183 -31) 1 1 0 )
(command "insert" "Idust" '(188 -31) 1 1 0 )
(command "insert" "Idust" '(206 -32) 1 1 0 )
(command "insert" "Idust" '(217 -40) 1 1 0 )
(command "insert" "Idust" '(207 -37) 1 1 0 )
(command "insert" "Idust" '(196 -30) 1 1 0 )
(command "insert" "Idust" '(211 -30) 1 1 0 )
(command "insert" "Idust" '(189 -31) 1 1 0 )
(command "insert" "Idust" '(222 -41) 1 1 0 )
(command "insert" "Idust" '(220 -41) 1 1 0 )
(command "insert" "Idust" '(198 -35) 1 1 0 )
(command "insert" "Idust" '(224 -31) 1 1 0 )
(command "insert" "Idust" '(210 -30) 1 1 0 )
(command "insert" "Idust" '(205 -32) 1 1 0 )
(command "insert" "Idust" '(206 -31) 1 1 0 )
(command "insert" "Idust" '(207 -30) 1 1 0 )
(command "insert" "Idust" '(220 -31) 1 1 0 )
(command "insert" "Idust" '(207 -34) 1 1 0 )
(command "insert" "Idust" '(221 -30) 1 1 0 )
(command "insert" "Idust" '(186 -32) 1 1 0 )
(command "insert" "Idust" '(217 -38) 1 1 0 )
(command "insert" "Idust" '(212 -32) 1 1 0 )
(command "insert" "Idust" '(186 -31) 1 1 0 )
(command "insert" "Idust" '(194 -32) 1 1 0 )
(command "insert" "Idust" '(218 -37) 1 1 0 )
(command "insert" "Idust" '(213 -37) 1 1 0 )
(command "insert" "Idust" '(187 -30) 1 1 0 )
(command "insert" "Idust" '(220 -32) 1 1 0 )
(command "insert" "Idust" '(219 -40) 1 1 0 )
(command "insert" "Idust" '(215 -38) 1 1 0 )
(command "insert" "Idust" '(222 -39) 1 1 0 )
(command "insert" "Idust" '(221 -37) 1 1 0 )
(command "insert" "Idust" '(199 -35) 1 1 0 )
(command "insert" "Idust" '(223 -38) 1 1 0 )
(command "insert" "Idust" '(210 -36) 1 1 0 )
(command "insert" "Idust" '(200 -31) 1 1 0 )
(command "insert" "Idust" '(200 -33) 1 1 0 )
(command "insert" "Idust" '(201 -30) 1 1 0 )
(command "insert" "Idust" '(183 -30) 1 1 0 )
(command "insert" "Idust" '(206 -33) 1 1 0 )
(command "insert" "Idust" '(219 -33) 1 1 0 )
(command "insert" "Idust" '(207 -36) 1 1 0 )
(command "insert" "Idust" '(196 -31) 1 1 0 )
(command "insert" "Idust" '(211 -33) 1 1 0 )
(command "insert" "Idust" '(197 -30) 1 1 0 )
(command "insert" "Idust" '(216 -32) 1 1 0 )
(command "insert" "Idust" '(190 -32) 1 1 0 )
(command "insert" "Idust" '(200 -32) 1 1 0 )
(command "insert" "Idust" '(198 -32) 1 1 0 )
(command "insert" "Idust" '(208 -32) 1 1 0 )
(command "insert" "Idust" '(210 -31) 1 1 0 )
(command "insert" "Idust" '(197 -31) 1 1 0 )
(command "insert" "Idust" '(219 -31) 1 1 0 )
(command "insert" "Idust" '(184 -30) 1 1 0 )
(command "insert" "Idust" '(216 -40) 1 1 0 )
(command "insert" "Idust" '(211 -38) 1 1 0 )
(command "insert" "Idust" '(185 -31) 1 1 0 )
(command "insert" "Idust" '(217 -37) 1 1 0 )
(command "insert" "Idust" '(212 -33) 1 1 0 )
(command "insert" "Idust" '(219 -38) 1 1 0 )
(command "insert" "Idust" '(218 -34) 1 1 0 )
(command "insert" "Idust" '(214 -36) 1 1 0 )
(command "insert" "Idust" '(213 -36) 1 1 0 )
(command "insert" "Idust" '(220 -33) 1 1 0 )
(command "insert" "Idust" '(215 -33) 1 1 0 )
(command "insert" "Idust" '(222 -36) 1 1 0 )
(command "insert" "Idust" '(221 -36) 1 1 0 )
(command "insert" "Idust" '(199 -34) 1 1 0 )
(command "insert" "Idust" '(214 -30) 1 1 0 )
(command "insert" "Idust" '(209 -38) 1 1 0 )
(command "insert" "Idust" '(215 -31) 1 1 0 )
(command "insert" "Idust" '(204 -32) 1 1 0 )
(command "insert" "Idust" '(210 -37) 1 1 0 )
(command "insert" "Idust" '(206 -34) 1 1 0 )
(command "insert" "Idust" '(194 -30) 1 1 0 )
(command "insert" "Idust" '(195 -31) 1 1 0 )
(command "insert" "Idust" '(185 -32) 1 1 0 )
(command "insert" "Idust" '(183 -32) 1 1 0 )
(command "insert" "Idust" '(216 -34) 1 1 0 )
(command "insert" "Idust" '(211 -32) 1 1 0 )
(command "insert" "Idust" '(193 -32) 1 1 0 )
(command "insert" "Idust" '(217 -35) 1 1 0 )
(command "insert" "Idust" '(219 -32) 1 1 0 )
(command "insert" "Idust" '(214 -34) 1 1 0 )
(command "insert" "Idust" '(216 -33) 1 1 0 )
(command "insert" "Idust" '(208 -30) 1 1 0 )
(command "insert" "Idust" '(198 -33) 1 1 0 )
(command "insert" "Idust" '(222 -34) 1 1 0 )
(command "insert" "Idust" '(209 -31) 1 1 0 )
(command "insert" "Idust" '(208 -33) 1 1 0 )
(command "insert" "Idust" '(203 -33) 1 1 0 )
(command "insert" "Idust" '(190 -30) 1 1 0 )
(command "insert" "Idust" '(191 -31) 1 1 0 )
(command "insert" "Idust" '(218 -31) 1 1 0 )
(command "insert" "Idust" '(204 -30) 1 1 0 )
(command "insert" "Idust" '(219 -30) 1 1 0 )
(command "insert" "Idust" '(205 -31) 1 1 0 )
(command "insert" "Idust" '(184 -31) 1 1 0 )
(command "insert" "Idust" '(216 -41) 1 1 0 )
(command "insert" "Idust" '(185 -30) 1 1 0 )
(command "insert" "Idust" '(217 -36) 1 1 0 )
(command "insert" "Idust" '(212 -34) 1 1 0 )
(command "insert" "Idust" '(218 -35) 1 1 0 )
(command "insert" "Idust" '(214 -37) 1 1 0 )
(command "insert" "Idust" '(213 -35) 1 1 0 )
(command "insert" "Idust" '(220 -34) 1 1 0 )
(command "insert" "Idust" '(224 -37) 1 1 0 )
(command "insert" "Idust" '(215 -34) 1 1 0 )
(command "insert" "Idust" '(222 -37) 1 1 0 )
(command "insert" "Idust" '(221 -35) 1 1 0 )
(command "insert" "Idust" '(224 -40) 1 1 0 )
(command "insert" "Idust" '(223 -32) 1 1 0 )
(command "insert" "Idust" '(202 -34) 1 1 0 )
(command "insert" "Idust" '(209 -37) 1 1 0 )
(command "insert" "Idust" '(215 -30) 1 1 0 )
(command "insert" "Idust" '(204 -33) 1 1 0 )
(command "insert" "Idust" '(210 -34) 1 1 0 )
(command "insert" "Idust" '(218 -30) 1 1 0 )
(command "insert" "Idust" '(205 -33) 1 1 0 )
(command "insert" "Idust" '(194 -31) 1 1 0 )
(command "insert" "Idust" '(195 -30) 1 1 0 )
(command "insert" "Idust" '(207 -38) 1 1 0 )
(command "insert" "Idust" '(211 -35) 1 1 0 )
(command "insert" "Idust" '(217 -34) 1 1 0 )
(command "insert" "Idust" '(212 -36) 1 1 0 )
(command "insert" "Idust" '(219 -35) 1 1 0 )
(command "insert" "Idust" '(214 -35) 1 1 0 )
(command "insert" "Idust" '(220 -36) 1 1 0 )
(command "insert" "Idust" '(200 -34) 1 1 0 )
(command "insert" "Idust" '(208 -31) 1 1 0 )
(command "insert" "Idust" '(223 -41) 1 1 0 )
(command "insert" "Idust" '(222 -35) 1 1 0 )
(command "insert" "Idust" '(221 -41) 1 1 0 )
(command "insert" "Idust" '(201 -35) 1 1 0 )
(command "insert" "Idust" '(209 -30) 1 1 0 )
(command "insert" "Idust" '(208 -34) 1 1 0 )
(command "insert" "Idust" '(203 -32) 1 1 0 )
(command "insert" "Idust" '(209 -35) 1 1 0 )
(command "insert" "Idust" '(190 -31) 1 1 0 )
(command "insert" "Idust" '(215 -32) 1 1 0 )
(command "insert" "Idust" '(191 -30) 1 1 0 )
(command "insert" "Idust" '(216 -30) 1 1 0 )
(command "insert" "Idust" '(217 -31) 1 1 0 )
(command "insert" "Idust" '(204 -31) 1 1 0 )
(command "insert" "Idust" '(189 -32) 1 1 0 )
(command "insert" "Idust" '(205 -30) 1 1 0 )
(command "insert" "Idust" '(184 -32) 1 1 0 )
(command "insert" "Idust" '(192 -32) 1 1 0 )
(command "insert" "Idust" '(212 -35) 1 1 0 )
(command "insert" "Idust" '(218 -32) 1 1 0 )
(command "insert" "Idust" '(213 -34) 1 1 0 )
(command "insert" "Idust" '(212 -30) 1 1 0 )
(command "insert" "Idust" '(220 -35) 1 1 0 )
(command "insert" "Idust" '(215 -35) 1 1 0 )
(command "insert" "Idust" '(213 -31) 1 1 0 )
(command "insert" "Idust" '(221 -34) 1 1 0 )
(command "insert" "Idust" '(224 -41) 1 1 0 )
(command "insert" "Idust" '(223 -35) 1 1 0 )
(command "insert" "Idust" '(202 -35) 1 1 0 )
(command "insert" "Idust" '(209 -36) 1 1 0 )
(command "layer" "m" "ped" "" )
(command "insert" "ped" '(97 -22) 1 1 0 )
(command "insert" "ped" '(99 -22) 1 1 0 )
(command "insert" "ped" '(97 -21) 1 1 0 )
(command "insert" "ped" '(104 -22) 1 1 0 )
(command "insert" "ped" '(98 -21) 1 1 0 )
(command "insert" "ped" '(98 -23) 1 1 0 )
(command "insert" "ped" '(101 -22) 1 1 0 )
(command "insert" "ped" '(100 -23) 1 1 0 )
(command "insert" "ped" '(102 -22) 1 1 0 )
(command "insert" "ped" '(100 -21) 1 1 0 )
(command "insert" "ped" '(96 -21) 1 1 0 )
(command "insert" "ped" '(103 -23) 1 1 0 )
(command "insert" "ped" '(96 -22) 1 1 0 )
(command "insert" "ped" '(103 -21) 1 1 0 )
(command "insert" "ped" '(104 -23) 1 1 0 )
(command "insert" "ped" '(97 -23) 1 1 0 )
(command "insert" "ped" '(99 -23) 1 1 0 )
(command "insert" "ped" '(104 -21) 1 1 0 )
(command "insert" "ped" '(102 -21) 1 1 0 )
(command "insert" "ped" '(99 -21) 1 1 0 )
(command "insert" "ped" '(98 -22) 1 1 0 )
(command "insert" "ped" '(102 -23) 1 1 0 )
(command "insert" "ped" '(100 -22) 1 1 0 )
(command "insert" "ped" '(103 -22) 1 1 0 )
(command "insert" "ped" '(101 -23) 1 1 0 )
(command "insert" "ped" '(96 -23) 1 1 0 )
(command "insert" "ped" '(101 -21) 1 1 0 )
(command "layer" "m" "Commmer" "" )
(command "insert" "Commmer" '(195 -77) 1 1 0 )
(command "insert" "Commmer" '(193 -77) 1 1 0 )
(command "insert" "Commmer" '(195 -75) 1 1 0 )
(command "insert" "Commmer" '(192 -76) 1 1 0 )
(command "insert" "Commmer" '(196 -76) 1 1 0 )
(command "insert" "Commmer" '(194 -76) 1 1 0 )
(command "insert" "Commmer" '(197 -77) 1 1 0 )
(command "insert" "Commmer" '(193 -75) 1 1 0 )
(command "insert" "Commmer" '(196 -75) 1 1 0 )
(command "insert" "Commmer" '(195 -76) 1 1 0 )
(command "insert" "Commmer" '(193 -76) 1 1 0 )
(command "insert" "Commmer" '(197 -76) 1 1 0 )
(command "insert" "Commmer" '(197 -75) 1 1 0 )
(command "insert" "Commmer" '(194 -75) 1 1 0 )
(command "insert" "Commmer" '(192 -75) 1 1 0 )
(command "insert" "Commmer" '(196 -77) 1 1 0 )
(command "insert" "Commmer" '(194 -77) 1 1 0 )
(command "insert" "Commmer" '(192 -77) 1 1 0 )
(command "layer" "m" "ped" "" )
(command "insert" "ped" '(94 -12) 1 1 0 )
(command "insert" "ped" '(90 -14) 1 1 0 )
(command "insert" "ped" '(94 -14) 1 1 0 )
(command "insert" "ped" '(89 -12) 1 1 0 )
(command "insert" "ped" '(91 -13) 1 1 0 )
(command "insert" "ped" '(92 -13) 1 1 0 )
(command "insert" "ped" '(87 -14) 1 1 0 )
(command "insert" "ped" '(95 -13) 1 1 0 )
(command "insert" "ped" '(88 -13) 1 1 0 )
(command "insert" "ped" '(92 -14) 1 1 0 )
(command "insert" "ped" '(87 -12) 1 1 0 )
(command "insert" "ped" '(90 -13) 1 1 0 )
(command "insert" "ped" '(92 -12) 1 1 0 )
(command "insert" "ped" '(94 -13) 1 1 0 )
(command "insert" "ped" '(91 -14) 1 1 0 )
(command "insert" "ped" '(89 -13) 1 1 0 )
(command "insert" "ped" '(95 -14) 1 1 0 )
(command "insert" "ped" '(91 -12) 1 1 0 )
(command "insert" "ped" '(95 -12) 1 1 0 )
(command "insert" "ped" '(88 -14) 1 1 0 )
(command "insert" "ped" '(93 -12) 1 1 0 )
(command "insert" "ped" '(88 -12) 1 1 0 )
(command "insert" "ped" '(93 -14) 1 1 0 )
(command "insert" "ped" '(89 -14) 1 1 0 )
(command "insert" "ped" '(87 -13) 1 1 0 )
(command "insert" "ped" '(90 -12) 1 1 0 )
(command "insert" "ped" '(93 -13) 1 1 0 )
(command "layer" "m" "Commmer" "" )
(command "insert" "Commmer" '(3 -34) 1 1 0 )
(command "insert" "Commmer" '(3 -35) 1 1 0 )
(command "insert" "Commmer" '(5 -34) 1 1 0 )
(command "insert" "Commmer" '(3 -33) 1 1 0 )
(command "insert" "Commmer" '(4 -35) 1 1 0 )
(command "insert" "Commmer" '(5 -33) 1 1 0 )
(command "insert" "Commmer" '(4 -34) 1 1 0 )
(command "insert" "Commmer" '(4 -33) 1 1 0 )
(command "insert" "Commmer" '(5 -35) 1 1 0 )
(command "layer" "m" "edge" "" )
(command "insert" "edge" '(297 -58) 1 1 0 )
(command "insert" "edge" '(298 -63) 1 1 0 )
(command "insert" "edge" '(297 -64) 1 1 0 )
(command "insert" "edge" '(296 -65) 1 1 0 )
(command "insert" "edge" '(295 -59) 1 1 0 )
(command "insert" "edge" '(298 -58) 1 1 0 )
(command "insert" "edge" '(299 -60) 1 1 0 )
(command "insert" "edge" '(293 -56) 1 1 0 )
(command "insert" "edge" '(294 -62) 1 1 0 )
(command "insert" "edge" '(297 -61) 1 1 0 )
(command "insert" "edge" '(299 -65) 1 1 0 )
(command "insert" "edge" '(295 -63) 1 1 0 )
(command "insert" "edge" '(296 -60) 1 1 0 )
(command "insert" "edge" '(298 -64) 1 1 0 )
(command "insert" "edge" '(294 -58) 1 1 0 )
(command "insert" "edge" '(297 -57) 1 1 0 )
(command "insert" "edge" '(298 -62) 1 1 0 )
(command "insert" "edge" '(296 -59) 1 1 0 )
(command "insert" "edge" '(295 -58) 1 1 0 )
(command "insert" "edge" '(295 -65) 1 1 0 )
(command "insert" "edge" '(299 -63) 1 1 0 )
(command "insert" "edge" '(294 -63) 1 1 0 )
(command "insert" "edge" '(294 -64) 1 1 0 )
(command "insert" "edge" '(297 -60) 1 1 0 )
(command "insert" "edge" '(298 -60) 1 1 0 )
(command "insert" "edge" '(299 -64) 1 1 0 )
(command "insert" "edge" '(295 -62) 1 1 0 )
(command "insert" "edge" '(296 -61) 1 1 0 )
(command "insert" "edge" '(299 -59) 1 1 0 )
(command "insert" "edge" '(298 -65) 1 1 0 )
(command "insert" "edge" '(291 -55) 1 1 0 )
(command "insert" "edge" '(294 -59) 1 1 0 )
(command "insert" "edge" '(298 -59) 1 1 0 )
(command "insert" "edge" '(293 -54) 1 1 0 )
(command "insert" "edge" '(296 -57) 1 1 0 )
(command "insert" "edge" '(295 -64) 1 1 0 )
(command "insert" "edge" '(299 -62) 1 1 0 )
(command "insert" "edge" '(294 -60) 1 1 0 )
(command "insert" "edge" '(294 -65) 1 1 0 )
(command "insert" "edge" '(296 -63) 1 1 0 )
(command "insert" "edge" '(295 -57) 1 1 0 )
(command "insert" "edge" '(296 -62) 1 1 0 )
(command "insert" "edge" '(299 -58) 1 1 0 )
(command "insert" "edge" '(297 -59) 1 1 0 )
(command "insert" "edge" '(292 -54) 1 1 0 )
(command "insert" "edge" '(297 -63) 1 1 0 )
(command "insert" "edge" '(295 -61) 1 1 0 )
(command "insert" "edge" '(296 -58) 1 1 0 )
(command "insert" "edge" '(291 -56) 1 1 0 )
(command "insert" "edge" '(293 -55) 1 1 0 )
(command "insert" "edge" '(297 -65) 1 1 0 )
(command "insert" "edge" '(294 -61) 1 1 0 )
(command "insert" "edge" '(296 -64) 1 1 0 )
(command "insert" "edge" '(298 -57) 1 1 0 )
(command "insert" "edge" '(299 -61) 1 1 0 )
(command "insert" "edge" '(292 -55) 1 1 0 )
(command "insert" "edge" '(294 -57) 1 1 0 )
(command "insert" "edge" '(297 -62) 1 1 0 )
(command "insert" "edge" '(292 -56) 1 1 0 )
(command "insert" "edge" '(295 -60) 1 1 0 )
(command "insert" "edge" '(298 -61) 1 1 0 )
(command "insert" "edge" '(299 -57) 1 1 0 )
(command "insert" "edge" '(291 -54) 1 1 0 )
(command "layer" "m" "Commmer" "" )
(command "insert" "Commmer" '(158 -59) 1 1 0 )
(command "insert" "Commmer" '(160 -57) 1 1 0 )
(command "insert" "Commmer" '(155 -57) 1 1 0 )
(command "insert" "Commmer" '(153 -58) 1 1 0 )
(command "insert" "Commmer" '(164 -57) 1 1 0 )
(command "insert" "Commmer" '(156 -59) 1 1 0 )
(command "insert" "Commmer" '(159 -57) 1 1 0 )
(command "insert" "Commmer" '(163 -58) 1 1 0 )
(command "insert" "Commmer" '(157 -58) 1 1 0 )
(command "insert" "Commmer" '(160 -58) 1 1 0 )
(command "insert" "Commmer" '(154 -58) 1 1 0 )
(command "insert" "Commmer" '(161 -59) 1 1 0 )
(command "insert" "Commmer" '(153 -57) 1 1 0 )
(command "insert" "Commmer" '(164 -58) 1 1 0 )
(command "insert" "Commmer" '(162 -57) 1 1 0 )
(command "insert" "Commmer" '(157 -57) 1 1 0 )
(command "insert" "Commmer" '(158 -57) 1 1 0 )
(command "insert" "Commmer" '(160 -59) 1 1 0 )
(command "insert" "Commmer" '(163 -57) 1 1 0 )
(command "insert" "Commmer" '(154 -59) 1 1 0 )
(command "insert" "Commmer" '(155 -59) 1 1 0 )
(command "insert" "Commmer" '(161 -58) 1 1 0 )
(command "insert" "Commmer" '(164 -59) 1 1 0 )
(command "insert" "Commmer" '(159 -59) 1 1 0 )
(command "insert" "Commmer" '(156 -57) 1 1 0 )
(command "insert" "Commmer" '(162 -58) 1 1 0 )
(command "insert" "Commmer" '(155 -58) 1 1 0 )
(command "insert" "Commmer" '(158 -58) 1 1 0 )
(command "insert" "Commmer" '(161 -57) 1 1 0 )
(command "insert" "Commmer" '(159 -58) 1 1 0 )
(command "insert" "Commmer" '(153 -59) 1 1 0 )
(command "insert" "Commmer" '(156 -58) 1 1 0 )
(command "insert" "Commmer" '(162 -59) 1 1 0 )
(command "insert" "Commmer" '(163 -59) 1 1 0 )
(command "insert" "Commmer" '(154 -57) 1 1 0 )
(command "insert" "Commmer" '(157 -59) 1 1 0 )
(command "layer" "m" "edge" "" )
(command "insert" "edge" '(263 -47) 1 1 0 )
(command "insert" "edge" '(256 -47) 1 1 0 )
(command "insert" "edge" '(256 -45) 1 1 0 )
(command "insert" "edge" '(260 -47) 1 1 0 )
(command "insert" "edge" '(263 -45) 1 1 0 )
(command "insert" "edge" '(257 -46) 1 1 0 )
(command "insert" "edge" '(255 -47) 1 1 0 )
(command "insert" "edge" '(260 -46) 1 1 0 )
(command "insert" "edge" '(260 -45) 1 1 0 )
(command "insert" "edge" '(258 -45) 1 1 0 )
(command "insert" "edge" '(255 -45) 1 1 0 )
(command "insert" "edge" '(262 -45) 1 1 0 )
(command "insert" "edge" '(258 -47) 1 1 0 )
(command "insert" "edge" '(262 -47) 1 1 0 )
(command "insert" "edge" '(259 -47) 1 1 0 )
(command "insert" "edge" '(263 -46) 1 1 0 )
(command "insert" "edge" '(259 -45) 1 1 0 )
(command "insert" "edge" '(256 -46) 1 1 0 )
(command "insert" "edge" '(255 -46) 1 1 0 )
(command "insert" "edge" '(261 -45) 1 1 0 )
(command "insert" "edge" '(257 -47) 1 1 0 )
(command "insert" "edge" '(261 -47) 1 1 0 )
(command "insert" "edge" '(261 -46) 1 1 0 )
(command "insert" "edge" '(257 -45) 1 1 0 )
(command "insert" "edge" '(258 -46) 1 1 0 )
(command "insert" "edge" '(259 -46) 1 1 0 )
(command "insert" "edge" '(262 -46) 1 1 0 )
(command "layer" "m" "Commmer" "" )
(command "insert" "Commmer" '(26 -33) 1 1 0 )
(command "insert" "Commmer" '(26 -35) 1 1 0 )
(command "insert" "Commmer" '(26 -34) 1 1 0 )
(command "insert" "Commmer" '(24 -33) 1 1 0 )
(command "insert" "Commmer" '(24 -35) 1 1 0 )
(command "insert" "Commmer" '(24 -34) 1 1 0 )
(command "insert" "Commmer" '(25 -34) 1 1 0 )
(command "insert" "Commmer" '(25 -35) 1 1 0 )
(command "insert" "Commmer" '(25 -33) 1 1 0 )
(command "layer" "m" "edge" "" )
(command "insert" "edge" '(148 -77) 1 1 0 )
(command "insert" "edge" '(114 -54) 1 1 0 )
(command "insert" "edge" '(147 -70) 1 1 0 )
(command "insert" "edge" '(150 -79) 1 1 0 )
(command "insert" "edge" '(147 -59) 1 1 0 )
(command "insert" "edge" '(115 -56) 1 1 0 )
(command "insert" "edge" '(160 -73) 1 1 0 )
(command "insert" "edge" '(149 -68) 1 1 0 )
(command "insert" "edge" '(148 -60) 1 1 0 )
(command "insert" "edge" '(116 -51) 1 1 0 )
(command "insert" "edge" '(161 -74) 1 1 0 )
(command "insert" "edge" '(120 -54) 1 1 0 )
(command "insert" "edge" '(112 -51) 1 1 0 )
(command "insert" "edge" '(121 -55) 1 1 0 )
(command "insert" "edge" '(164 -74) 1 1 0 )
(command "insert" "edge" '(156 -76) 1 1 0 )
(command "insert" "edge" '(123 -52) 1 1 0 )
(command "insert" "edge" '(122 -52) 1 1 0 )
(command "insert" "edge" '(104 -44) 1 1 0 )
(command "insert" "edge" '(124 -55) 1 1 0 )
(command "insert" "edge" '(152 -80) 1 1 0 )
(command "insert" "edge" '(153 -70) 1 1 0 )
(command "insert" "edge" '(154 -69) 1 1 0 )
(command "insert" "edge" '(125 -54) 1 1 0 )
(command "insert" "edge" '(155 -71) 1 1 0 )
(command "insert" "edge" '(136 -51) 1 1 0 )
(command "insert" "edge" '(163 -73) 1 1 0 )
(command "insert" "edge" '(133 -53) 1 1 0 )
(command "insert" "edge" '(154 -74) 1 1 0 )
(command "insert" "edge" '(155 -72) 1 1 0 )
(command "insert" "edge" '(107 -47) 1 1 0 )
(command "insert" "edge" '(144 -51) 1 1 0 )
(command "insert" "edge" '(157 -69) 1 1 0 )
(command "insert" "edge" '(158 -76) 1 1 0 )
(command "insert" "edge" '(140 -52) 1 1 0 )
(command "insert" "edge" '(170 -74) 1 1 0 )
(command "insert" "edge" '(137 -51) 1 1 0 )
(command "insert" "edge" '(169 -73) 1 1 0 )
(command "insert" "edge" '(157 -78) 1 1 0 )
(command "insert" "edge" '(148 -71) 1 1 0 )
(command "insert" "edge" '(142 -53) 1 1 0 )
(command "insert" "edge" '(175 -73) 1 1 0 )
(command "insert" "edge" '(147 -64) 1 1 0 )
(command "insert" "edge" '(149 -77) 1 1 0 )
(command "insert" "edge" '(148 -59) 1 1 0 )
(command "insert" "edge" '(147 -53) 1 1 0 )
(command "insert" "edge" '(129 -53) 1 1 0 )
(command "insert" "edge" '(146 -51) 1 1 0 )
(command "insert" "edge" '(160 -72) 1 1 0 )
(command "insert" "edge" '(149 -58) 1 1 0 )
(command "insert" "edge" '(148 -54) 1 1 0 )
(command "insert" "edge" '(116 -53) 1 1 0 )
(command "insert" "edge" '(151 -75) 1 1 0 )
(command "insert" "edge" '(121 -56) 1 1 0 )
(command "insert" "edge" '(149 -55) 1 1 0 )
(command "insert" "edge" '(119 -53) 1 1 0 )
(command "insert" "edge" '(153 -79) 1 1 0 )
(command "insert" "edge" '(152 -74) 1 1 0 )
(command "insert" "edge" '(117 -51) 1 1 0 )
(command "insert" "edge" '(157 -81) 1 1 0 )
(command "insert" "edge" '(156 -80) 1 1 0 )
(command "insert" "edge" '(152 -69) 1 1 0 )
(command "insert" "edge" '(168 -74) 1 1 0 )
(command "insert" "edge" '(140 -51) 1 1 0 )
(command "insert" "edge" '(157 -75) 1 1 0 )
(command "insert" "edge" '(127 -51) 1 1 0 )
(command "insert" "edge" '(108 -50) 1 1 0 )
(command "insert" "edge" '(158 -74) 1 1 0 )
(command "insert" "edge" '(112 -53) 1 1 0 )
(command "insert" "edge" '(156 -78) 1 1 0 )
(command "insert" "edge" '(111 -51) 1 1 0 )
(command "insert" "edge" '(112 -56) 1 1 0 )
(command "insert" "edge" '(114 -55) 1 1 0 )
(command "insert" "edge" '(182 -74) 1 1 0 )
(command "insert" "edge" '(146 -53) 1 1 0 )
(command "insert" "edge" '(142 -51) 1 1 0 )
(command "insert" "edge" '(150 -76) 1 1 0 )
(command "insert" "edge" '(147 -58) 1 1 0 )
(command "insert" "edge" '(171 -73) 1 1 0 )
(command "insert" "edge" '(149 -67) 1 1 0 )
(command "insert" "edge" '(148 -61) 1 1 0 )
(command "insert" "edge" '(129 -51) 1 1 0 )
(command "insert" "edge" '(161 -73) 1 1 0 )
(command "insert" "edge" '(120 -55) 1 1 0 )
(command "insert" "edge" '(151 -77) 1 1 0 )
(command "insert" "edge" '(121 -54) 1 1 0 )
(command "insert" "edge" '(123 -55) 1 1 0 )
(command "insert" "edge" '(153 -80) 1 1 0 )
(command "insert" "edge" '(148 -51) 1 1 0 )
(command "insert" "edge" '(119 -51) 1 1 0 )
(command "insert" "edge" '(123 -56) 1 1 0 )
(command "insert" "edge" '(153 -69) 1 1 0 )
(command "insert" "edge" '(176 -72) 1 1 0 )
(command "insert" "edge" '(125 -53) 1 1 0 )
(command "insert" "edge" '(155 -70) 1 1 0 )
(command "insert" "edge" '(136 -52) 1 1 0 )
(command "insert" "edge" '(106 -47) 1 1 0 )
(command "insert" "edge" '(134 -52) 1 1 0 )
(command "insert" "edge" '(133 -52) 1 1 0 )
(command "insert" "edge" '(154 -75) 1 1 0 )
(command "insert" "edge" '(155 -75) 1 1 0 )
(command "insert" "edge" '(107 -46) 1 1 0 )
(command "insert" "edge" '(144 -52) 1 1 0 )
(command "insert" "edge" '(102 -44) 1 1 0 )
(command "insert" "edge" '(154 -70) 1 1 0 )
(command "insert" "edge" '(158 -77) 1 1 0 )
(command "insert" "edge" '(156 -69) 1 1 0 )
(command "insert" "edge" '(108 -52) 1 1 0 )
(command "insert" "edge" '(169 -72) 1 1 0 )
(command "insert" "edge" '(150 -80) 1 1 0 )
(command "insert" "edge" '(148 -64) 1 1 0 )
(command "insert" "edge" '(175 -72) 1 1 0 )
(command "insert" "edge" '(147 -67) 1 1 0 )
(command "insert" "edge" '(143 -51) 1 1 0 )
(command "insert" "edge" '(174 -73) 1 1 0 )
(command "insert" "edge" '(150 -74) 1 1 0 )
(command "insert" "edge" '(147 -52) 1 1 0 )
(command "insert" "edge" '(99 -42) 1 1 0 )
(command "insert" "edge" '(129 -52) 1 1 0 )
(command "insert" "edge" '(115 -53) 1 1 0 )
(command "insert" "edge" '(149 -57) 1 1 0 )
(command "insert" "edge" '(148 -55) 1 1 0 )
(command "insert" "edge" '(130 -51) 1 1 0 )
(command "insert" "edge" '(116 -54) 1 1 0 )
(command "insert" "edge" '(151 -74) 1 1 0 )
(command "insert" "edge" '(149 -54) 1 1 0 )
(command "insert" "edge" '(117 -55) 1 1 0 )
(command "insert" "edge" '(119 -52) 1 1 0 )
(command "insert" "edge" '(153 -78) 1 1 0 )
(command "insert" "edge" '(175 -74) 1 1 0 )
(command "insert" "edge" '(167 -74) 1 1 0 )
(command "insert" "edge" '(173 -73) 1 1 0 )
(command "insert" "edge" '(152 -75) 1 1 0 )
(command "insert" "edge" '(147 -69) 1 1 0 )
(command "insert" "edge" '(157 -80) 1 1 0 )
(command "insert" "edge" '(156 -81) 1 1 0 )
(command "insert" "edge" '(180 -74) 1 1 0 )
(command "insert" "edge" '(177 -74) 1 1 0 )
(command "insert" "edge" '(102 -42) 1 1 0 )
(command "insert" "edge" '(157 -74) 1 1 0 )
(command "insert" "edge" '(108 -51) 1 1 0 )
(command "insert" "edge" '(158 -75) 1 1 0 )
(command "insert" "edge" '(112 -54) 1 1 0 )
(command "insert" "edge" '(156 -79) 1 1 0 )
(command "insert" "edge" '(106 -46) 1 1 0 )
(command "insert" "edge" '(109 -50) 1 1 0 )
(command "insert" "edge" '(113 -55) 1 1 0 )
(command "insert" "edge" '(150 -70) 1 1 0 )
(command "insert" "edge" '(149 -51) 1 1 0 )
(command "insert" "edge" '(114 -52) 1 1 0 )
(command "insert" "edge" '(147 -72) 1 1 0 )
(command "insert" "edge" '(140 -53) 1 1 0 )
(command "insert" "edge" '(150 -77) 1 1 0 )
(command "insert" "edge" '(147 -61) 1 1 0 )
(command "insert" "edge" '(171 -72) 1 1 0 )
(command "insert" "edge" '(128 -51) 1 1 0 )
(command "insert" "edge" '(143 -53) 1 1 0 )
(command "insert" "edge" '(149 -66) 1 1 0 )
(command "insert" "edge" '(148 -62) 1 1 0 )
(command "insert" "edge" '(124 -54) 1 1 0 )
(command "insert" "edge" '(163 -72) 1 1 0 )
(command "insert" "edge" '(161 -72) 1 1 0 )
(command "insert" "edge" '(149 -63) 1 1 0 )
(command "insert" "edge" '(151 -76) 1 1 0 )
(command "insert" "edge" '(121 -53) 1 1 0 )
(command "insert" "edge" '(123 -54) 1 1 0 )
(command "insert" "edge" '(99 -44) 1 1 0 )
(command "insert" "edge" '(105 -47) 1 1 0 )
(command "insert" "edge" '(176 -73) 1 1 0 )
(command "insert" "edge" '(110 -55) 1 1 0 )
(command "insert" "edge" '(125 -52) 1 1 0 )
(command "insert" "edge" '(136 -53) 1 1 0 )
(command "insert" "edge" '(106 -44) 1 1 0 )
(command "insert" "edge" '(134 -53) 1 1 0 )
(command "insert" "edge" '(126 -56) 1 1 0 )
(command "insert" "edge" '(154 -72) 1 1 0 )
(command "insert" "edge" '(155 -74) 1 1 0 )
(command "insert" "edge" '(100 -44) 1 1 0 )
(command "insert" "edge" '(144 -53) 1 1 0 )
(command "insert" "edge" '(139 -53) 1 1 0 )
(command "insert" "edge" '(154 -71) 1 1 0 )
(command "insert" "edge" '(156 -70) 1 1 0 )
(command "insert" "edge" '(108 -53) 1 1 0 )
(command "insert" "edge" '(170 -72) 1 1 0 )
(command "insert" "edge" '(109 -56) 1 1 0 )
(command "insert" "edge" '(148 -65) 1 1 0 )
(command "insert" "edge" '(111 -54) 1 1 0 )
(command "insert" "edge" '(147 -66) 1 1 0 )
(command "insert" "edge" '(149 -75) 1 1 0 )
(command "insert" "edge" '(150 -75) 1 1 0 )
(command "insert" "edge" '(147 -55) 1 1 0 )
(command "insert" "edge" '(115 -52) 1 1 0 )
(command "insert" "edge" '(154 -77) 1 1 0 )
(command "insert" "edge" '(149 -56) 1 1 0 )
(command "insert" "edge" '(110 -54) 1 1 0 )
(command "insert" "edge" '(155 -80) 1 1 0 )
(command "insert" "edge" '(116 -55) 1 1 0 )
(command "insert" "edge" '(151 -69) 1 1 0 )
(command "insert" "edge" '(111 -55) 1 1 0 )
(command "insert" "edge" '(118 -54) 1 1 0 )
(command "insert" "edge" '(117 -54) 1 1 0 )
(command "insert" "edge" '(121 -51) 1 1 0 )
(command "insert" "edge" '(119 -55) 1 1 0 )
(command "insert" "edge" '(162 -74) 1 1 0 )
(command "insert" "edge" '(153 -77) 1 1 0 )
(command "insert" "edge" '(133 -51) 1 1 0 )
(command "insert" "edge" '(131 -51) 1 1 0 )
(command "insert" "edge" '(152 -76) 1 1 0 )
(command "insert" "edge" '(150 -71) 1 1 0 )
(command "insert" "edge" '(132 -52) 1 1 0 )
(command "insert" "edge" '(178 -74) 1 1 0 )
(command "insert" "edge" '(134 -51) 1 1 0 )
(command "insert" "edge" '(156 -82) 1 1 0 )
(command "insert" "edge" '(154 -78) 1 1 0 )
(command "insert" "edge" '(177 -73) 1 1 0 )
(command "insert" "edge" '(159 -73) 1 1 0 )
(command "insert" "edge" '(102 -43) 1 1 0 )
(command "insert" "edge" '(157 -73) 1 1 0 )
(command "insert" "edge" '(180 -72) 1 1 0 )
(command "insert" "edge" '(158 -72) 1 1 0 )
(command "insert" "edge" '(112 -55) 1 1 0 )
(command "insert" "edge" '(156 -72) 1 1 0 )
(command "insert" "edge" '(109 -49) 1 1 0 )
(command "insert" "edge" '(113 -54) 1 1 0 )
(command "insert" "edge" '(148 -72) 1 1 0 )
(command "insert" "edge" '(114 -53) 1 1 0 )
(command "insert" "edge" '(158 -82) 1 1 0 )
(command "insert" "edge" '(149 -76) 1 1 0 )
(command "insert" "edge" '(149 -53) 1 1 0 )
(command "insert" "edge" '(147 -60) 1 1 0 )
(command "insert" "edge" '(128 -52) 1 1 0 )
(command "insert" "edge" '(122 -53) 1 1 0 )
(command "insert" "edge" '(149 -65) 1 1 0 )
(command "insert" "edge" '(148 -63) 1 1 0 )
(command "insert" "edge" '(126 -54) 1 1 0 )
(command "insert" "edge" '(149 -62) 1 1 0 )
(command "insert" "edge" '(160 -74) 1 1 0 )
(command "insert" "edge" '(121 -52) 1 1 0 )
(command "insert" "edge" '(147 -75) 1 1 0 )
(command "insert" "edge" '(122 -51) 1 1 0 )
(command "insert" "edge" '(153 -75) 1 1 0 )
(command "insert" "edge" '(105 -46) 1 1 0 )
(command "insert" "edge" '(176 -74) 1 1 0 )
(command "insert" "edge" '(132 -51) 1 1 0 )
(command "insert" "edge" '(125 -51) 1 1 0 )
(command "insert" "edge" '(152 -70) 1 1 0 )
(command "insert" "edge" '(106 -45) 1 1 0 )
(command "insert" "edge" '(166 -74) 1 1 0 )
(command "insert" "edge" '(110 -49) 1 1 0 )
(command "insert" "edge" '(154 -73) 1 1 0 )
(command "insert" "edge" '(155 -77) 1 1 0 )
(command "insert" "edge" '(135 -51) 1 1 0 )
(command "insert" "edge" '(139 -52) 1 1 0 )
(command "insert" "edge" '(138 -52) 1 1 0 )
(command "insert" "edge" '(103 -43) 1 1 0 )
(command "insert" "edge" '(156 -71) 1 1 0 )
(command "insert" "edge" '(157 -79) 1 1 0 )
(command "insert" "edge" '(146 -52) 1 1 0 )
(command "insert" "edge" '(170 -73) 1 1 0 )
(command "insert" "edge" '(158 -70) 1 1 0 )
(command "insert" "edge" '(109 -55) 1 1 0 )
(command "insert" "edge" '(148 -66) 1 1 0 )
(command "insert" "edge" '(113 -56) 1 1 0 )
(command "insert" "edge" '(150 -69) 1 1 0 )
(command "insert" "edge" '(174 -72) 1 1 0 )
(command "insert" "edge" '(111 -52) 1 1 0 )
(command "insert" "edge" '(149 -74) 1 1 0 )
(command "insert" "edge" '(150 -72) 1 1 0 )
(command "insert" "edge" '(147 -54) 1 1 0 )
(command "insert" "edge" '(156 -74) 1 1 0 )
(command "insert" "edge" '(115 -55) 1 1 0 )
(command "insert" "edge" '(149 -71) 1 1 0 )
(command "insert" "edge" '(173 -74) 1 1 0 )
(command "insert" "edge" '(117 -56) 1 1 0 )
(command "insert" "edge" '(154 -79) 1 1 0 )
(command "insert" "edge" '(149 -52) 1 1 0 )
(command "insert" "edge" '(118 -55) 1 1 0 )
(command "insert" "edge" '(117 -53) 1 1 0 )
(command "insert" "edge" '(119 -54) 1 1 0 )
(command "insert" "edge" '(123 -51) 1 1 0 )
(command "insert" "edge" '(153 -76) 1 1 0 )
(command "insert" "edge" '(139 -51) 1 1 0 )
(command "insert" "edge" '(124 -52) 1 1 0 )
(command "insert" "edge" '(152 -77) 1 1 0 )
(command "insert" "edge" '(132 -53) 1 1 0 )
(command "insert" "edge" '(154 -80) 1 1 0 )
(command "insert" "edge" '(156 -83) 1 1 0 )
(command "insert" "edge" '(110 -48) 1 1 0 )
(command "insert" "edge" '(179 -72) 1 1 0 )
(command "insert" "edge" '(177 -72) 1 1 0 )
(command "insert" "edge" '(135 -53) 1 1 0 )
(command "insert" "edge" '(159 -72) 1 1 0 )
(command "insert" "edge" '(157 -72) 1 1 0 )
(command "insert" "edge" '(126 -53) 1 1 0 )
(command "insert" "edge" '(158 -73) 1 1 0 )
(command "insert" "edge" '(156 -73) 1 1 0 )
(command "insert" "edge" '(109 -48) 1 1 0 )
(command "insert" "edge" '(108 -56) 1 1 0 )
(command "insert" "edge" '(113 -53) 1 1 0 )
(command "insert" "edge" '(148 -73) 1 1 0 )
(command "insert" "edge" '(158 -83) 1 1 0 )
(command "insert" "edge" '(147 -74) 1 1 0 )
(command "insert" "edge" '(148 -68) 1 1 0 )
(command "insert" "edge" '(172 -73) 1 1 0 )
(command "insert" "edge" '(147 -63) 1 1 0 )
(command "insert" "edge" '(171 -74) 1 1 0 )
(command "insert" "edge" '(111 -53) 1 1 0 )
(command "insert" "edge" '(128 -53) 1 1 0 )
(command "insert" "edge" '(149 -64) 1 1 0 )
(command "insert" "edge" '(148 -56) 1 1 0 )
(command "insert" "edge" '(163 -74) 1 1 0 )
(command "insert" "edge" '(128 -56) 1 1 0 )
(command "insert" "edge" '(120 -51) 1 1 0 )
(command "insert" "edge" '(165 -74) 1 1 0 )
(command "insert" "edge" '(151 -78) 1 1 0 )
(command "insert" "edge" '(179 -73) 1 1 0 )
(command "insert" "edge" '(172 -74) 1 1 0 )
(command "insert" "edge" '(119 -56) 1 1 0 )
(command "insert" "edge" '(124 -51) 1 1 0 )
(command "insert" "edge" '(107 -43) 1 1 0 )
(command "insert" "edge" '(153 -74) 1 1 0 )
(command "insert" "edge" '(105 -45) 1 1 0 )
(command "insert" "edge" '(152 -71) 1 1 0 )
(command "insert" "edge" '(106 -42) 1 1 0 )
(command "insert" "edge" '(101 -44) 1 1 0 )
(command "insert" "edge" '(155 -76) 1 1 0 )
(command "insert" "edge" '(148 -53) 1 1 0 )
(command "insert" "edge" '(138 -53) 1 1 0 )
(command "insert" "edge" '(103 -42) 1 1 0 )
(command "insert" "edge" '(126 -52) 1 1 0 )
(command "insert" "edge" '(126 -51) 1 1 0 )
(command "insert" "edge" '(108 -55) 1 1 0 )
(command "insert" "edge" '(158 -71) 1 1 0 )
(command "insert" "edge" '(141 -53) 1 1 0 )
(command "insert" "edge" '(109 -54) 1 1 0 )
(command "insert" "edge" '(113 -51) 1 1 0 )
(command "insert" "edge" '(148 -67) 1 1 0 )
(command "insert" "edge" '(114 -56) 1 1 0 )
(command "insert" "edge" '(107 -42) 1 1 0 )
(command "insert" "edge" '(147 -68) 1 1 0 )
(command "insert" "edge" '(149 -73) 1 1 0 )
(command "insert" "edge" '(150 -73) 1 1 0 )
(command "insert" "edge" '(147 -57) 1 1 0 )
(command "insert" "edge" '(115 -54) 1 1 0 )
(command "insert" "edge" '(149 -70) 1 1 0 )
(command "insert" "edge" '(110 -52) 1 1 0 )
(command "insert" "edge" '(151 -71) 1 1 0 )
(command "insert" "edge" '(120 -52) 1 1 0 )
(command "insert" "edge" '(165 -73) 1 1 0 )
(command "insert" "edge" '(117 -52) 1 1 0 )
(command "insert" "edge" '(164 -72) 1 1 0 )
(command "insert" "edge" '(162 -72) 1 1 0 )
(command "insert" "edge" '(122 -54) 1 1 0 )
(command "insert" "edge" '(104 -42) 1 1 0 )
(command "insert" "edge" '(131 -53) 1 1 0 )
(command "insert" "edge" '(124 -53) 1 1 0 )
(command "insert" "edge" '(152 -78) 1 1 0 )
(command "insert" "edge" '(105 -43) 1 1 0 )
(command "insert" "edge" '(125 -56) 1 1 0 )
(command "insert" "edge" '(155 -69) 1 1 0 )
(command "insert" "edge" '(178 -72) 1 1 0 )
(command "insert" "edge" '(118 -52) 1 1 0 )
(command "insert" "edge" '(154 -76) 1 1 0 )
(command "insert" "edge" '(107 -45) 1 1 0 )
(command "insert" "edge" '(135 -52) 1 1 0 )
(command "insert" "edge" '(157 -71) 1 1 0 )
(command "insert" "edge" '(158 -78) 1 1 0 )
(command "insert" "edge" '(103 -44) 1 1 0 )
(command "insert" "edge" '(126 -55) 1 1 0 )
(command "insert" "edge" '(113 -52) 1 1 0 )
(command "insert" "edge" '(130 -52) 1 1 0 )
(command "insert" "edge" '(148 -74) 1 1 0 )
(command "insert" "edge" '(114 -51) 1 1 0 )
(command "insert" "edge" '(158 -80) 1 1 0 )
(command "insert" "edge" '(147 -77) 1 1 0 )
(command "insert" "edge" '(148 -69) 1 1 0 )
(command "insert" "edge" '(151 -80) 1 1 0 )
(command "insert" "edge" '(147 -62) 1 1 0 )
(command "insert" "edge" '(128 -54) 1 1 0 )
(command "insert" "edge" '(174 -74) 1 1 0 )
(command "insert" "edge" '(148 -57) 1 1 0 )
(command "insert" "edge" '(147 -51) 1 1 0 )
(command "insert" "edge" '(116 -56) 1 1 0 )
(command "insert" "edge" '(149 -60) 1 1 0 )
(command "insert" "edge" '(148 -52) 1 1 0 )
(command "insert" "edge" '(127 -54) 1 1 0 )
(command "insert" "edge" '(151 -73) 1 1 0 )
(command "insert" "edge" '(172 -72) 1 1 0 )
(command "insert" "edge" '(153 -73) 1 1 0 )
(command "insert" "edge" '(105 -44) 1 1 0 )
(command "insert" "edge" '(167 -73) 1 1 0 )
(command "insert" "edge" '(100 -42) 1 1 0 )
(command "insert" "edge" '(152 -72) 1 1 0 )
(command "insert" "edge" '(106 -43) 1 1 0 )
(command "insert" "edge" '(166 -72) 1 1 0 )
(command "insert" "edge" '(157 -83) 1 1 0 )
(command "insert" "edge" '(155 -79) 1 1 0 )
(command "insert" "edge" '(149 -61) 1 1 0 )
(command "insert" "edge" '(145 -53) 1 1 0 )
(command "insert" "edge" '(168 -72) 1 1 0 )
(command "insert" "edge" '(181 -74) 1 1 0 )
(command "insert" "edge" '(181 -72) 1 1 0 )
(command "insert" "edge" '(108 -48) 1 1 0 )
(command "insert" "edge" '(157 -82) 1 1 0 )
(command "insert" "edge" '(141 -52) 1 1 0 )
(command "insert" "edge" '(127 -53) 1 1 0 )
(command "insert" "edge" '(108 -54) 1 1 0 )
(command "insert" "edge" '(109 -53) 1 1 0 )
(command "insert" "edge" '(111 -56) 1 1 0 )
(command "insert" "edge" '(148 -76) 1 1 0 )
(command "insert" "edge" '(155 -78) 1 1 0 )
(command "insert" "edge" '(157 -77) 1 1 0 )
(command "insert" "edge" '(147 -71) 1 1 0 )
(command "insert" "edge" '(149 -72) 1 1 0 )
(command "insert" "edge" '(150 -78) 1 1 0 )
(command "insert" "edge" '(147 -56) 1 1 0 )
(command "insert" "edge" '(143 -52) 1 1 0 )
(command "insert" "edge" '(149 -69) 1 1 0 )
(command "insert" "edge" '(110 -53) 1 1 0 )
(command "insert" "edge" '(151 -70) 1 1 0 )
(command "insert" "edge" '(120 -53) 1 1 0 )
(command "insert" "edge" '(118 -53) 1 1 0 )
(command "insert" "edge" '(127 -55) 1 1 0 )
(command "insert" "edge" '(122 -56) 1 1 0 )
(command "insert" "edge" '(164 -73) 1 1 0 )
(command "insert" "edge" '(118 -56) 1 1 0 )
(command "insert" "edge" '(162 -73) 1 1 0 )
(command "insert" "edge" '(123 -53) 1 1 0 )
(command "insert" "edge" '(122 -55) 1 1 0 )
(command "insert" "edge" '(104 -43) 1 1 0 )
(command "insert" "edge" '(109 -51) 1 1 0 )
(command "insert" "edge" '(131 -52) 1 1 0 )
(command "insert" "edge" '(99 -43) 1 1 0 )
(command "insert" "edge" '(152 -79) 1 1 0 )
(command "insert" "edge" '(153 -71) 1 1 0 )
(command "insert" "edge" '(105 -42) 1 1 0 )
(command "insert" "edge" '(125 -55) 1 1 0 )
(command "insert" "edge" '(180 -73) 1 1 0 )
(command "insert" "edge" '(178 -73) 1 1 0 )
(command "insert" "edge" '(179 -74) 1 1 0 )
(command "insert" "edge" '(155 -73) 1 1 0 )
(command "insert" "edge" '(107 -44) 1 1 0 )
(command "insert" "edge" '(159 -74) 1 1 0 )
(command "insert" "edge" '(157 -70) 1 1 0 )
(command "insert" "edge" '(145 -51) 1 1 0 )
(command "insert" "edge" '(158 -79) 1 1 0 )
(command "insert" "edge" '(165 -72) 1 1 0 )
(command "insert" "edge" '(156 -75) 1 1 0 )
(command "insert" "edge" '(101 -43) 1 1 0 )
(command "insert" "edge" '(157 -76) 1 1 0 )
(command "insert" "edge" '(148 -75) 1 1 0 )
(command "insert" "edge" '(169 -74) 1 1 0 )
(command "insert" "edge" '(158 -81) 1 1 0 )
(command "insert" "edge" '(147 -76) 1 1 0 )
(command "insert" "edge" '(148 -70) 1 1 0 )
(command "insert" "edge" '(137 -53) 1 1 0 )
(command "insert" "edge" '(142 -52) 1 1 0 )
(command "insert" "edge" '(147 -65) 1 1 0 )
(command "insert" "edge" '(128 -55) 1 1 0 )
(command "insert" "edge" '(151 -79) 1 1 0 )
(command "insert" "edge" '(148 -58) 1 1 0 )
(command "insert" "edge" '(173 -72) 1 1 0 )
(command "insert" "edge" '(115 -51) 1 1 0 )
(command "insert" "edge" '(149 -59) 1 1 0 )
(command "insert" "edge" '(110 -51) 1 1 0 )
(command "insert" "edge" '(110 -50) 1 1 0 )
(command "insert" "edge" '(130 -53) 1 1 0 )
(command "insert" "edge" '(116 -52) 1 1 0 )
(command "insert" "edge" '(151 -72) 1 1 0 )
(command "insert" "edge" '(110 -56) 1 1 0 )
(command "insert" "edge" '(118 -51) 1 1 0 )
(command "insert" "edge" '(127 -52) 1 1 0 )
(command "insert" "edge" '(147 -73) 1 1 0 )
(command "insert" "edge" '(153 -72) 1 1 0 )
(command "insert" "edge" '(167 -72) 1 1 0 )
(command "insert" "edge" '(100 -43) 1 1 0 )
(command "insert" "edge" '(124 -56) 1 1 0 )
(command "insert" "edge" '(152 -73) 1 1 0 )
(command "insert" "edge" '(166 -73) 1 1 0 )
(command "insert" "edge" '(101 -42) 1 1 0 )
(command "insert" "edge" '(137 -52) 1 1 0 )
(command "insert" "edge" '(141 -51) 1 1 0 )
(command "insert" "edge" '(138 -51) 1 1 0 )
(command "insert" "edge" '(145 -52) 1 1 0 )
(command "insert" "edge" '(168 -73) 1 1 0 )
(command "insert" "edge" '(181 -73) 1 1 0 )
(command "insert" "edge" '(182 -73) 1 1 0 )
(command "insert" "edge" '(120 -56) 1 1 0 )
(command "insert" "edge" '(108 -49) 1 1 0 )
(command "insert" "edge" '(158 -69) 1 1 0 )
(command "insert" "edge" '(112 -52) 1 1 0 )
(command "insert" "edge" '(156 -77) 1 1 0 )
(command "insert" "edge" '(127 -56) 1 1 0 )
(command "insert" "edge" '(109 -52) 1 1 0 )
(command "insert" "edge" '(182 -72) 1 1 0 )
(command "layer" "m" "ped" "" )
(command "insert" "ped" '(211 -72) 1 1 0 )
(command "insert" "ped" '(200 -77) 1 1 0 )
(command "insert" "ped" '(189 -72) 1 1 0 )
(command "insert" "ped" '(191 -69) 1 1 0 )
(command "insert" "ped" '(202 -79) 1 1 0 )
(command "insert" "ped" '(186 -72) 1 1 0 )
(command "insert" "ped" '(207 -77) 1 1 0 )
(command "insert" "ped" '(199 -80) 1 1 0 )
(command "insert" "ped" '(211 -78) 1 1 0 )
(command "insert" "ped" '(186 -71) 1 1 0 )
(command "insert" "ped" '(191 -72) 1 1 0 )
(command "insert" "ped" '(188 -70) 1 1 0 )
(command "insert" "ped" '(195 -78) 1 1 0 )
(command "insert" "ped" '(209 -79) 1 1 0 )
(command "insert" "ped" '(187 -65) 1 1 0 )
(command "insert" "ped" '(192 -79) 1 1 0 )
(command "insert" "ped" '(201 -79) 1 1 0 )
(command "insert" "ped" '(191 -79) 1 1 0 )
(command "insert" "ped" '(189 -75) 1 1 0 )
(command "insert" "ped" '(201 -75) 1 1 0 )
(command "insert" "ped" '(199 -74) 1 1 0 )
(command "insert" "ped" '(211 -74) 1 1 0 )
(command "insert" "ped" '(200 -80) 1 1 0 )
(command "insert" "ped" '(198 -79) 1 1 0 )
(command "insert" "ped" '(207 -79) 1 1 0 )
(command "insert" "ped" '(205 -75) 1 1 0 )
(command "insert" "ped" '(210 -77) 1 1 0 )
(command "insert" "ped" '(190 -79) 1 1 0 )
(command "insert" "ped" '(204 -78) 1 1 0 )
(command "insert" "ped" '(209 -74) 1 1 0 )
(command "insert" "ped" '(201 -74) 1 1 0 )
(command "insert" "ped" '(197 -79) 1 1 0 )
(command "insert" "ped" '(189 -78) 1 1 0 )
(command "insert" "ped" '(194 -78) 1 1 0 )
(command "insert" "ped" '(203 -76) 1 1 0 )
(command "insert" "ped" '(208 -76) 1 1 0 )
(command "insert" "ped" '(211 -73) 1 1 0 )
(command "insert" "ped" '(198 -72) 1 1 0 )
(command "insert" "ped" '(211 -79) 1 1 0 )
(command "insert" "ped" '(205 -78) 1 1 0 )
(command "insert" "ped" '(202 -80) 1 1 0 )
(command "insert" "ped" '(210 -78) 1 1 0 )
(command "insert" "ped" '(190 -72) 1 1 0 )
(command "insert" "ped" '(187 -70) 1 1 0 )
(command "insert" "ped" '(188 -72) 1 1 0 )
(command "insert" "ped" '(207 -72) 1 1 0 )
(command "insert" "ped" '(196 -79) 1 1 0 )
(command "insert" "ped" '(187 -64) 1 1 0 )
(command "insert" "ped" '(188 -63) 1 1 0 )
(command "insert" "ped" '(202 -75) 1 1 0 )
(command "insert" "ped" '(203 -75) 1 1 0 )
(command "insert" "ped" '(199 -76) 1 1 0 )
(command "insert" "ped" '(186 -67) 1 1 0 )
(command "insert" "ped" '(199 -78) 1 1 0 )
(command "insert" "ped" '(206 -77) 1 1 0 )
(command "insert" "ped" '(188 -66) 1 1 0 )
(command "insert" "ped" '(192 -80) 1 1 0 )
(command "insert" "ped" '(212 -75) 1 1 0 )
(command "insert" "ped" '(190 -69) 1 1 0 )
(command "insert" "ped" '(210 -72) 1 1 0 )
(command "insert" "ped" '(209 -80) 1 1 0 )
(command "insert" "ped" '(189 -79) 1 1 0 )
(command "insert" "ped" '(191 -75) 1 1 0 )
(command "insert" "ped" '(189 -71) 1 1 0 )
(command "insert" "ped" '(208 -73) 1 1 0 )
(command "insert" "ped" '(202 -76) 1 1 0 )
(command "insert" "ped" '(186 -73) 1 1 0 )
(command "insert" "ped" '(207 -75) 1 1 0 )
(command "insert" "ped" '(208 -79) 1 1 0 )
(command "insert" "ped" '(186 -68) 1 1 0 )
(command "insert" "ped" '(210 -73) 1 1 0 )
(command "insert" "ped" '(206 -78) 1 1 0 )
(command "insert" "ped" '(188 -71) 1 1 0 )
(command "insert" "ped" '(209 -78) 1 1 0 )
(command "insert" "ped" '(191 -78) 1 1 0 )
(command "insert" "ped" '(189 -80) 1 1 0 )
(command "insert" "ped" '(190 -70) 1 1 0 )
(command "insert" "ped" '(212 -77) 1 1 0 )
(command "insert" "ped" '(194 -80) 1 1 0 )
(command "insert" "ped" '(201 -78) 1 1 0 )
(command "insert" "ped" '(200 -75) 1 1 0 )
(command "insert" "ped" '(189 -74) 1 1 0 )
(command "insert" "ped" '(196 -78) 1 1 0 )
(command "insert" "ped" '(201 -80) 1 1 0 )
(command "insert" "ped" '(212 -76) 1 1 0 )
(command "insert" "ped" '(186 -74) 1 1 0 )
(command "insert" "ped" '(198 -76) 1 1 0 )
(command "insert" "ped" '(207 -78) 1 1 0 )
(command "insert" "ped" '(199 -79) 1 1 0 )
(command "insert" "ped" '(206 -75) 1 1 0 )
(command "insert" "ped" '(190 -76) 1 1 0 )
(command "insert" "ped" '(204 -79) 1 1 0 )
(command "insert" "ped" '(188 -68) 1 1 0 )
(command "insert" "ped" '(209 -73) 1 1 0 )
(command "insert" "ped" '(212 -74) 1 1 0 )
(command "insert" "ped" '(212 -72) 1 1 0 )
(command "insert" "ped" '(201 -73) 1 1 0 )
(command "insert" "ped" '(211 -77) 1 1 0 )
(command "insert" "ped" '(206 -80) 1 1 0 )
(command "insert" "ped" '(197 -78) 1 1 0 )
(command "insert" "ped" '(191 -77) 1 1 0 )
(command "insert" "ped" '(189 -77) 1 1 0 )
(command "insert" "ped" '(194 -79) 1 1 0 )
(command "insert" "ped" '(203 -79) 1 1 0 )
(command "insert" "ped" '(208 -77) 1 1 0 )
(command "insert" "ped" '(203 -80) 1 1 0 )
(command "insert" "ped" '(198 -73) 1 1 0 )
(command "insert" "ped" '(208 -80) 1 1 0 )
(command "insert" "ped" '(205 -77) 1 1 0 )
(command "insert" "ped" '(210 -79) 1 1 0 )
(command "insert" "ped" '(190 -73) 1 1 0 )
(command "insert" "ped" '(204 -76) 1 1 0 )
(command "insert" "ped" '(188 -73) 1 1 0 )
(command "insert" "ped" '(200 -74) 1 1 0 )
(command "insert" "ped" '(187 -74) 1 1 0 )
(command "insert" "ped" '(188 -67) 1 1 0 )
(command "insert" "ped" '(187 -63) 1 1 0 )
(command "insert" "ped" '(202 -72) 1 1 0 )
(command "insert" "ped" '(203 -74) 1 1 0 )
(command "insert" "ped" '(187 -66) 1 1 0 )
(command "insert" "ped" '(208 -74) 1 1 0 )
(command "insert" "ped" '(186 -64) 1 1 0 )
(command "insert" "ped" '(193 -80) 1 1 0 )
(command "insert" "ped" '(198 -74) 1 1 0 )
(command "insert" "ped" '(205 -80) 1 1 0 )
(command "insert" "ped" '(210 -80) 1 1 0 )
(command "insert" "ped" '(190 -74) 1 1 0 )
(command "insert" "ped" '(187 -68) 1 1 0 )
(command "insert" "ped" '(212 -73) 1 1 0 )
(command "insert" "ped" '(187 -73) 1 1 0 )
(command "insert" "ped" '(204 -80) 1 1 0 )
(command "insert" "ped" '(191 -74) 1 1 0 )
(command "insert" "ped" '(189 -70) 1 1 0 )
(command "insert" "ped" '(191 -76) 1 1 0 )
(command "insert" "ped" '(191 -71) 1 1 0 )
(command "insert" "ped" '(202 -77) 1 1 0 )
(command "insert" "ped" '(203 -73) 1 1 0 )
(command "insert" "ped" '(191 -80) 1 1 0 )
(command "insert" "ped" '(207 -74) 1 1 0 )
(command "insert" "ped" '(196 -80) 1 1 0 )
(command "insert" "ped" '(186 -69) 1 1 0 )
(command "insert" "ped" '(206 -79) 1 1 0 )
(command "insert" "ped" '(204 -75) 1 1 0 )
(command "insert" "ped" '(188 -64) 1 1 0 )
(command "insert" "ped" '(209 -77) 1 1 0 )
(command "insert" "ped" '(190 -71) 1 1 0 )
(command "insert" "ped" '(187 -67) 1 1 0 )
(command "insert" "ped" '(210 -74) 1 1 0 )
(command "insert" "ped" '(201 -77) 1 1 0 )
(command "insert" "ped" '(191 -73) 1 1 0 )
(command "insert" "ped" '(189 -73) 1 1 0 )
(command "insert" "ped" '(199 -73) 1 1 0 )
(command "insert" "ped" '(211 -80) 1 1 0 )
(command "insert" "ped" '(202 -78) 1 1 0 )
(command "insert" "ped" '(211 -76) 1 1 0 )
(command "insert" "ped" '(200 -79) 1 1 0 )
(command "insert" "ped" '(198 -77) 1 1 0 )
(command "insert" "ped" '(207 -73) 1 1 0 )
(command "insert" "ped" '(186 -70) 1 1 0 )
(command "insert" "ped" '(210 -75) 1 1 0 )
(command "insert" "ped" '(198 -80) 1 1 0 )
(command "insert" "ped" '(190 -77) 1 1 0 )
(command "insert" "ped" '(212 -80) 1 1 0 )
(command "insert" "ped" '(188 -69) 1 1 0 )
(command "insert" "ped" '(195 -79) 1 1 0 )
(command "insert" "ped" '(209 -72) 1 1 0 )
(command "insert" "ped" '(199 -77) 1 1 0 )
(command "insert" "ped" '(192 -78) 1 1 0 )
(command "insert" "ped" '(201 -72) 1 1 0 )
(command "insert" "ped" '(187 -69) 1 1 0 )
(command "insert" "ped" '(200 -73) 1 1 0 )
(command "insert" "ped" '(189 -76) 1 1 0 )
(command "insert" "ped" '(203 -78) 1 1 0 )
(command "insert" "ped" '(199 -75) 1 1 0 )
(command "insert" "ped" '(208 -78) 1 1 0 )
(command "insert" "ped" '(211 -75) 1 1 0 )
(command "insert" "ped" '(198 -78) 1 1 0 )
(command "insert" "ped" '(207 -76) 1 1 0 )
(command "insert" "ped" '(205 -76) 1 1 0 )
(command "insert" "ped" '(210 -76) 1 1 0 )
(command "insert" "ped" '(190 -78) 1 1 0 )
(command "insert" "ped" '(204 -77) 1 1 0 )
(command "insert" "ped" '(188 -74) 1 1 0 )
(command "insert" "ped" '(209 -75) 1 1 0 )
(command "insert" "ped" '(193 -78) 1 1 0 )
(command "insert" "ped" '(186 -63) 1 1 0 )
(command "insert" "ped" '(200 -72) 1 1 0 )
(command "insert" "ped" '(190 -80) 1 1 0 )
(command "insert" "ped" '(195 -80) 1 1 0 )
(command "insert" "ped" '(193 -79) 1 1 0 )
(command "insert" "ped" '(202 -73) 1 1 0 )
(command "insert" "ped" '(203 -77) 1 1 0 )
(command "insert" "ped" '(208 -75) 1 1 0 )
(command "insert" "ped" '(200 -76) 1 1 0 )
(command "insert" "ped" '(186 -65) 1 1 0 )
(command "insert" "ped" '(200 -78) 1 1 0 )
(command "insert" "ped" '(198 -75) 1 1 0 )
(command "insert" "ped" '(205 -79) 1 1 0 )
(command "insert" "ped" '(190 -75) 1 1 0 )
(command "insert" "ped" '(187 -71) 1 1 0 )
(command "insert" "ped" '(212 -78) 1 1 0 )
(command "insert" "ped" '(187 -72) 1 1 0 )
(command "insert" "ped" '(189 -69) 1 1 0 )
(command "insert" "ped" '(191 -70) 1 1 0 )
(command "insert" "ped" '(197 -80) 1 1 0 )
(command "insert" "ped" '(202 -74) 1 1 0 )
(command "insert" "ped" '(203 -72) 1 1 0 )
(command "insert" "ped" '(207 -80) 1 1 0 )
(command "insert" "ped" '(208 -72) 1 1 0 )
(command "insert" "ped" '(186 -66) 1 1 0 )
(command "insert" "ped" '(206 -76) 1 1 0 )
(command "insert" "ped" '(188 -65) 1 1 0 )
(command "insert" "ped" '(199 -72) 1 1 0 )
(command "insert" "ped" '(209 -76) 1 1 0 )
(command "insert" "ped" '(212 -79) 1 1 0 )
(command "insert" "ped" '(201 -76) 1 1 0 )
(command "layer" "m" "mroads" "" )
(command "insert" "mroads" '(5 -31) 1 1 0 )
(command "insert" "mroads" '(66 -31) 1 1 0 )
(command "insert" "mroads" '(6 -28) 1 1 0 )
(command "insert" "mroads" '(67 -30) 1 1 0 )
(command "insert" "mroads" '(7 -25) 1 1 0 )
(command "insert" "mroads" '(22 -19) 1 1 0 )
(command "insert" "mroads" '(18 -19) 1 1 0 )
(command "insert" "mroads" '(38 -21) 1 1 0 )
(command "insert" "mroads" '(114 -31) 1 1 0 )
(command "insert" "mroads" '(13 -32) 1 1 0 )
(command "insert" "mroads" '(35 -15) 1 1 0 )
(command "insert" "mroads" '(14 -31) 1 1 0 )
(command "insert" "mroads" '(15 -30) 1 1 0 )
(command "insert" "mroads" '(35 -21) 1 1 0 )
(command "insert" "mroads" '(12 -17) 1 1 0 )
(command "insert" "mroads" '(36 -22) 1 1 0 )
(command "insert" "mroads" '(1 -28) 1 1 0 )
(command "insert" "mroads" '(25 -15) 1 1 0 )
(command "insert" "mroads" '(39 -16) 1 1 0 )
(command "insert" "mroads" '(63 -30) 1 1 0 )
(command "insert" "mroads" '(37 -23) 1 1 0 )
(command "insert" "mroads" '(2 -27) 1 1 0 )
(command "insert" "mroads" '(109 -32) 1 1 0 )
(command "insert" "mroads" '(29 -17) 1 1 0 )
(command "insert" "mroads" '(31 -15) 1 1 0 )
(command "insert" "mroads" '(5 -24) 1 1 0 )
(command "insert" "mroads" '(20 -32) 1 1 0 )
(command "insert" "mroads" '(6 -23) 1 1 0 )
(command "insert" "mroads" '(30 -16) 1 1 0 )
(command "insert" "mroads" '(28 -32) 1 1 0 )
(command "insert" "mroads" '(7 -22) 1 1 0 )
(command "insert" "mroads" '(41 -23) 1 1 0 )
(command "insert" "mroads" '(42 -31) 1 1 0 )
(command "insert" "mroads" '(23 -19) 1 1 0 )
(command "insert" "mroads" '(21 -15) 1 1 0 )
(command "insert" "mroads" '(43 -30) 1 1 0 )
(command "insert" "mroads" '(116 -32) 1 1 0 )
(command "insert" "mroads" '(8 -18) 1 1 0 )
(command "insert" "mroads" '(11 -15) 1 1 0 )
(command "insert" "mroads" '(35 -26) 1 1 0 )
(command "insert" "mroads" '(9 -19) 1 1 0 )
(command "insert" "mroads" '(36 -29) 1 1 0 )
(command "insert" "mroads" '(1 -21) 1 1 0 )
(command "insert" "mroads" '(25 -16) 1 1 0 )
(command "insert" "mroads" '(29 -20) 1 1 0 )
(command "insert" "mroads" '(37 -16) 1 1 0 )
(command "insert" "mroads" '(98 -30) 1 1 0 )
(command "insert" "mroads" '(38 -31) 1 1 0 )
(command "insert" "mroads" '(99 -31) 1 1 0 )
(command "insert" "mroads" '(39 -30) 1 1 0 )
(command "insert" "mroads" '(3 -17) 1 1 0 )
(command "insert" "mroads" '(19 -18) 1 1 0 )
(command "insert" "mroads" '(7 -15) 1 1 0 )
(command "insert" "mroads" '(31 -18) 1 1 0 )
(command "insert" "mroads" '(46 -30) 1 1 0 )
(command "insert" "mroads" '(6 -32) 1 1 0 )
(command "insert" "mroads" '(34 -32) 1 1 0 )
(command "insert" "mroads" '(32 -16) 1 1 0 )
(command "insert" "mroads" '(94 -30) 1 1 0 )
(command "insert" "mroads" '(18 -31) 1 1 0 )
(command "insert" "mroads" '(42 -32) 1 1 0 )
(command "insert" "mroads" '(86 -32) 1 1 0 )
(command "insert" "mroads" '(34 -26) 1 1 0 )
(command "insert" "mroads" '(8 -25) 1 1 0 )
(command "insert" "mroads" '(94 -32) 1 1 0 )
(command "insert" "mroads" '(9 -20) 1 1 0 )
(command "insert" "mroads" '(10 -19) 1 1 0 )
(command "insert" "mroads" '(37 -25) 1 1 0 )
(command "insert" "mroads" '(26 -30) 1 1 0 )
(command "insert" "mroads" '(7 -18) 1 1 0 )
(command "insert" "mroads" '(38 -22) 1 1 0 )
(command "insert" "mroads" '(27 -31) 1 1 0 )
(command "insert" "mroads" '(40 -20) 1 1 0 )
(command "insert" "mroads" '(39 -23) 1 1 0 )
(command "insert" "mroads" '(88 -31) 1 1 0 )
(command "insert" "mroads" '(74 -30) 1 1 0 )
(command "insert" "mroads" '(89 -30) 1 1 0 )
(command "insert" "mroads" '(3 -22) 1 1 0 )
(command "insert" "mroads" '(75 -31) 1 1 0 )
(command "insert" "mroads" '(4 -17) 1 1 0 )
(command "insert" "mroads" '(5 -20) 1 1 0 )
(command "insert" "mroads" '(6 -27) 1 1 0 )
(command "insert" "mroads" '(21 -17) 1 1 0 )
(command "insert" "mroads" '(17 -17) 1 1 0 )
(command "insert" "mroads" '(22 -30) 1 1 0 )
(command "insert" "mroads" '(33 -22) 1 1 0 )
(command "insert" "mroads" '(23 -31) 1 1 0 )
(command "insert" "mroads" '(12 -32) 1 1 0 )
(command "insert" "mroads" '(34 -21) 1 1 0 )
(command "insert" "mroads" '(70 -30) 1 1 0 )
(command "insert" "mroads" '(85 -30) 1 1 0 )
(command "insert" "mroads" '(48 -32) 1 1 0 )
(command "insert" "mroads" '(71 -31) 1 1 0 )
(command "insert" "mroads" '(34 -15) 1 1 0 )
(command "insert" "mroads" '(11 -19) 1 1 0 )
(command "insert" "mroads" '(100 -32) 1 1 0 )
(command "insert" "mroads" '(27 -20) 1 1 0 )
(command "insert" "mroads" '(1 -25) 1 1 0 )
(command "insert" "mroads" '(108 -32) 1 1 0 )
(command "insert" "mroads" '(2 -30) 1 1 0 )
(command "insert" "mroads" '(3 -31) 1 1 0 )
(command "insert" "mroads" '(64 -31) 1 1 0 )
(command "insert" "mroads" '(4 -24) 1 1 0 )
(command "insert" "mroads" '(19 -32) 1 1 0 )
(command "insert" "mroads" '(62 -31) 1 1 0 )
(command "insert" "mroads" '(50 -30) 1 1 0 )
(command "insert" "mroads" '(65 -30) 1 1 0 )
(command "insert" "mroads" '(5 -29) 1 1 0 )
(command "insert" "mroads" '(27 -32) 1 1 0 )
(command "insert" "mroads" '(6 -18) 1 1 0 )
(command "insert" "mroads" '(101 -32) 1 1 0 )
(command "insert" "mroads" '(112 -31) 1 1 0 )
(command "insert" "mroads" '(41 -21) 1 1 0 )
(command "insert" "mroads" '(22 -17) 1 1 0 )
(command "insert" "mroads" '(79 -32) 1 1 0 )
(command "insert" "mroads" '(18 -17) 1 1 0 )
(command "insert" "mroads" '(23 -20) 1 1 0 )
(command "insert" "mroads" '(40 -31) 1 1 0 )
(command "insert" "mroads" '(115 -32) 1 1 0 )
(command "insert" "mroads" '(60 -31) 1 1 0 )
(command "insert" "mroads" '(61 -30) 1 1 0 )
(command "insert" "mroads" '(35 -23) 1 1 0 )
(command "insert" "mroads" '(24 -16) 1 1 0 )
(command "insert" "mroads" '(36 -16) 1 1 0 )
(command "insert" "mroads" '(108 -31) 1 1 0 )
(command "insert" "mroads" '(37 -21) 1 1 0 )
(command "insert" "mroads" '(2 -25) 1 1 0 )
(command "insert" "mroads" '(109 -30) 1 1 0 )
(command "insert" "mroads" '(7 -16) 1 1 0 )
(command "insert" "mroads" '(38 -26) 1 1 0 )
(command "insert" "mroads" '(40 -18) 1 1 0 )
(command "insert" "mroads" '(114 -32) 1 1 0 )
(command "insert" "mroads" '(116 -30) 1 1 0 )
(command "insert" "mroads" '(6 -21) 1 1 0 )
(command "insert" "mroads" '(111 -31) 1 1 0 )
(command "insert" "mroads" '(19 -15) 1 1 0 )
(command "insert" "mroads" '(41 -30) 1 1 0 )
(command "insert" "mroads" '(5 -32) 1 1 0 )
(command "insert" "mroads" '(33 -32) 1 1 0 )
(command "insert" "mroads" '(41 -32) 1 1 0 )
(command "insert" "mroads" '(7 -29) 1 1 0 )
(command "insert" "mroads" '(85 -32) 1 1 0 )
(command "insert" "mroads" '(9 -15) 1 1 0 )
(command "insert" "mroads" '(33 -26) 1 1 0 )
(command "insert" "mroads" '(22 -31) 1 1 0 )
(command "insert" "mroads" '(93 -32) 1 1 0 )
(command "insert" "mroads" '(8 -20) 1 1 0 )
(command "insert" "mroads" '(37 -15) 1 1 0 )
(command "insert" "mroads" '(35 -28) 1 1 0 )
(command "insert" "mroads" '(9 -17) 1 1 0 )
(command "insert" "mroads" '(96 -30) 1 1 0 )
(command "insert" "mroads" '(36 -31) 1 1 0 )
(command "insert" "mroads" '(15 -15) 1 1 0 )
(command "insert" "mroads" '(97 -31) 1 1 0 )
(command "insert" "mroads" '(37 -30) 1 1 0 )
(command "insert" "mroads" '(38 -29) 1 1 0 )
(command "insert" "mroads" '(83 -31) 1 1 0 )
(command "insert" "mroads" '(39 -24) 1 1 0 )
(command "insert" "mroads" '(5 -15) 1 1 0 )
(command "insert" "mroads" '(3 -19) 1 1 0 )
(command "insert" "mroads" '(4 -20) 1 1 0 )
(command "insert" "mroads" '(19 -20) 1 1 0 )
(command "insert" "mroads" '(92 -30) 1 1 0 )
(command "insert" "mroads" '(16 -31) 1 1 0 )
(command "insert" "mroads" '(93 -31) 1 1 0 )
(command "insert" "mroads" '(17 -30) 1 1 0 )
(command "insert" "mroads" '(32 -18) 1 1 0 )
(command "insert" "mroads" '(11 -32) 1 1 0 )
(command "insert" "mroads" '(33 -19) 1 1 0 )
(command "insert" "mroads" '(40 -29) 1 1 0 )
(command "insert" "mroads" '(8 -27) 1 1 0 )
(command "insert" "mroads" '(63 -32) 1 1 0 )
(command "insert" "mroads" '(5 -21) 1 1 0 )
(command "insert" "mroads" '(24 -30) 1 1 0 )
(command "insert" "mroads" '(14 -17) 1 1 0 )
(command "insert" "mroads" '(71 -32) 1 1 0 )
(command "insert" "mroads" '(10 -17) 1 1 0 )
(command "insert" "mroads" '(25 -31) 1 1 0 )
(command "insert" "mroads" '(99 -32) 1 1 0 )
(command "insert" "mroads" '(111 -32) 1 1 0 )
(command "insert" "mroads" '(107 -32) 1 1 0 )
(command "insert" "mroads" '(38 -20) 1 1 0 )
(command "insert" "mroads" '(12 -31) 1 1 0 )
(command "insert" "mroads" '(27 -17) 1 1 0 )
(command "insert" "mroads" '(39 -17) 1 1 0 )
(command "insert" "mroads" '(13 -30) 1 1 0 )
(command "insert" "mroads" '(41 -24) 1 1 0 )
(command "insert" "mroads" '(3 -24) 1 1 0 )
(command "insert" "mroads" '(56 -32) 1 1 0 )
(command "insert" "mroads" '(4 -19) 1 1 0 )
(command "insert" "mroads" '(26 -32) 1 1 0 )
(command "insert" "mroads" '(5 -18) 1 1 0 )
(command "insert" "mroads" '(20 -30) 1 1 0 )
(command "insert" "mroads" '(6 -25) 1 1 0 )
(command "insert" "mroads" '(21 -31) 1 1 0 )
(command "insert" "mroads" '(40 -22) 1 1 0 )
(command "insert" "mroads" '(78 -32) 1 1 0 )
(command "insert" "mroads" '(41 -18) 1 1 0 )
(command "insert" "mroads" '(18 -20) 1 1 0 )
(command "insert" "mroads" '(33 -20) 1 1 0 )
(command "insert" "mroads" '(69 -31) 1 1 0 )
(command "insert" "mroads" '(34 -19) 1 1 0 )
(command "insert" "mroads" '(32 -15) 1 1 0 )
(command "insert" "mroads" '(15 -32) 1 1 0 )
(command "insert" "mroads" '(64 -32) 1 1 0 )
(command "insert" "mroads" '(35 -16) 1 1 0 )
(command "insert" "mroads" '(38 -15) 1 1 0 )
(command "insert" "mroads" '(77 -32) 1 1 0 )
(command "insert" "mroads" '(1 -31) 1 1 0 )
(command "insert" "mroads" '(28 -17) 1 1 0 )
(command "insert" "mroads" '(2 -28) 1 1 0 )
(command "insert" "mroads" '(48 -30) 1 1 0 )
(command "insert" "mroads" '(113 -32) 1 1 0 )
(command "insert" "mroads" '(49 -31) 1 1 0 )
(command "insert" "mroads" '(4 -26) 1 1 0 )
(command "insert" "mroads" '(28 -15) 1 1 0 )
(command "insert" "mroads" '(5 -27) 1 1 0 )
(command "insert" "mroads" '(40 -26) 1 1 0 )
(command "insert" "mroads" '(4 -32) 1 1 0 )
(command "insert" "mroads" '(7 -21) 1 1 0 )
(command "insert" "mroads" '(18 -15) 1 1 0 )
(command "insert" "mroads" '(40 -32) 1 1 0 )
(command "insert" "mroads" '(34 -20) 1 1 0 )
(command "insert" "mroads" '(58 -31) 1 1 0 )
(command "insert" "mroads" '(44 -30) 1 1 0 )
(command "insert" "mroads" '(59 -30) 1 1 0 )
(command "insert" "mroads" '(92 -32) 1 1 0 )
(command "insert" "mroads" '(45 -31) 1 1 0 )
(command "insert" "mroads" '(6 -17) 1 1 0 )
(command "insert" "mroads" '(106 -31) 1 1 0 )
(command "insert" "mroads" '(35 -25) 1 1 0 )
(command "insert" "mroads" '(24 -18) 1 1 0 )
(command "insert" "mroads" '(107 -30) 1 1 0 )
(command "insert" "mroads" '(36 -18) 1 1 0 )
(command "insert" "mroads" '(25 -19) 1 1 0 )
(command "insert" "mroads" '(13 -16) 1 1 0 )
(command "insert" "mroads" '(37 -19) 1 1 0 )
(command "insert" "mroads" '(2 -23) 1 1 0 )
(command "insert" "mroads" '(38 -24) 1 1 0 )
(command "insert" "mroads" '(39 -29) 1 1 0 )
(command "insert" "mroads" '(54 -31) 1 1 0 )
(command "insert" "mroads" '(115 -31) 1 1 0 )
(command "insert" "mroads" '(55 -30) 1 1 0 )
(command "insert" "mroads" '(22 -20) 1 1 0 )
(command "insert" "mroads" '(30 -20) 1 1 0 )
(command "insert" "mroads" '(19 -17) 1 1 0 )
(command "insert" "mroads" '(102 -31) 1 1 0 )
(command "insert" "mroads" '(41 -28) 1 1 0 )
(command "insert" "mroads" '(31 -17) 1 1 0 )
(command "insert" "mroads" '(103 -30) 1 1 0 )
(command "insert" "mroads" '(10 -32) 1 1 0 )
(command "insert" "mroads" '(22 -32) 1 1 0 )
(command "insert" "mroads" '(18 -32) 1 1 0 )
(command "insert" "mroads" '(33 -24) 1 1 0 )
(command "insert" "mroads" '(62 -32) 1 1 0 )
(command "insert" "mroads" '(110 -30) 1 1 0 )
(command "insert" "mroads" '(34 -31) 1 1 0 )
(command "insert" "mroads" '(8 -22) 1 1 0 )
(command "insert" "mroads" '(23 -17) 1 1 0 )
(command "insert" "mroads" '(70 -32) 1 1 0 )
(command "insert" "mroads" '(35 -30) 1 1 0 )
(command "insert" "mroads" '(98 -32) 1 1 0 )
(command "insert" "mroads" '(36 -25) 1 1 0 )
(command "insert" "mroads" '(10 -20) 1 1 0 )
(command "insert" "mroads" '(25 -20) 1 1 0 )
(command "insert" "mroads" '(82 -31) 1 1 0 )
(command "insert" "mroads" '(106 -32) 1 1 0 )
(command "insert" "mroads" '(37 -28) 1 1 0 )
(command "insert" "mroads" '(26 -19) 1 1 0 )
(command "insert" "mroads" '(38 -19) 1 1 0 )
(command "insert" "mroads" '(3 -15) 1 1 0 )
(command "insert" "mroads" '(39 -26) 1 1 0 )
(command "insert" "mroads" '(51 -31) 1 1 0 )
(command "insert" "mroads" '(3 -21) 1 1 0 )
(command "insert" "mroads" '(25 -32) 1 1 0 )
(command "insert" "mroads" '(90 -30) 1 1 0 )
(command "insert" "mroads" '(30 -31) 1 1 0 )
(command "insert" "mroads" '(4 -22) 1 1 0 )
(command "insert" "mroads" '(91 -31) 1 1 0 )
(command "insert" "mroads" '(31 -30) 1 1 0 )
(command "insert" "mroads" '(5 -23) 1 1 0 )
(command "insert" "mroads" '(20 -17) 1 1 0 )
(command "insert" "mroads" '(16 -17) 1 1 0 )
(command "insert" "mroads" '(21 -20) 1 1 0 )
(command "insert" "mroads" '(32 -20) 1 1 0 )
(command "insert" "mroads" '(33 -17) 1 1 0 )
(command "insert" "mroads" '(34 -22) 1 1 0 )
(command "insert" "mroads" '(8 -29) 1 1 0 )
(command "insert" "mroads" '(61 -31) 1 1 0 )
(command "insert" "mroads" '(86 -30) 1 1 0 )
(command "insert" "mroads" '(10 -31) 1 1 0 )
(command "insert" "mroads" '(6 -19) 1 1 0 )
(command "insert" "mroads" '(87 -31) 1 1 0 )
(command "insert" "mroads" '(11 -30) 1 1 0 )
(command "insert" "mroads" '(76 -32) 1 1 0 )
(command "insert" "mroads" '(27 -19) 1 1 0 )
(command "insert" "mroads" '(39 -19) 1 1 0 )
(command "insert" "mroads" '(28 -20) 1 1 0 )
(command "insert" "mroads" '(3 -26) 1 1 0 )
(command "insert" "mroads" '(40 -15) 1 1 0 )
(command "insert" "mroads" '(4 -29) 1 1 0 )
(command "insert" "mroads" '(19 -31) 1 1 0 )
(command "insert" "mroads" '(7 -26) 1 1 0 )
(command "insert" "mroads" '(5 -16) 1 1 0 )
(command "insert" "mroads" '(3 -32) 1 1 0 )
(command "insert" "mroads" '(66 -30) 1 1 0 )
(command "insert" "mroads" '(6 -31) 1 1 0 )
(command "insert" "mroads" '(67 -31) 1 1 0 )
(command "insert" "mroads" '(7 -30) 1 1 0 )
(command "insert" "mroads" '(22 -18) 1 1 0 )
(command "insert" "mroads" '(55 -32) 1 1 0 )
(command "insert" "mroads" '(18 -18) 1 1 0 )
(command "insert" "mroads" '(83 -32) 1 1 0 )
(command "insert" "mroads" '(114 -30) 1 1 0 )
(command "insert" "mroads" '(34 -17) 1 1 0 )
(command "insert" "mroads" '(91 -32) 1 1 0 )
(command "insert" "mroads" '(14 -30) 1 1 0 )
(command "insert" "mroads" '(36 -15) 1 1 0 )
(command "insert" "mroads" '(15 -31) 1 1 0 )
(command "insert" "mroads" '(35 -18) 1 1 0 )
(command "insert" "mroads" '(12 -16) 1 1 0 )
(command "insert" "mroads" '(36 -21) 1 1 0 )
(command "insert" "mroads" '(1 -29) 1 1 0 )
(command "insert" "mroads" '(63 -31) 1 1 0 )
(command "insert" "mroads" '(28 -19) 1 1 0 )
(command "insert" "mroads" '(2 -26) 1 1 0 )
(command "insert" "mroads" '(26 -15) 1 1 0 )
(command "insert" "mroads" '(12 -15) 1 1 0 )
(command "insert" "mroads" '(29 -18) 1 1 0 )
(command "insert" "mroads" '(5 -25) 1 1 0 )
(command "insert" "mroads" '(16 -15) 1 1 0 )
(command "insert" "mroads" '(6 -22) 1 1 0 )
(command "insert" "mroads" '(30 -19) 1 1 0 )
(command "insert" "mroads" '(41 -25) 1 1 0 )
(command "insert" "mroads" '(56 -31) 1 1 0 )
(command "insert" "mroads" '(9 -32) 1 1 0 )
(command "insert" "mroads" '(42 -30) 1 1 0 )
(command "insert" "mroads" '(23 -16) 1 1 0 )
(command "insert" "mroads" '(43 -31) 1 1 0 )
(command "insert" "mroads" '(17 -32) 1 1 0 )
(command "insert" "mroads" '(22 -15) 1 1 0 )
(command "insert" "mroads" '(61 -32) 1 1 0 )
(command "insert" "mroads" '(52 -30) 1 1 0 )
(command "insert" "mroads" '(105 -30) 1 1 0 )
(command "insert" "mroads" '(69 -32) 1 1 0 )
(command "insert" "mroads" '(34 -24) 1 1 0 )
(command "insert" "mroads" '(8 -17) 1 1 0 )
(command "insert" "mroads" '(97 -32) 1 1 0 )
(command "insert" "mroads" '(35 -27) 1 1 0 )
(command "insert" "mroads" '(24 -20) 1 1 0 )
(command "insert" "mroads" '(105 -32) 1 1 0 )
(command "insert" "mroads" '(36 -28) 1 1 0 )
(command "insert" "mroads" '(1 -22) 1 1 0 )
(command "insert" "mroads" '(6 -29) 1 1 0 )
(command "insert" "mroads" '(37 -17) 1 1 0 )
(command "insert" "mroads" '(2 -21) 1 1 0 )
(command "insert" "mroads" '(38 -30) 1 1 0 )
(command "insert" "mroads" '(53 -30) 1 1 0 )
(command "insert" "mroads" '(112 -32) 1 1 0 )
(command "insert" "mroads" '(39 -31) 1 1 0 )
(command "insert" "mroads" '(100 -31) 1 1 0 )
(command "insert" "mroads" '(24 -32) 1 1 0 )
(command "insert" "mroads" '(101 -30) 1 1 0 )
(command "insert" "mroads" '(19 -19) 1 1 0 )
(command "insert" "mroads" '(31 -19) 1 1 0 )
(command "insert" "mroads" '(20 -20) 1 1 0 )
(command "insert" "mroads" '(47 -31) 1 1 0 )
(command "insert" "mroads" '(32 -31) 1 1 0 )
(command "insert" "mroads" '(18 -30) 1 1 0 )
(command "insert" "mroads" '(33 -30) 1 1 0 )
(command "insert" "mroads" '(34 -29) 1 1 0 )
(command "insert" "mroads" '(8 -24) 1 1 0 )
(command "insert" "mroads" '(39 -32) 1 1 0 )
(command "insert" "mroads" '(80 -31) 1 1 0 )
(command "insert" "mroads" '(81 -30) 1 1 0 )
(command "insert" "mroads" '(36 -27) 1 1 0 )
(command "insert" "mroads" '(10 -18) 1 1 0 )
(command "insert" "mroads" '(75 -32) 1 1 0 )
(command "insert" "mroads" '(37 -26) 1 1 0 )
(command "insert" "mroads" '(26 -17) 1 1 0 )
(command "insert" "mroads" '(38 -17) 1 1 0 )
(command "insert" "mroads" '(39 -20) 1 1 0 )
(command "insert" "mroads" '(88 -30) 1 1 0 )
(command "insert" "mroads" '(28 -31) 1 1 0 )
(command "insert" "mroads" '(89 -31) 1 1 0 )
(command "insert" "mroads" '(29 -30) 1 1 0 )
(command "insert" "mroads" '(3 -23) 1 1 0 )
(command "insert" "mroads" '(4 -16) 1 1 0 )
(command "insert" "mroads" '(2 -32) 1 1 0 )
(command "insert" "mroads" '(76 -31) 1 1 0 )
(command "insert" "mroads" '(46 -32) 1 1 0 )
(command "insert" "mroads" '(20 -19) 1 1 0 )
(command "insert" "mroads" '(33 -29) 1 1 0 )
(command "insert" "mroads" '(77 -30) 1 1 0 )
(command "insert" "mroads" '(6 -26) 1 1 0 )
(command "insert" "mroads" '(21 -18) 1 1 0 )
(command "insert" "mroads" '(54 -32) 1 1 0 )
(command "insert" "mroads" '(33 -23) 1 1 0 )
(command "insert" "mroads" '(90 -32) 1 1 0 )
(command "insert" "mroads" '(84 -30) 1 1 0 )
(command "insert" "mroads" '(8 -31) 1 1 0 )
(command "insert" "mroads" '(95 -31) 1 1 0 )
(command "insert" "mroads" '(85 -31) 1 1 0 )
(command "insert" "mroads" '(9 -30) 1 1 0 )
(command "insert" "mroads" '(15 -16) 1 1 0 )
(command "insert" "mroads" '(11 -16) 1 1 0 )
(command "insert" "mroads" '(1 -26) 1 1 0 )
(command "insert" "mroads" '(40 -21) 1 1 0 )
(command "insert" "mroads" '(73 -31) 1 1 0 )
(command "insert" "mroads" '(3 -28) 1 1 0 )
(command "insert" "mroads" '(64 -30) 1 1 0 )
(command "insert" "mroads" '(4 -31) 1 1 0 )
(command "insert" "mroads" '(65 -31) 1 1 0 )
(command "insert" "mroads" '(5 -30) 1 1 0 )
(command "insert" "mroads" '(40 -23) 1 1 0 )
(command "insert" "mroads" '(112 -30) 1 1 0 )
(command "insert" "mroads" '(8 -32) 1 1 0 )
(command "insert" "mroads" '(41 -22) 1 1 0 )
(command "insert" "mroads" '(22 -16) 1 1 0 )
(command "insert" "mroads" '(113 -31) 1 1 0 )
(command "insert" "mroads" '(18 -16) 1 1 0 )
(command "insert" "mroads" '(16 -32) 1 1 0 )
(command "insert" "mroads" '(60 -32) 1 1 0 )
(command "insert" "mroads" '(68 -32) 1 1 0 )
(command "insert" "mroads" '(96 -32) 1 1 0 )
(command "insert" "mroads" '(60 -30) 1 1 0 )
(command "insert" "mroads" '(104 -32) 1 1 0 )
(command "insert" "mroads" '(35 -20) 1 1 0 )
(command "insert" "mroads" '(24 -15) 1 1 0 )
(command "insert" "mroads" '(36 -23) 1 1 0 )
(command "insert" "mroads" '(108 -30) 1 1 0 )
(command "insert" "mroads" '(37 -22) 1 1 0 )
(command "insert" "mroads" '(2 -24) 1 1 0 )
(command "insert" "mroads" '(109 -31) 1 1 0 )
(command "insert" "mroads" '(29 -16) 1 1 0 )
(command "insert" "mroads" '(30 -15) 1 1 0 )
(command "insert" "mroads" '(25 -18) 1 1 0 )
(command "insert" "mroads" '(40 -30) 1 1 0 )
(command "insert" "mroads" '(30 -17) 1 1 0 )
(command "insert" "mroads" '(7 -17) 1 1 0 )
(command "insert" "mroads" '(31 -20) 1 1 0 )
(command "insert" "mroads" '(20 -15) 1 1 0 )
(command "insert" "mroads" '(33 -31) 1 1 0 )
(command "insert" "mroads" '(23 -18) 1 1 0 )
(command "insert" "mroads" '(47 -32) 1 1 0 )
(command "insert" "mroads" '(33 -27) 1 1 0 )
(command "insert" "mroads" '(38 -32) 1 1 0 )
(command "insert" "mroads" '(10 -15) 1 1 0 )
(command "insert" "mroads" '(8 -19) 1 1 0 )
(command "insert" "mroads" '(35 -29) 1 1 0 )
(command "insert" "mroads" '(9 -18) 1 1 0 )
(command "insert" "mroads" '(74 -32) 1 1 0 )
(command "insert" "mroads" '(52 -32) 1 1 0 )
(command "insert" "mroads" '(36 -30) 1 1 0 )
(command "insert" "mroads" '(51 -30) 1 1 0 )
(command "insert" "mroads" '(41 -27) 1 1 0 )
(command "insert" "mroads" '(82 -32) 1 1 0 )
(command "insert" "mroads" '(37 -31) 1 1 0 )
(command "insert" "mroads" '(26 -20) 1 1 0 )
(command "insert" "mroads" '(7 -19) 1 1 0 )
(command "insert" "mroads" '(98 -31) 1 1 0 )
(command "insert" "mroads" '(38 -28) 1 1 0 )
(command "insert" "mroads" '(40 -19) 1 1 0 )
(command "insert" "mroads" '(99 -30) 1 1 0 )
(command "insert" "mroads" '(39 -25) 1 1 0 )
(command "insert" "mroads" '(3 -16) 1 1 0 )
(command "insert" "mroads" '(1 -32) 1 1 0 )
(command "insert" "mroads" '(6 -15) 1 1 0 )
(command "insert" "mroads" '(46 -31) 1 1 0 )
(command "insert" "mroads" '(53 -32) 1 1 0 )
(command "insert" "mroads" '(16 -30) 1 1 0 )
(command "insert" "mroads" '(47 -30) 1 1 0 )
(command "insert" "mroads" '(17 -31) 1 1 0 )
(command "insert" "mroads" '(32 -17) 1 1 0 )
(command "insert" "mroads" '(7 -28) 1 1 0 )
(command "insert" "mroads" '(89 -32) 1 1 0 )
(command "insert" "mroads" '(7 -24) 1 1 0 )
(command "insert" "mroads" '(94 -31) 1 1 0 )
(command "insert" "mroads" '(33 -28) 1 1 0 )
(command "insert" "mroads" '(95 -30) 1 1 0 )
(command "insert" "mroads" '(34 -27) 1 1 0 )
(command "insert" "mroads" '(8 -26) 1 1 0 )
(command "insert" "mroads" '(14 -16) 1 1 0 )
(command "insert" "mroads" '(10 -16) 1 1 0 )
(command "insert" "mroads" '(37 -24) 1 1 0 )
(command "insert" "mroads" '(68 -30) 1 1 0 )
(command "insert" "mroads" '(26 -31) 1 1 0 )
(command "insert" "mroads" '(26 -18) 1 1 0 )
(command "insert" "mroads" '(38 -23) 1 1 0 )
(command "insert" "mroads" '(83 -30) 1 1 0 )
(command "insert" "mroads" '(27 -30) 1 1 0 )
(command "insert" "mroads" '(39 -22) 1 1 0 )
(command "insert" "mroads" '(13 -31) 1 1 0 )
(command "insert" "mroads" '(74 -31) 1 1 0 )
(command "insert" "mroads" '(3 -25) 1 1 0 )
(command "insert" "mroads" '(75 -30) 1 1 0 )
(command "insert" "mroads" '(4 -18) 1 1 0 )
(command "insert" "mroads" '(62 -30) 1 1 0 )
(command "insert" "mroads" '(5 -19) 1 1 0 )
(command "insert" "mroads" '(23 -32) 1 1 0 )
(command "insert" "mroads" '(6 -24) 1 1 0 )
(command "insert" "mroads" '(21 -16) 1 1 0 )
(command "insert" "mroads" '(17 -16) 1 1 0 )
(command "insert" "mroads" '(41 -19) 1 1 0 )
(command "insert" "mroads" '(31 -32) 1 1 0 )
(command "insert" "mroads" '(59 -32) 1 1 0 )
(command "insert" "mroads" '(33 -21) 1 1 0 )
(command "insert" "mroads" '(23 -30) 1 1 0 )
(command "insert" "mroads" '(34 -18) 1 1 0 )
(command "insert" "mroads" '(67 -32) 1 1 0 )
(command "insert" "mroads" '(6 -20) 1 1 0 )
(command "insert" "mroads" '(70 -31) 1 1 0 )
(command "insert" "mroads" '(33 -15) 1 1 0 )
(command "insert" "mroads" '(71 -30) 1 1 0 )
(command "insert" "mroads" '(11 -18) 1 1 0 )
(command "insert" "mroads" '(35 -17) 1 1 0 )
(command "insert" "mroads" '(1 -24) 1 1 0 )
(command "insert" "mroads" '(39 -15) 1 1 0 )
(command "insert" "mroads" '(28 -16) 1 1 0 )
(command "insert" "mroads" '(2 -31) 1 1 0 )
(command "insert" "mroads" '(12 -30) 1 1 0 )
(command "insert" "mroads" '(41 -31) 1 1 0 )
(command "insert" "mroads" '(79 -31) 1 1 0 )
(command "insert" "mroads" '(3 -30) 1 1 0 )
(command "insert" "mroads" '(40 -17) 1 1 0 )
(command "insert" "mroads" '(4 -25) 1 1 0 )
(command "insert" "mroads" '(50 -31) 1 1 0 )
(command "insert" "mroads" '(5 -28) 1 1 0 )
(command "insert" "mroads" '(29 -15) 1 1 0 )
(command "insert" "mroads" '(40 -25) 1 1 0 )
(command "insert" "mroads" '(41 -20) 1 1 0 )
(command "insert" "mroads" '(58 -30) 1 1 0 )
(command "insert" "mroads" '(37 -32) 1 1 0 )
(command "insert" "mroads" '(59 -31) 1 1 0 )
(command "insert" "mroads" '(41 -16) 1 1 0 )
(command "insert" "mroads" '(45 -32) 1 1 0 )
(command "insert" "mroads" '(73 -32) 1 1 0 )
(command "insert" "mroads" '(106 -30) 1 1 0 )
(command "insert" "mroads" '(35 -22) 1 1 0 )
(command "insert" "mroads" '(24 -17) 1 1 0 )
(command "insert" "mroads" '(107 -31) 1 1 0 )
(command "insert" "mroads" '(81 -32) 1 1 0 )
(command "insert" "mroads" '(36 -17) 1 1 0 )
(command "insert" "mroads" '(13 -17) 1 1 0 )
(command "insert" "mroads" '(37 -20) 1 1 0 )
(command "insert" "mroads" '(2 -22) 1 1 0 )
(command "insert" "mroads" '(72 -30) 1 1 0 )
(command "insert" "mroads" '(38 -27) 1 1 0 )
(command "insert" "mroads" '(54 -30) 1 1 0 )
(command "insert" "mroads" '(34 -23) 1 1 0 )
(command "insert" "mroads" '(55 -31) 1 1 0 )
(command "insert" "mroads" '(116 -31) 1 1 0 )
(command "insert" "mroads" '(102 -30) 1 1 0 )
(command "insert" "mroads" '(41 -29) 1 1 0 )
(command "insert" "mroads" '(103 -31) 1 1 0 )
(command "insert" "mroads" '(88 -32) 1 1 0 )
(command "insert" "mroads" '(84 -31) 1 1 0 )
(command "insert" "mroads" '(8 -15) 1 1 0 )
(command "insert" "mroads" '(33 -25) 1 1 0 )
(command "insert" "mroads" '(34 -30) 1 1 0 )
(command "insert" "mroads" '(8 -21) 1 1 0 )
(command "insert" "mroads" '(35 -31) 1 1 0 )
(command "insert" "mroads" '(9 -16) 1 1 0 )
(command "insert" "mroads" '(14 -15) 1 1 0 )
(command "insert" "mroads" '(40 -28) 1 1 0 )
(command "insert" "mroads" '(96 -31) 1 1 0 )
(command "insert" "mroads" '(36 -24) 1 1 0 )
(command "insert" "mroads" '(78 -31) 1 1 0 )
(command "insert" "mroads" '(82 -30) 1 1 0 )
(command "insert" "mroads" '(97 -30) 1 1 0 )
(command "insert" "mroads" '(37 -29) 1 1 0 )
(command "insert" "mroads" '(31 -31) 1 1 0 )
(command "insert" "mroads" '(38 -18) 1 1 0 )
(command "insert" "mroads" '(103 -32) 1 1 0 )
(command "insert" "mroads" '(39 -27) 1 1 0 )
(command "insert" "mroads" '(4 -15) 1 1 0 )
(command "insert" "mroads" '(7 -23) 1 1 0 )
(command "insert" "mroads" '(3 -18) 1 1 0 )
(command "insert" "mroads" '(30 -30) 1 1 0 )
(command "insert" "mroads" '(4 -21) 1 1 0 )
(command "insert" "mroads" '(79 -30) 1 1 0 )
(command "insert" "mroads" '(20 -16) 1 1 0 )
(command "insert" "mroads" '(92 -31) 1 1 0 )
(command "insert" "mroads" '(16 -16) 1 1 0 )
(command "insert" "mroads" '(30 -32) 1 1 0 )
(command "insert" "mroads" '(93 -30) 1 1 0 )
(command "insert" "mroads" '(58 -32) 1 1 0 )
(command "insert" "mroads" '(32 -19) 1 1 0 )
(command "insert" "mroads" '(33 -18) 1 1 0 )
(command "insert" "mroads" '(66 -32) 1 1 0 )
(command "insert" "mroads" '(110 -32) 1 1 0 )
(command "insert" "mroads" '(34 -25) 1 1 0 )
(command "insert" "mroads" '(8 -28) 1 1 0 )
(command "insert" "mroads" '(57 -30) 1 1 0 )
(command "insert" "mroads" '(24 -31) 1 1 0 )
(command "insert" "mroads" '(10 -30) 1 1 0 )
(command "insert" "mroads" '(25 -30) 1 1 0 )
(command "insert" "mroads" '(11 -31) 1 1 0 )
(command "insert" "mroads" '(72 -31) 1 1 0 )
(command "insert" "mroads" '(27 -16) 1 1 0 )
(command "insert" "mroads" '(49 -32) 1 1 0 )
(command "insert" "mroads" '(73 -30) 1 1 0 )
(command "insert" "mroads" '(3 -27) 1 1 0 )
(command "insert" "mroads" '(4 -28) 1 1 0 )
(command "insert" "mroads" '(41 -15) 1 1 0 )
(command "insert" "mroads" '(5 -17) 1 1 0 )
(command "insert" "mroads" '(20 -31) 1 1 0 )
(command "insert" "mroads" '(6 -30) 1 1 0 )
(command "insert" "mroads" '(21 -30) 1 1 0 )
(command "insert" "mroads" '(7 -31) 1 1 0 )
(command "insert" "mroads" '(68 -31) 1 1 0 )
(command "insert" "mroads" '(36 -32) 1 1 0 )
(command "insert" "mroads" '(69 -30) 1 1 0 )
(command "insert" "mroads" '(34 -16) 1 1 0 )
(command "insert" "mroads" '(44 -32) 1 1 0 )
(command "insert" "mroads" '(72 -32) 1 1 0 )
(command "insert" "mroads" '(6 -16) 1 1 0 )
(command "insert" "mroads" '(80 -32) 1 1 0 )
(command "insert" "mroads" '(11 -20) 1 1 0 )
(command "insert" "mroads" '(35 -19) 1 1 0 )
(command "insert" "mroads" '(36 -20) 1 1 0 )
(command "insert" "mroads" '(1 -30) 1 1 0 )
(command "insert" "mroads" '(28 -18) 1 1 0 )
(command "insert" "mroads" '(2 -29) 1 1 0 )
(command "insert" "mroads" '(48 -31) 1 1 0 )
(command "insert" "mroads" '(29 -19) 1 1 0 )
(command "insert" "mroads" '(27 -15) 1 1 0 )
(command "insert" "mroads" '(49 -30) 1 1 0 )
(command "insert" "mroads" '(4 -27) 1 1 0 )
(command "insert" "mroads" '(32 -32) 1 1 0 )
(command "insert" "mroads" '(5 -26) 1 1 0 )
(command "insert" "mroads" '(51 -32) 1 1 0 )
(command "insert" "mroads" '(40 -27) 1 1 0 )
(command "insert" "mroads" '(30 -18) 1 1 0 )
(command "insert" "mroads" '(17 -15) 1 1 0 )
(command "insert" "mroads" '(41 -26) 1 1 0 )
(command "insert" "mroads" '(56 -30) 1 1 0 )
(command "insert" "mroads" '(57 -31) 1 1 0 )
(command "insert" "mroads" '(86 -31) 1 1 0 )
(command "insert" "mroads" '(104 -30) 1 1 0 )
(command "insert" "mroads" '(44 -31) 1 1 0 )
(command "insert" "mroads" '(23 -15) 1 1 0 )
(command "insert" "mroads" '(105 -31) 1 1 0 )
(command "insert" "mroads" '(45 -30) 1 1 0 )
(command "insert" "mroads" '(8 -16) 1 1 0 )
(command "insert" "mroads" '(35 -24) 1 1 0 )
(command "insert" "mroads" '(50 -32) 1 1 0 )
(command "insert" "mroads" '(24 -19) 1 1 0 )
(command "insert" "mroads" '(36 -19) 1 1 0 )
(command "insert" "mroads" '(1 -23) 1 1 0 )
(command "insert" "mroads" '(104 -31) 1 1 0 )
(command "insert" "mroads" '(13 -15) 1 1 0 )
(command "insert" "mroads" '(37 -18) 1 1 0 )
(command "insert" "mroads" '(102 -32) 1 1 0 )
(command "insert" "mroads" '(38 -25) 1 1 0 )
(command "insert" "mroads" '(53 -31) 1 1 0 )
(command "insert" "mroads" '(78 -30) 1 1 0 )
(command "insert" "mroads" '(39 -28) 1 1 0 )
(command "insert" "mroads" '(84 -32) 1 1 0 )
(command "insert" "mroads" '(100 -30) 1 1 0 )
(command "insert" "mroads" '(115 -30) 1 1 0 )
(command "insert" "mroads" '(25 -17) 1 1 0 )
(command "insert" "mroads" '(101 -31) 1 1 0 )
(command "insert" "mroads" '(21 -32) 1 1 0 )
(command "insert" "mroads" '(19 -16) 1 1 0 )
(command "insert" "mroads" '(31 -16) 1 1 0 )
(command "insert" "mroads" '(29 -32) 1 1 0 )
(command "insert" "mroads" '(41 -17) 1 1 0 )
(command "insert" "mroads" '(32 -30) 1 1 0 )
(command "insert" "mroads" '(65 -32) 1 1 0 )
(command "insert" "mroads" '(52 -31) 1 1 0 )
(command "insert" "mroads" '(7 -20) 1 1 0 )
(command "insert" "mroads" '(110 -31) 1 1 0 )
(command "insert" "mroads" '(34 -28) 1 1 0 )
(command "insert" "mroads" '(8 -23) 1 1 0 )
(command "insert" "mroads" '(80 -30) 1 1 0 )
(command "insert" "mroads" '(111 -30) 1 1 0 )
(command "insert" "mroads" '(57 -32) 1 1 0 )
(command "insert" "mroads" '(81 -31) 1 1 0 )
(command "insert" "mroads" '(36 -26) 1 1 0 )
(command "insert" "mroads" '(40 -24) 1 1 0 )
(command "insert" "mroads" '(37 -27) 1 1 0 )
(command "insert" "mroads" '(26 -16) 1 1 0 )
(command "insert" "mroads" '(38 -16) 1 1 0 )
(command "insert" "mroads" '(39 -21) 1 1 0 )
(command "insert" "mroads" '(28 -30) 1 1 0 )
(command "insert" "mroads" '(29 -31) 1 1 0 )
(command "insert" "mroads" '(3 -20) 1 1 0 )
(command "insert" "mroads" '(90 -31) 1 1 0 )
(command "insert" "mroads" '(4 -23) 1 1 0 )
(command "insert" "mroads" '(76 -30) 1 1 0 )
(command "insert" "mroads" '(91 -30) 1 1 0 )
(command "insert" "mroads" '(7 -27) 1 1 0 )
(command "insert" "mroads" '(5 -22) 1 1 0 )
(command "insert" "mroads" '(20 -18) 1 1 0 )
(command "insert" "mroads" '(77 -31) 1 1 0 )
(command "insert" "mroads" '(21 -19) 1 1 0 )
(command "insert" "mroads" '(7 -32) 1 1 0 )
(command "insert" "mroads" '(35 -32) 1 1 0 )
(command "insert" "mroads" '(113 -30) 1 1 0 )
(command "insert" "mroads" '(33 -16) 1 1 0 )
(command "insert" "mroads" '(43 -32) 1 1 0 )
(command "insert" "mroads" '(8 -30) 1 1 0 )
(command "insert" "mroads" '(40 -16) 1 1 0 )
(command "insert" "mroads" '(87 -32) 1 1 0 )
(command "insert" "mroads" '(9 -31) 1 1 0 )
(command "insert" "mroads" '(95 -32) 1 1 0 )
(command "insert" "mroads" '(15 -17) 1 1 0 )
(command "insert" "mroads" '(87 -30) 1 1 0 )
(command "insert" "mroads" '(11 -17) 1 1 0 )
(command "insert" "mroads" '(27 -18) 1 1 0 )
(command "insert" "mroads" '(1 -27) 1 1 0 )
(command "insert" "mroads" '(39 -18) 1 1 0 )
(command "insert" "mroads" '(14 -32) 1 1 0 )
(command "insert" "mroads" '(3 -29) 1 1 0 )
(command "insert" "mroads" '(4 -30) 1 1 0 )
(command "insert" "mroads" '(19 -30) 1 1 0 )
(command "layer" "m" "Commmer" "" )
(command "insert" "Commmer" '(109 -17) 1 1 0 )
(command "insert" "Commmer" '(104 -24) 1 1 0 )
(command "insert" "Commmer" '(102 -29) 1 1 0 )
(command "insert" "Commmer" '(105 -21) 1 1 0 )
(command "insert" "Commmer" '(103 -24) 1 1 0 )
(command "insert" "Commmer" '(105 -28) 1 1 0 )
(command "insert" "Commmer" '(106 -18) 1 1 0 )
(command "insert" "Commmer" '(102 -25) 1 1 0 )
(command "insert" "Commmer" '(108 -17) 1 1 0 )
(command "insert" "Commmer" '(107 -27) 1 1 0 )
(command "insert" "Commmer" '(103 -28) 1 1 0 )
(command "insert" "Commmer" '(105 -24) 1 1 0 )
(command "insert" "Commmer" '(106 -22) 1 1 0 )
(command "insert" "Commmer" '(104 -27) 1 1 0 )
(command "insert" "Commmer" '(107 -18) 1 1 0 )
(command "insert" "Commmer" '(104 -25) 1 1 0 )
(command "insert" "Commmer" '(104 -29) 1 1 0 )
(command "insert" "Commmer" '(105 -19) 1 1 0 )
(command "insert" "Commmer" '(105 -20) 1 1 0 )
(command "insert" "Commmer" '(105 -29) 1 1 0 )
(command "insert" "Commmer" '(103 -27) 1 1 0 )
(command "insert" "Commmer" '(109 -15) 1 1 0 )
(command "insert" "Commmer" '(106 -19) 1 1 0 )
(command "insert" "Commmer" '(106 -24) 1 1 0 )
(command "insert" "Commmer" '(107 -26) 1 1 0 )
(command "insert" "Commmer" '(110 -15) 1 1 0 )
(command "insert" "Commmer" '(107 -21) 1 1 0 )
(command "insert" "Commmer" '(106 -23) 1 1 0 )
(command "insert" "Commmer" '(102 -26) 1 1 0 )
(command "insert" "Commmer" '(106 -28) 1 1 0 )
(command "insert" "Commmer" '(108 -15) 1 1 0 )
(command "insert" "Commmer" '(105 -27) 1 1 0 )
(command "insert" "Commmer" '(110 -16) 1 1 0 )
(command "insert" "Commmer" '(103 -26) 1 1 0 )
(command "insert" "Commmer" '(108 -16) 1 1 0 )
(command "insert" "Commmer" '(103 -25) 1 1 0 )
(command "insert" "Commmer" '(106 -25) 1 1 0 )
(command "insert" "Commmer" '(105 -23) 1 1 0 )
(command "insert" "Commmer" '(105 -18) 1 1 0 )
(command "insert" "Commmer" '(107 -20) 1 1 0 )
(command "insert" "Commmer" '(107 -22) 1 1 0 )
(command "insert" "Commmer" '(102 -27) 1 1 0 )
(command "insert" "Commmer" '(106 -29) 1 1 0 )
(command "insert" "Commmer" '(107 -25) 1 1 0 )
(command "insert" "Commmer" '(105 -26) 1 1 0 )
(command "insert" "Commmer" '(110 -17) 1 1 0 )
(command "insert" "Commmer" '(102 -28) 1 1 0 )
(command "insert" "Commmer" '(105 -22) 1 1 0 )
(command "insert" "Commmer" '(107 -29) 1 1 0 )
(command "insert" "Commmer" '(104 -26) 1 1 0 )
(command "insert" "Commmer" '(107 -23) 1 1 0 )
(command "insert" "Commmer" '(106 -21) 1 1 0 )
(command "insert" "Commmer" '(105 -25) 1 1 0 )
(command "insert" "Commmer" '(107 -28) 1 1 0 )
(command "insert" "Commmer" '(102 -24) 1 1 0 )
(command "insert" "Commmer" '(104 -28) 1 1 0 )
(command "insert" "Commmer" '(107 -24) 1 1 0 )
(command "insert" "Commmer" '(106 -27) 1 1 0 )
(command "insert" "Commmer" '(109 -16) 1 1 0 )
(command "insert" "Commmer" '(103 -29) 1 1 0 )
(command "insert" "Commmer" '(107 -19) 1 1 0 )
(command "insert" "Commmer" '(106 -26) 1 1 0 )
(command "insert" "Commmer" '(106 -20) 1 1 0 )
(command "layer" "m" "Res" "" )
(command "insert" "Res" '(15 -27) 1 1 0 )
(command "insert" "Res" '(27 -26) 1 1 0 )
(command "insert" "Res" '(20 -25) 1 1 0 )
(command "insert" "Res" '(20 -28) 1 1 0 )
(command "insert" "Res" '(15 -20) 1 1 0 )
(command "insert" "Res" '(21 -28) 1 1 0 )
(command "insert" "Res" '(11 -28) 1 1 0 )
(command "insert" "Res" '(17 -20) 1 1 0 )
(command "insert" "Res" '(16 -28) 1 1 0 )
(command "insert" "Res" '(9 -29) 1 1 0 )
(command "insert" "Res" '(14 -26) 1 1 0 )
(command "insert" "Res" '(15 -19) 1 1 0 )
(command "insert" "Res" '(26 -25) 1 1 0 )
(command "insert" "Res" '(29 -27) 1 1 0 )
(command "insert" "Res" '(17 -28) 1 1 0 )
(command "insert" "Res" '(19 -29) 1 1 0 )
(command "insert" "Res" '(22 -27) 1 1 0 )
(command "insert" "Res" '(13 -25) 1 1 0 )
(command "insert" "Res" '(27 -25) 1 1 0 )
(command "insert" "Res" '(18 -27) 1 1 0 )
(command "insert" "Res" '(25 -26) 1 1 0 )
(command "insert" "Res" '(16 -22) 1 1 0 )
(command "insert" "Res" '(11 -27) 1 1 0 )
(command "insert" "Res" '(17 -23) 1 1 0 )
(command "insert" "Res" '(22 -28) 1 1 0 )
(command "insert" "Res" '(12 -28) 1 1 0 )
(command "insert" "Res" '(27 -28) 1 1 0 )
(command "insert" "Res" '(20 -27) 1 1 0 )
(command "insert" "Res" '(15 -22) 1 1 0 )
(command "insert" "Res" '(28 -27) 1 1 0 )
(command "insert" "Res" '(26 -26) 1 1 0 )
(command "insert" "Res" '(12 -25) 1 1 0 )
(command "insert" "Res" '(14 -24) 1 1 0 )
(command "insert" "Res" '(19 -24) 1 1 0 )
(command "insert" "Res" '(13 -28) 1 1 0 )
(command "insert" "Res" '(24 -24) 1 1 0 )
(command "insert" "Res" '(18 -28) 1 1 0 )
(command "insert" "Res" '(29 -25) 1 1 0 )
(command "insert" "Res" '(16 -19) 1 1 0 )
(command "insert" "Res" '(14 -29) 1 1 0 )
(command "insert" "Res" '(17 -18) 1 1 0 )
(command "insert" "Res" '(9 -27) 1 1 0 )
(command "insert" "Res" '(27 -27) 1 1 0 )
(command "insert" "Res" '(18 -25) 1 1 0 )
(command "insert" "Res" '(20 -24) 1 1 0 )
(command "insert" "Res" '(23 -28) 1 1 0 )
(command "insert" "Res" '(25 -24) 1 1 0 )
(command "insert" "Res" '(15 -21) 1 1 0 )
(command "insert" "Res" '(21 -29) 1 1 0 )
(command "insert" "Res" '(11 -29) 1 1 0 )
(command "insert" "Res" '(17 -21) 1 1 0 )
(command "insert" "Res" '(16 -27) 1 1 0 )
(command "insert" "Res" '(23 -27) 1 1 0 )
(command "insert" "Res" '(10 -29) 1 1 0 )
(command "insert" "Res" '(28 -25) 1 1 0 )
(command "insert" "Res" '(26 -24) 1 1 0 )
(command "insert" "Res" '(29 -28) 1 1 0 )
(command "insert" "Res" '(28 -28) 1 1 0 )
(command "insert" "Res" '(12 -27) 1 1 0 )
(command "insert" "Res" '(17 -29) 1 1 0 )
(command "insert" "Res" '(19 -26) 1 1 0 )
(command "insert" "Res" '(13 -26) 1 1 0 )
(command "insert" "Res" '(24 -26) 1 1 0 )
(command "insert" "Res" '(28 -29) 1 1 0 )
(command "insert" "Res" '(18 -26) 1 1 0 )
(command "insert" "Res" '(20 -29) 1 1 0 )
(command "insert" "Res" '(16 -21) 1 1 0 )
(command "insert" "Res" '(28 -26) 1 1 0 )
(command "insert" "Res" '(24 -25) 1 1 0 )
(command "insert" "Res" '(27 -29) 1 1 0 )
(command "insert" "Res" '(20 -26) 1 1 0 )
(command "insert" "Res" '(15 -23) 1 1 0 )
(command "insert" "Res" '(21 -27) 1 1 0 )
(command "insert" "Res" '(16 -29) 1 1 0 )
(command "insert" "Res" '(9 -28) 1 1 0 )
(command "insert" "Res" '(12 -24) 1 1 0 )
(command "insert" "Res" '(14 -27) 1 1 0 )
(command "insert" "Res" '(19 -25) 1 1 0 )
(command "insert" "Res" '(10 -27) 1 1 0 )
(command "insert" "Res" '(13 -29) 1 1 0 )
(command "insert" "Res" '(15 -18) 1 1 0 )
(command "insert" "Res" '(29 -26) 1 1 0 )
(command "insert" "Res" '(16 -18) 1 1 0 )
(command "insert" "Res" '(14 -28) 1 1 0 )
(command "insert" "Res" '(17 -19) 1 1 0 )
(command "insert" "Res" '(19 -28) 1 1 0 )
(command "insert" "Res" '(13 -24) 1 1 0 )
(command "insert" "Res" '(27 -24) 1 1 0 )
(command "insert" "Res" '(18 -24) 1 1 0 )
(command "insert" "Res" '(23 -29) 1 1 0 )
(command "insert" "Res" '(25 -25) 1 1 0 )
(command "insert" "Res" '(16 -23) 1 1 0 )
(command "insert" "Res" '(17 -22) 1 1 0 )
(command "insert" "Res" '(22 -29) 1 1 0 )
(command "insert" "Res" '(12 -29) 1 1 0 )
(command "insert" "Res" '(17 -27) 1 1 0 )
(command "insert" "Res" '(10 -28) 1 1 0 )
(command "insert" "Res" '(28 -24) 1 1 0 )
(command "insert" "Res" '(29 -29) 1 1 0 )
(command "insert" "Res" '(12 -26) 1 1 0 )
(command "insert" "Res" '(14 -25) 1 1 0 )
(command "insert" "Res" '(19 -27) 1 1 0 )
(command "insert" "Res" '(13 -27) 1 1 0 )
(command "insert" "Res" '(15 -28) 1 1 0 )
(command "insert" "Res" '(18 -29) 1 1 0 )
(command "insert" "Res" '(15 -29) 1 1 0 )
(command "insert" "Res" '(29 -24) 1 1 0 )
(command "insert" "Res" '(16 -20) 1 1 0 )
(command "layer" "m" "Res" "" )
(command "insert" "Res" '(190 -91) 1 1 0 )
(command "insert" "Res" '(199 -85) 1 1 0 )
(command "insert" "Res" '(202 -81) 1 1 0 )
(command "insert" "Res" '(193 -90) 1 1 0 )
(command "insert" "Res" '(197 -83) 1 1 0 )
(command "insert" "Res" '(189 -86) 1 1 0 )
(command "insert" "Res" '(190 -92) 1 1 0 )
(command "insert" "Res" '(200 -83) 1 1 0 )
(command "insert" "Res" '(195 -89) 1 1 0 )
(command "insert" "Res" '(198 -81) 1 1 0 )
(command "insert" "Res" '(195 -81) 1 1 0 )
(command "insert" "Res" '(192 -92) 1 1 0 )
(command "insert" "Res" '(194 -83) 1 1 0 )
(command "insert" "Res" '(196 -83) 1 1 0 )
(command "insert" "Res" '(190 -84) 1 1 0 )
(command "insert" "Res" '(202 -82) 1 1 0 )
(command "insert" "Res" '(192 -81) 1 1 0 )
(command "insert" "Res" '(197 -89) 1 1 0 )
(command "insert" "Res" '(201 -81) 1 1 0 )
(command "insert" "Res" '(196 -88) 1 1 0 )
(command "insert" "Res" '(203 -82) 1 1 0 )
(command "insert" "Res" '(191 -85) 1 1 0 )
(command "insert" "Res" '(194 -91) 1 1 0 )
(command "insert" "Res" '(193 -88) 1 1 0 )
(command "insert" "Res" '(198 -82) 1 1 0 )
(command "insert" "Res" '(192 -89) 1 1 0 )
(command "insert" "Res" '(197 -81) 1 1 0 )
(command "insert" "Res" '(189 -84) 1 1 0 )
(command "insert" "Res" '(200 -85) 1 1 0 )
(command "insert" "Res" '(199 -82) 1 1 0 )
(command "insert" "Res" '(193 -83) 1 1 0 )
(command "insert" "Res" '(191 -84) 1 1 0 )
(command "insert" "Res" '(195 -83) 1 1 0 )
(command "insert" "Res" '(194 -81) 1 1 0 )
(command "insert" "Res" '(189 -92) 1 1 0 )
(command "insert" "Res" '(190 -90) 1 1 0 )
(command "insert" "Res" '(194 -92) 1 1 0 )
(command "insert" "Res" '(192 -83) 1 1 0 )
(command "insert" "Res" '(203 -81) 1 1 0 )
(command "insert" "Res" '(191 -86) 1 1 0 )
(command "insert" "Res" '(191 -90) 1 1 0 )
(command "insert" "Res" '(200 -82) 1 1 0 )
(command "insert" "Res" '(194 -89) 1 1 0 )
(command "insert" "Res" '(199 -81) 1 1 0 )
(command "insert" "Res" '(192 -91) 1 1 0 )
(command "insert" "Res" '(193 -91) 1 1 0 )
(command "insert" "Res" '(194 -82) 1 1 0 )
(command "insert" "Res" '(196 -82) 1 1 0 )
(command "insert" "Res" '(193 -81) 1 1 0 )
(command "insert" "Res" '(198 -85) 1 1 0 )
(command "insert" "Res" '(201 -82) 1 1 0 )
(command "insert" "Res" '(197 -87) 1 1 0 )
(command "insert" "Res" '(189 -90) 1 1 0 )
(command "insert" "Res" '(203 -83) 1 1 0 )
(command "insert" "Res" '(194 -90) 1 1 0 )
(command "insert" "Res" '(199 -84) 1 1 0 )
(command "insert" "Res" '(193 -89) 1 1 0 )
(command "insert" "Res" '(192 -88) 1 1 0 )
(command "insert" "Res" '(197 -82) 1 1 0 )
(command "insert" "Res" '(189 -85) 1 1 0 )
(command "insert" "Res" '(200 -84) 1 1 0 )
(command "insert" "Res" '(194 -87) 1 1 0 )
(command "insert" "Res" '(199 -83) 1 1 0 )
(command "insert" "Res" '(196 -87) 1 1 0 )
(command "insert" "Res" '(193 -92) 1 1 0 )
(command "insert" "Res" '(198 -86) 1 1 0 )
(command "insert" "Res" '(191 -92) 1 1 0 )
(command "insert" "Res" '(195 -88) 1 1 0 )
(command "insert" "Res" '(190 -85) 1 1 0 )
(command "insert" "Res" '(193 -87) 1 1 0 )
(command "insert" "Res" '(195 -87) 1 1 0 )
(command "insert" "Res" '(202 -83) 1 1 0 )
(command "insert" "Res" '(192 -82) 1 1 0 )
(command "insert" "Res" '(197 -88) 1 1 0 )
(command "insert" "Res" '(191 -91) 1 1 0 )
(command "insert" "Res" '(196 -89) 1 1 0 )
(command "insert" "Res" '(200 -81) 1 1 0 )
(command "insert" "Res" '(194 -88) 1 1 0 )
(command "insert" "Res" '(199 -86) 1 1 0 )
(command "insert" "Res" '(192 -87) 1 1 0 )
(command "insert" "Res" '(198 -83) 1 1 0 )
(command "insert" "Res" '(192 -90) 1 1 0 )
(command "insert" "Res" '(200 -86) 1 1 0 )
(command "insert" "Res" '(196 -81) 1 1 0 )
(command "insert" "Res" '(190 -86) 1 1 0 )
(command "insert" "Res" '(193 -82) 1 1 0 )
(command "insert" "Res" '(198 -84) 1 1 0 )
(command "insert" "Res" '(195 -82) 1 1 0 )
(command "insert" "Res" '(201 -83) 1 1 0 )
(command "insert" "Res" '(189 -91) 1 1 0 )
(command "layer" "m" "Res" "" )
(command "insert" "Res" '(220 -74) 1 1 0 )
(command "insert" "Res" '(221 -75) 1 1 0 )
(command "insert" "Res" '(219 -72) 1 1 0 )
(command "insert" "Res" '(219 -75) 1 1 0 )
(command "insert" "Res" '(220 -76) 1 1 0 )
(command "insert" "Res" '(219 -77) 1 1 0 )
(command "insert" "Res" '(220 -73) 1 1 0 )
(command "insert" "Res" '(219 -73) 1 1 0 )
(command "insert" "Res" '(221 -72) 1 1 0 )
(command "insert" "Res" '(220 -75) 1 1 0 )
(command "insert" "Res" '(219 -76) 1 1 0 )
(command "insert" "Res" '(219 -74) 1 1 0 )
(command "insert" "Res" '(221 -76) 1 1 0 )
(command "insert" "Res" '(220 -72) 1 1 0 )
(command "insert" "Res" '(221 -73) 1 1 0 )
(command "insert" "Res" '(220 -77) 1 1 0 )
(command "insert" "Res" '(221 -74) 1 1 0 )
(command "insert" "Res" '(221 -77) 1 1 0 )
(command "layer" "m" "edge" "" )
(command "insert" "edge" '(2 -39) 1 1 0 )
(command "insert" "edge" '(2 -41) 1 1 0 )
(command "insert" "edge" '(2 -43) 1 1 0 )
(command "insert" "edge" '(1 -46) 1 1 0 )
(command "insert" "edge" '(2 -47) 1 1 0 )
(command "insert" "edge" '(2 -45) 1 1 0 )
(command "insert" "edge" '(1 -39) 1 1 0 )
(command "insert" "edge" '(1 -42) 1 1 0 )
(command "insert" "edge" '(2 -42) 1 1 0 )
(command "insert" "edge" '(1 -43) 1 1 0 )
(command "insert" "edge" '(1 -44) 1 1 0 )
(command "insert" "edge" '(1 -45) 1 1 0 )
(command "insert" "edge" '(1 -40) 1 1 0 )
(command "insert" "edge" '(1 -47) 1 1 0 )
(command "insert" "edge" '(2 -44) 1 1 0 )
(command "insert" "edge" '(2 -40) 1 1 0 )
(command "insert" "edge" '(2 -46) 1 1 0 )
(command "insert" "edge" '(1 -41) 1 1 0 )
(command "layer" "m" "Commmer" "" )
(command "insert" "Commmer" '(221 -61) 1 1 0 )
(command "insert" "Commmer" '(219 -50) 1 1 0 )
(command "insert" "Commmer" '(217 -65) 1 1 0 )
(command "insert" "Commmer" '(217 -52) 1 1 0 )
(command "insert" "Commmer" '(220 -49) 1 1 0 )
(command "insert" "Commmer" '(216 -64) 1 1 0 )
(command "insert" "Commmer" '(218 -51) 1 1 0 )
(command "insert" "Commmer" '(217 -49) 1 1 0 )
(command "insert" "Commmer" '(216 -62) 1 1 0 )
(command "insert" "Commmer" '(219 -58) 1 1 0 )
(command "insert" "Commmer" '(217 -63) 1 1 0 )
(command "insert" "Commmer" '(220 -61) 1 1 0 )
(command "insert" "Commmer" '(218 -60) 1 1 0 )
(command "insert" "Commmer" '(219 -49) 1 1 0 )
(command "insert" "Commmer" '(220 -58) 1 1 0 )
(command "insert" "Commmer" '(221 -59) 1 1 0 )
(command "insert" "Commmer" '(220 -60) 1 1 0 )
(command "insert" "Commmer" '(218 -52) 1 1 0 )
(command "insert" "Commmer" '(221 -49) 1 1 0 )
(command "insert" "Commmer" '(218 -64) 1 1 0 )
(command "insert" "Commmer" '(220 -55) 1 1 0 )
(command "insert" "Commmer" '(219 -57) 1 1 0 )
(command "insert" "Commmer" '(221 -54) 1 1 0 )
(command "insert" "Commmer" '(218 -49) 1 1 0 )
(command "insert" "Commmer" '(219 -60) 1 1 0 )
(command "insert" "Commmer" '(217 -61) 1 1 0 )
(command "insert" "Commmer" '(216 -51) 1 1 0 )
(command "insert" "Commmer" '(217 -50) 1 1 0 )
(command "insert" "Commmer" '(216 -60) 1 1 0 )
(command "insert" "Commmer" '(221 -62) 1 1 0 )
(command "insert" "Commmer" '(221 -57) 1 1 0 )
(command "insert" "Commmer" '(219 -54) 1 1 0 )
(command "insert" "Commmer" '(218 -50) 1 1 0 )
(command "insert" "Commmer" '(216 -61) 1 1 0 )
(command "insert" "Commmer" '(219 -59) 1 1 0 )
(command "insert" "Commmer" '(216 -48) 1 1 0 )
(command "insert" "Commmer" '(218 -63) 1 1 0 )
(command "insert" "Commmer" '(219 -62) 1 1 0 )
(command "insert" "Commmer" '(221 -50) 1 1 0 )
(command "insert" "Commmer" '(216 -53) 1 1 0 )
(command "insert" "Commmer" '(220 -62) 1 1 0 )
(command "insert" "Commmer" '(221 -60) 1 1 0 )
(command "insert" "Commmer" '(220 -57) 1 1 0 )
(command "insert" "Commmer" '(221 -56) 1 1 0 )
(command "insert" "Commmer" '(220 -54) 1 1 0 )
(command "insert" "Commmer" '(217 -64) 1 1 0 )
(command "insert" "Commmer" '(221 -55) 1 1 0 )
(command "insert" "Commmer" '(216 -65) 1 1 0 )
(command "insert" "Commmer" '(218 -48) 1 1 0 )
(command "insert" "Commmer" '(216 -63) 1 1 0 )
(command "insert" "Commmer" '(219 -61) 1 1 0 )
(command "insert" "Commmer" '(217 -62) 1 1 0 )
(command "insert" "Commmer" '(216 -50) 1 1 0 )
(command "insert" "Commmer" '(220 -50) 1 1 0 )
(command "insert" "Commmer" '(218 -61) 1 1 0 )
(command "insert" "Commmer" '(217 -51) 1 1 0 )
(command "insert" "Commmer" '(217 -48) 1 1 0 )
(command "insert" "Commmer" '(219 -48) 1 1 0 )
(command "insert" "Commmer" '(220 -59) 1 1 0 )
(command "insert" "Commmer" '(217 -53) 1 1 0 )
(command "insert" "Commmer" '(221 -58) 1 1 0 )
(command "insert" "Commmer" '(219 -55) 1 1 0 )
(command "insert" "Commmer" '(218 -53) 1 1 0 )
(command "insert" "Commmer" '(218 -65) 1 1 0 )
(command "insert" "Commmer" '(220 -48) 1 1 0 )
(command "insert" "Commmer" '(219 -56) 1 1 0 )
(command "insert" "Commmer" '(216 -49) 1 1 0 )
(command "insert" "Commmer" '(218 -62) 1 1 0 )
(command "insert" "Commmer" '(221 -48) 1 1 0 )
(command "insert" "Commmer" '(216 -52) 1 1 0 )
(command "insert" "Commmer" '(217 -60) 1 1 0 )
(command "insert" "Commmer" '(220 -56) 1 1 0 )
(command "layer" "m" "ped" "" )
(command "insert" "ped" '(1 -3) 1 1 0 )
(command "insert" "ped" '(2 -18) 1 1 0 )
(command "insert" "ped" '(2 -8) 1 1 0 )
(command "insert" "ped" '(1 -17) 1 1 0 )
(command "insert" "ped" '(2 -1) 1 1 0 )
(command "insert" "ped" '(1 -15) 1 1 0 )
(command "insert" "ped" '(6 -2) 1 1 0 )
(command "insert" "ped" '(1 -6) 1 1 0 )
(command "insert" "ped" '(2 -12) 1 1 0 )
(command "insert" "ped" '(5 -1) 1 1 0 )
(command "insert" "ped" '(2 -5) 1 1 0 )
(command "insert" "ped" '(1 -11) 1 1 0 )
(command "insert" "ped" '(7 -2) 1 1 0 )
(command "insert" "ped" '(1 -2) 1 1 0 )
(command "insert" "ped" '(2 -19) 1 1 0 )
(command "insert" "ped" '(2 -9) 1 1 0 )
(command "insert" "ped" '(8 -1) 1 1 0 )
(command "insert" "ped" '(1 -16) 1 1 0 )
(command "insert" "ped" '(1 -14) 1 1 0 )
(command "insert" "ped" '(1 -5) 1 1 0 )
(command "insert" "ped" '(2 -13) 1 1 0 )
(command "insert" "ped" '(1 -20) 1 1 0 )
(command "insert" "ped" '(2 -2) 1 1 0 )
(command "insert" "ped" '(1 -10) 1 1 0 )
(command "insert" "ped" '(4 -1) 1 1 0 )
(command "insert" "ped" '(1 -1) 1 1 0 )
(command "insert" "ped" '(2 -16) 1 1 0 )
(command "insert" "ped" '(3 -2) 1 1 0 )
(command "insert" "ped" '(2 -6) 1 1 0 )
(command "insert" "ped" '(8 -2) 1 1 0 )
(command "insert" "ped" '(7 -1) 1 1 0 )
(command "insert" "ped" '(1 -13) 1 1 0 )
(command "insert" "ped" '(2 -20) 1 1 0 )
(command "insert" "ped" '(1 -4) 1 1 0 )
(command "insert" "ped" '(2 -10) 1 1 0 )
(command "insert" "ped" '(1 -19) 1 1 0 )
(command "insert" "ped" '(2 -3) 1 1 0 )
(command "insert" "ped" '(1 -9) 1 1 0 )
(command "insert" "ped" '(4 -2) 1 1 0 )
(command "insert" "ped" '(2 -14) 1 1 0 )
(command "insert" "ped" '(2 -17) 1 1 0 )
(command "insert" "ped" '(2 -7) 1 1 0 )
(command "insert" "ped" '(1 -12) 1 1 0 )
(command "insert" "ped" '(6 -1) 1 1 0 )
(command "insert" "ped" '(3 -1) 1 1 0 )
(command "insert" "ped" '(2 -11) 1 1 0 )
(command "insert" "ped" '(1 -18) 1 1 0 )
(command "insert" "ped" '(1 -8) 1 1 0 )
(command "insert" "ped" '(1 -7) 1 1 0 )
(command "insert" "ped" '(2 -15) 1 1 0 )
(command "insert" "ped" '(5 -2) 1 1 0 )
(command "insert" "ped" '(2 -4) 1 1 0 )
(command "layer" "m" "ped" "" )
(command "insert" "ped" '(267 -49) 1 1 0 )
(command "insert" "ped" '(266 -48) 1 1 0 )
(command "insert" "ped" '(257 -48) 1 1 0 )
(command "insert" "ped" '(261 -50) 1 1 0 )
(command "insert" "ped" '(256 -49) 1 1 0 )
(command "insert" "ped" '(269 -50) 1 1 0 )
(command "insert" "ped" '(253 -45) 1 1 0 )
(command "insert" "ped" '(259 -48) 1 1 0 )
(command "insert" "ped" '(253 -46) 1 1 0 )
(command "insert" "ped" '(254 -45) 1 1 0 )
(command "insert" "ped" '(267 -48) 1 1 0 )
(command "insert" "ped" '(258 -48) 1 1 0 )
(command "insert" "ped" '(262 -50) 1 1 0 )
(command "insert" "ped" '(255 -50) 1 1 0 )
(command "insert" "ped" '(252 -47) 1 1 0 )
(command "insert" "ped" '(261 -49) 1 1 0 )
(command "insert" "ped" '(256 -50) 1 1 0 )
(command "insert" "ped" '(263 -50) 1 1 0 )
(command "insert" "ped" '(260 -48) 1 1 0 )
(command "insert" "ped" '(269 -49) 1 1 0 )
(command "insert" "ped" '(264 -50) 1 1 0 )
(command "insert" "ped" '(268 -48) 1 1 0 )
(command "insert" "ped" '(252 -45) 1 1 0 )
(command "insert" "ped" '(258 -49) 1 1 0 )
(command "insert" "ped" '(261 -48) 1 1 0 )
(command "insert" "ped" '(254 -46) 1 1 0 )
(command "insert" "ped" '(260 -49) 1 1 0 )
(command "insert" "ped" '(269 -48) 1 1 0 )
(command "insert" "ped" '(255 -49) 1 1 0 )
(command "insert" "ped" '(257 -50) 1 1 0 )
(command "insert" "ped" '(265 -50) 1 1 0 )
(command "insert" "ped" '(259 -50) 1 1 0 )
(command "insert" "ped" '(268 -49) 1 1 0 )
(command "insert" "ped" '(252 -46) 1 1 0 )
(command "insert" "ped" '(263 -49) 1 1 0 )
(command "insert" "ped" '(267 -50) 1 1 0 )
(command "insert" "ped" '(253 -47) 1 1 0 )
(command "insert" "ped" '(262 -48) 1 1 0 )
(command "insert" "ped" '(254 -47) 1 1 0 )
(command "insert" "ped" '(266 -49) 1 1 0 )
(command "insert" "ped" '(264 -48) 1 1 0 )
(command "insert" "ped" '(258 -50) 1 1 0 )
(command "insert" "ped" '(260 -50) 1 1 0 )
(command "insert" "ped" '(255 -48) 1 1 0 )
(command "insert" "ped" '(257 -49) 1 1 0 )
(command "insert" "ped" '(268 -50) 1 1 0 )
(command "insert" "ped" '(265 -48) 1 1 0 )
(command "insert" "ped" '(256 -48) 1 1 0 )
(command "insert" "ped" '(263 -48) 1 1 0 )
(command "insert" "ped" '(264 -49) 1 1 0 )
(command "insert" "ped" '(262 -49) 1 1 0 )
(command "insert" "ped" '(259 -49) 1 1 0 )
(command "insert" "ped" '(266 -50) 1 1 0 )
(command "insert" "ped" '(265 -49) 1 1 0 )
(command "layer" "m" "Commmer" "" )
(command "insert" "Commmer" '(54 -35) 1 1 0 )
(command "insert" "Commmer" '(52 -35) 1 1 0 )
(command "insert" "Commmer" '(53 -34) 1 1 0 )
(command "insert" "Commmer" '(52 -33) 1 1 0 )
(command "insert" "Commmer" '(55 -35) 1 1 0 )
(command "insert" "Commmer" '(51 -34) 1 1 0 )
(command "insert" "Commmer" '(56 -34) 1 1 0 )
(command "insert" "Commmer" '(55 -33) 1 1 0 )
(command "insert" "Commmer" '(54 -34) 1 1 0 )
(command "insert" "Commmer" '(52 -34) 1 1 0 )
(command "insert" "Commmer" '(55 -34) 1 1 0 )
(command "insert" "Commmer" '(53 -35) 1 1 0 )
(command "insert" "Commmer" '(56 -35) 1 1 0 )
(command "insert" "Commmer" '(51 -35) 1 1 0 )
(command "insert" "Commmer" '(53 -33) 1 1 0 )
(command "insert" "Commmer" '(56 -33) 1 1 0 )
(command "insert" "Commmer" '(54 -33) 1 1 0 )
(command "insert" "Commmer" '(51 -33) 1 1 0 )
(command "layer" "m" "ped" "" )
(command "insert" "ped" '(205 -86) 1 1 0 )
(command "insert" "ped" '(210 -86) 1 1 0 )
(command "insert" "ped" '(212 -89) 1 1 0 )
(command "insert" "ped" '(207 -84) 1 1 0 )
(command "insert" "ped" '(212 -84) 1 1 0 )
(command "insert" "ped" '(209 -84) 1 1 0 )
(command "insert" "ped" '(203 -87) 1 1 0 )
(command "insert" "ped" '(208 -85) 1 1 0 )
(command "insert" "ped" '(209 -89) 1 1 0 )
(command "insert" "ped" '(211 -86) 1 1 0 )
(command "insert" "ped" '(203 -88) 1 1 0 )
(command "insert" "ped" '(208 -88) 1 1 0 )
(command "insert" "ped" '(205 -85) 1 1 0 )
(command "insert" "ped" '(206 -86) 1 1 0 )
(command "insert" "ped" '(210 -87) 1 1 0 )
(command "insert" "ped" '(204 -84) 1 1 0 )
(command "insert" "ped" '(207 -87) 1 1 0 )
(command "insert" "ped" '(212 -85) 1 1 0 )
(command "insert" "ped" '(205 -89) 1 1 0 )
(command "insert" "ped" '(201 -89) 1 1 0 )
(command "insert" "ped" '(208 -86) 1 1 0 )
(command "insert" "ped" '(209 -88) 1 1 0 )
(command "insert" "ped" '(211 -89) 1 1 0 )
(command "insert" "ped" '(209 -87) 1 1 0 )
(command "insert" "ped" '(208 -89) 1 1 0 )
(command "insert" "ped" '(205 -84) 1 1 0 )
(command "insert" "ped" '(206 -87) 1 1 0 )
(command "insert" "ped" '(210 -84) 1 1 0 )
(command "insert" "ped" '(211 -85) 1 1 0 )
(command "insert" "ped" '(204 -85) 1 1 0 )
(command "insert" "ped" '(207 -86) 1 1 0 )
(command "insert" "ped" '(201 -88) 1 1 0 )
(command "insert" "ped" '(212 -86) 1 1 0 )
(command "insert" "ped" '(205 -88) 1 1 0 )
(command "insert" "ped" '(207 -89) 1 1 0 )
(command "insert" "ped" '(210 -88) 1 1 0 )
(command "insert" "ped" '(204 -89) 1 1 0 )
(command "insert" "ped" '(206 -88) 1 1 0 )
(command "insert" "ped" '(208 -87) 1 1 0 )
(command "insert" "ped" '(211 -88) 1 1 0 )
(command "insert" "ped" '(202 -88) 1 1 0 )
(command "insert" "ped" '(209 -86) 1 1 0 )
(command "insert" "ped" '(202 -87) 1 1 0 )
(command "insert" "ped" '(206 -84) 1 1 0 )
(command "insert" "ped" '(210 -85) 1 1 0 )
(command "insert" "ped" '(211 -84) 1 1 0 )
(command "insert" "ped" '(204 -86) 1 1 0 )
(command "insert" "ped" '(212 -87) 1 1 0 )
(command "insert" "ped" '(205 -87) 1 1 0 )
(command "insert" "ped" '(207 -88) 1 1 0 )
(command "insert" "ped" '(204 -88) 1 1 0 )
(command "insert" "ped" '(210 -89) 1 1 0 )
(command "insert" "ped" '(212 -88) 1 1 0 )
(command "insert" "ped" '(206 -89) 1 1 0 )
(command "insert" "ped" '(207 -85) 1 1 0 )
(command "insert" "ped" '(202 -89) 1 1 0 )
(command "insert" "ped" '(201 -87) 1 1 0 )
(command "insert" "ped" '(209 -85) 1 1 0 )
(command "insert" "ped" '(206 -85) 1 1 0 )
(command "insert" "ped" '(208 -84) 1 1 0 )
(command "insert" "ped" '(211 -87) 1 1 0 )
(command "insert" "ped" '(204 -87) 1 1 0 )
(command "insert" "ped" '(203 -89) 1 1 0 )
(command "layer" "m" "Commmer" "" )
(command "insert" "Commmer" '(9 -26) 1 1 0 )
(command "insert" "Commmer" '(13 -22) 1 1 0 )
(command "insert" "Commmer" '(9 -22) 1 1 0 )
(command "insert" "Commmer" '(11 -23) 1 1 0 )
(command "insert" "Commmer" '(10 -21) 1 1 0 )
(command "insert" "Commmer" '(17 -25) 1 1 0 )
(command "insert" "Commmer" '(10 -26) 1 1 0 )
(command "insert" "Commmer" '(11 -24) 1 1 0 )
(command "insert" "Commmer" '(16 -24) 1 1 0 )
(command "insert" "Commmer" '(9 -25) 1 1 0 )
(command "insert" "Commmer" '(15 -26) 1 1 0 )
(command "insert" "Commmer" '(14 -22) 1 1 0 )
(command "insert" "Commmer" '(9 -21) 1 1 0 )
(command "insert" "Commmer" '(11 -22) 1 1 0 )
(command "insert" "Commmer" '(13 -21) 1 1 0 )
(command "insert" "Commmer" '(17 -24) 1 1 0 )
(command "insert" "Commmer" '(16 -25) 1 1 0 )
(command "insert" "Commmer" '(9 -24) 1 1 0 )
(command "insert" "Commmer" '(10 -22) 1 1 0 )
(command "insert" "Commmer" '(14 -23) 1 1 0 )
(command "insert" "Commmer" '(12 -21) 1 1 0 )
(command "insert" "Commmer" '(15 -25) 1 1 0 )
(command "insert" "Commmer" '(10 -24) 1 1 0 )
(command "insert" "Commmer" '(11 -26) 1 1 0 )
(command "insert" "Commmer" '(16 -26) 1 1 0 )
(command "insert" "Commmer" '(11 -21) 1 1 0 )
(command "insert" "Commmer" '(10 -23) 1 1 0 )
(command "insert" "Commmer" '(12 -22) 1 1 0 )
(command "insert" "Commmer" '(13 -23) 1 1 0 )
(command "insert" "Commmer" '(15 -24) 1 1 0 )
(command "insert" "Commmer" '(10 -25) 1 1 0 )
(command "insert" "Commmer" '(9 -23) 1 1 0 )
(command "insert" "Commmer" '(14 -21) 1 1 0 )
(command "insert" "Commmer" '(17 -26) 1 1 0 )
(command "insert" "Commmer" '(12 -23) 1 1 0 )
(command "insert" "Commmer" '(11 -25) 1 1 0 )
(command "layer" "m" "mroads" "" )
(command "insert" "mroads" '(5 -31) 1 1 0 )
(command "insert" "mroads" '(66 -31) 1 1 0 )
(command "insert" "mroads" '(6 -28) 1 1 0 )
(command "insert" "mroads" '(67 -30) 1 1 0 )
(command "insert" "mroads" '(7 -25) 1 1 0 )
(command "insert" "mroads" '(22 -19) 1 1 0 )
(command "insert" "mroads" '(18 -19) 1 1 0 )
(command "insert" "mroads" '(38 -21) 1 1 0 )
(command "insert" "mroads" '(114 -31) 1 1 0 )
(command "insert" "mroads" '(13 -32) 1 1 0 )
(command "insert" "mroads" '(35 -15) 1 1 0 )
(command "insert" "mroads" '(14 -31) 1 1 0 )
(command "insert" "mroads" '(15 -30) 1 1 0 )
(command "insert" "mroads" '(35 -21) 1 1 0 )
(command "insert" "mroads" '(12 -17) 1 1 0 )
(command "insert" "mroads" '(36 -22) 1 1 0 )
(command "insert" "mroads" '(1 -28) 1 1 0 )
(command "insert" "mroads" '(25 -15) 1 1 0 )
(command "insert" "mroads" '(39 -16) 1 1 0 )
(command "insert" "mroads" '(63 -30) 1 1 0 )
(command "insert" "mroads" '(37 -23) 1 1 0 )
(command "insert" "mroads" '(2 -27) 1 1 0 )
(command "insert" "mroads" '(109 -32) 1 1 0 )
(command "insert" "mroads" '(29 -17) 1 1 0 )
(command "insert" "mroads" '(31 -15) 1 1 0 )
(command "insert" "mroads" '(5 -24) 1 1 0 )
(command "insert" "mroads" '(20 -32) 1 1 0 )
(command "insert" "mroads" '(6 -23) 1 1 0 )
(command "insert" "mroads" '(30 -16) 1 1 0 )
(command "insert" "mroads" '(28 -32) 1 1 0 )
(command "insert" "mroads" '(7 -22) 1 1 0 )
(command "insert" "mroads" '(41 -23) 1 1 0 )
(command "insert" "mroads" '(42 -31) 1 1 0 )
(command "insert" "mroads" '(23 -19) 1 1 0 )
(command "insert" "mroads" '(21 -15) 1 1 0 )
(command "insert" "mroads" '(43 -30) 1 1 0 )
(command "insert" "mroads" '(116 -32) 1 1 0 )
(command "insert" "mroads" '(8 -18) 1 1 0 )
(command "insert" "mroads" '(11 -15) 1 1 0 )
(command "insert" "mroads" '(35 -26) 1 1 0 )
(command "insert" "mroads" '(9 -19) 1 1 0 )
(command "insert" "mroads" '(36 -29) 1 1 0 )
(command "insert" "mroads" '(1 -21) 1 1 0 )
(command "insert" "mroads" '(25 -16) 1 1 0 )
(command "insert" "mroads" '(29 -20) 1 1 0 )
(command "insert" "mroads" '(37 -16) 1 1 0 )
(command "insert" "mroads" '(98 -30) 1 1 0 )
(command "insert" "mroads" '(38 -31) 1 1 0 )
(command "insert" "mroads" '(99 -31) 1 1 0 )
(command "insert" "mroads" '(39 -30) 1 1 0 )
(command "insert" "mroads" '(3 -17) 1 1 0 )
(command "insert" "mroads" '(19 -18) 1 1 0 )
(command "insert" "mroads" '(7 -15) 1 1 0 )
(command "insert" "mroads" '(31 -18) 1 1 0 )
(command "insert" "mroads" '(46 -30) 1 1 0 )
(command "insert" "mroads" '(6 -32) 1 1 0 )
(command "insert" "mroads" '(34 -32) 1 1 0 )
(command "insert" "mroads" '(32 -16) 1 1 0 )
(command "insert" "mroads" '(94 -30) 1 1 0 )
(command "insert" "mroads" '(18 -31) 1 1 0 )
(command "insert" "mroads" '(42 -32) 1 1 0 )
(command "insert" "mroads" '(86 -32) 1 1 0 )
(command "insert" "mroads" '(34 -26) 1 1 0 )
(command "insert" "mroads" '(8 -25) 1 1 0 )
(command "insert" "mroads" '(94 -32) 1 1 0 )
(command "insert" "mroads" '(9 -20) 1 1 0 )
(command "insert" "mroads" '(10 -19) 1 1 0 )
(command "insert" "mroads" '(37 -25) 1 1 0 )
(command "insert" "mroads" '(26 -30) 1 1 0 )
(command "insert" "mroads" '(7 -18) 1 1 0 )
(command "insert" "mroads" '(38 -22) 1 1 0 )
(command "insert" "mroads" '(27 -31) 1 1 0 )
(command "insert" "mroads" '(40 -20) 1 1 0 )
(command "insert" "mroads" '(39 -23) 1 1 0 )
(command "insert" "mroads" '(88 -31) 1 1 0 )
(command "insert" "mroads" '(74 -30) 1 1 0 )
(command "insert" "mroads" '(89 -30) 1 1 0 )
(command "insert" "mroads" '(3 -22) 1 1 0 )
(command "insert" "mroads" '(75 -31) 1 1 0 )
(command "insert" "mroads" '(4 -17) 1 1 0 )
(command "insert" "mroads" '(5 -20) 1 1 0 )
(command "insert" "mroads" '(6 -27) 1 1 0 )
(command "insert" "mroads" '(21 -17) 1 1 0 )
(command "insert" "mroads" '(17 -17) 1 1 0 )
(command "insert" "mroads" '(22 -30) 1 1 0 )
(command "insert" "mroads" '(33 -22) 1 1 0 )
(command "insert" "mroads" '(23 -31) 1 1 0 )
(command "insert" "mroads" '(12 -32) 1 1 0 )
(command "insert" "mroads" '(34 -21) 1 1 0 )
(command "insert" "mroads" '(70 -30) 1 1 0 )
(command "insert" "mroads" '(85 -30) 1 1 0 )
(command "insert" "mroads" '(48 -32) 1 1 0 )
(command "insert" "mroads" '(71 -31) 1 1 0 )
(command "insert" "mroads" '(34 -15) 1 1 0 )
(command "insert" "mroads" '(11 -19) 1 1 0 )
(command "insert" "mroads" '(100 -32) 1 1 0 )
(command "insert" "mroads" '(27 -20) 1 1 0 )
(command "insert" "mroads" '(1 -25) 1 1 0 )
(command "insert" "mroads" '(108 -32) 1 1 0 )
(command "insert" "mroads" '(2 -30) 1 1 0 )
(command "insert" "mroads" '(3 -31) 1 1 0 )
(command "insert" "mroads" '(64 -31) 1 1 0 )
(command "insert" "mroads" '(4 -24) 1 1 0 )
(command "insert" "mroads" '(19 -32) 1 1 0 )
(command "insert" "mroads" '(62 -31) 1 1 0 )
(command "insert" "mroads" '(50 -30) 1 1 0 )
(command "insert" "mroads" '(65 -30) 1 1 0 )
(command "insert" "mroads" '(5 -29) 1 1 0 )
(command "insert" "mroads" '(27 -32) 1 1 0 )
(command "insert" "mroads" '(6 -18) 1 1 0 )
(command "insert" "mroads" '(101 -32) 1 1 0 )
(command "insert" "mroads" '(112 -31) 1 1 0 )
(command "insert" "mroads" '(41 -21) 1 1 0 )
(command "insert" "mroads" '(22 -17) 1 1 0 )
(command "insert" "mroads" '(79 -32) 1 1 0 )
(command "insert" "mroads" '(18 -17) 1 1 0 )
(command "insert" "mroads" '(23 -20) 1 1 0 )
(command "insert" "mroads" '(40 -31) 1 1 0 )
(command "insert" "mroads" '(115 -32) 1 1 0 )
(command "insert" "mroads" '(60 -31) 1 1 0 )
(command "insert" "mroads" '(61 -30) 1 1 0 )
(command "insert" "mroads" '(35 -23) 1 1 0 )
(command "insert" "mroads" '(24 -16) 1 1 0 )
(command "insert" "mroads" '(36 -16) 1 1 0 )
(command "insert" "mroads" '(108 -31) 1 1 0 )
(command "insert" "mroads" '(37 -21) 1 1 0 )
(command "insert" "mroads" '(2 -25) 1 1 0 )
(command "insert" "mroads" '(109 -30) 1 1 0 )
(command "insert" "mroads" '(7 -16) 1 1 0 )
(command "insert" "mroads" '(38 -26) 1 1 0 )
(command "insert" "mroads" '(40 -18) 1 1 0 )
(command "insert" "mroads" '(114 -32) 1 1 0 )
(command "insert" "mroads" '(116 -30) 1 1 0 )
(command "insert" "mroads" '(6 -21) 1 1 0 )
(command "insert" "mroads" '(111 -31) 1 1 0 )
(command "insert" "mroads" '(19 -15) 1 1 0 )
(command "insert" "mroads" '(41 -30) 1 1 0 )
(command "insert" "mroads" '(5 -32) 1 1 0 )
(command "insert" "mroads" '(33 -32) 1 1 0 )
(command "insert" "mroads" '(41 -32) 1 1 0 )
(command "insert" "mroads" '(7 -29) 1 1 0 )
(command "insert" "mroads" '(85 -32) 1 1 0 )
(command "insert" "mroads" '(9 -15) 1 1 0 )
(command "insert" "mroads" '(33 -26) 1 1 0 )
(command "insert" "mroads" '(22 -31) 1 1 0 )
(command "insert" "mroads" '(93 -32) 1 1 0 )
(command "insert" "mroads" '(8 -20) 1 1 0 )
(command "insert" "mroads" '(37 -15) 1 1 0 )
(command "insert" "mroads" '(35 -28) 1 1 0 )
(command "insert" "mroads" '(9 -17) 1 1 0 )
(command "insert" "mroads" '(96 -30) 1 1 0 )
(command "insert" "mroads" '(36 -31) 1 1 0 )
(command "insert" "mroads" '(15 -15) 1 1 0 )
(command "insert" "mroads" '(97 -31) 1 1 0 )
(command "insert" "mroads" '(37 -30) 1 1 0 )
(command "insert" "mroads" '(38 -29) 1 1 0 )
(command "insert" "mroads" '(83 -31) 1 1 0 )
(command "insert" "mroads" '(39 -24) 1 1 0 )
(command "insert" "mroads" '(5 -15) 1 1 0 )
(command "insert" "mroads" '(3 -19) 1 1 0 )
(command "insert" "mroads" '(4 -20) 1 1 0 )
(command "insert" "mroads" '(19 -20) 1 1 0 )
(command "insert" "mroads" '(92 -30) 1 1 0 )
(command "insert" "mroads" '(16 -31) 1 1 0 )
(command "insert" "mroads" '(93 -31) 1 1 0 )
(command "insert" "mroads" '(17 -30) 1 1 0 )
(command "insert" "mroads" '(32 -18) 1 1 0 )
(command "insert" "mroads" '(11 -32) 1 1 0 )
(command "insert" "mroads" '(33 -19) 1 1 0 )
(command "insert" "mroads" '(40 -29) 1 1 0 )
(command "insert" "mroads" '(8 -27) 1 1 0 )
(command "insert" "mroads" '(63 -32) 1 1 0 )
(command "insert" "mroads" '(5 -21) 1 1 0 )
(command "insert" "mroads" '(24 -30) 1 1 0 )
(command "insert" "mroads" '(14 -17) 1 1 0 )
(command "insert" "mroads" '(71 -32) 1 1 0 )
(command "insert" "mroads" '(10 -17) 1 1 0 )
(command "insert" "mroads" '(25 -31) 1 1 0 )
(command "insert" "mroads" '(99 -32) 1 1 0 )
(command "insert" "mroads" '(111 -32) 1 1 0 )
(command "insert" "mroads" '(107 -32) 1 1 0 )
(command "insert" "mroads" '(38 -20) 1 1 0 )
(command "insert" "mroads" '(12 -31) 1 1 0 )
(command "insert" "mroads" '(27 -17) 1 1 0 )
(command "insert" "mroads" '(39 -17) 1 1 0 )
(command "insert" "mroads" '(13 -30) 1 1 0 )
(command "insert" "mroads" '(41 -24) 1 1 0 )
(command "insert" "mroads" '(3 -24) 1 1 0 )
(command "insert" "mroads" '(56 -32) 1 1 0 )
(command "insert" "mroads" '(4 -19) 1 1 0 )
(command "insert" "mroads" '(26 -32) 1 1 0 )
(command "insert" "mroads" '(5 -18) 1 1 0 )
(command "insert" "mroads" '(20 -30) 1 1 0 )
(command "insert" "mroads" '(6 -25) 1 1 0 )
(command "insert" "mroads" '(21 -31) 1 1 0 )
(command "insert" "mroads" '(40 -22) 1 1 0 )
(command "insert" "mroads" '(78 -32) 1 1 0 )
(command "insert" "mroads" '(41 -18) 1 1 0 )
(command "insert" "mroads" '(18 -20) 1 1 0 )
(command "insert" "mroads" '(33 -20) 1 1 0 )
(command "insert" "mroads" '(69 -31) 1 1 0 )
(command "insert" "mroads" '(34 -19) 1 1 0 )
(command "insert" "mroads" '(32 -15) 1 1 0 )
(command "insert" "mroads" '(15 -32) 1 1 0 )
(command "insert" "mroads" '(64 -32) 1 1 0 )
(command "insert" "mroads" '(35 -16) 1 1 0 )
(command "insert" "mroads" '(38 -15) 1 1 0 )
(command "insert" "mroads" '(77 -32) 1 1 0 )
(command "insert" "mroads" '(1 -31) 1 1 0 )
(command "insert" "mroads" '(28 -17) 1 1 0 )
(command "insert" "mroads" '(2 -28) 1 1 0 )
(command "insert" "mroads" '(48 -30) 1 1 0 )
(command "insert" "mroads" '(113 -32) 1 1 0 )
(command "insert" "mroads" '(49 -31) 1 1 0 )
(command "insert" "mroads" '(4 -26) 1 1 0 )
(command "insert" "mroads" '(28 -15) 1 1 0 )
(command "insert" "mroads" '(5 -27) 1 1 0 )
(command "insert" "mroads" '(40 -26) 1 1 0 )
(command "insert" "mroads" '(4 -32) 1 1 0 )
(command "insert" "mroads" '(7 -21) 1 1 0 )
(command "insert" "mroads" '(18 -15) 1 1 0 )
(command "insert" "mroads" '(40 -32) 1 1 0 )
(command "insert" "mroads" '(34 -20) 1 1 0 )
(command "insert" "mroads" '(58 -31) 1 1 0 )
(command "insert" "mroads" '(44 -30) 1 1 0 )
(command "insert" "mroads" '(59 -30) 1 1 0 )
(command "insert" "mroads" '(92 -32) 1 1 0 )
(command "insert" "mroads" '(45 -31) 1 1 0 )
(command "insert" "mroads" '(6 -17) 1 1 0 )
(command "insert" "mroads" '(106 -31) 1 1 0 )
(command "insert" "mroads" '(35 -25) 1 1 0 )
(command "insert" "mroads" '(24 -18) 1 1 0 )
(command "insert" "mroads" '(107 -30) 1 1 0 )
(command "insert" "mroads" '(36 -18) 1 1 0 )
(command "insert" "mroads" '(25 -19) 1 1 0 )
(command "insert" "mroads" '(13 -16) 1 1 0 )
(command "insert" "mroads" '(37 -19) 1 1 0 )
(command "insert" "mroads" '(2 -23) 1 1 0 )
(command "insert" "mroads" '(38 -24) 1 1 0 )
(command "insert" "mroads" '(39 -29) 1 1 0 )
(command "insert" "mroads" '(54 -31) 1 1 0 )
(command "insert" "mroads" '(115 -31) 1 1 0 )
(command "insert" "mroads" '(55 -30) 1 1 0 )
(command "insert" "mroads" '(22 -20) 1 1 0 )
(command "insert" "mroads" '(30 -20) 1 1 0 )
(command "insert" "mroads" '(19 -17) 1 1 0 )
(command "insert" "mroads" '(102 -31) 1 1 0 )
(command "insert" "mroads" '(41 -28) 1 1 0 )
(command "insert" "mroads" '(31 -17) 1 1 0 )
(command "insert" "mroads" '(103 -30) 1 1 0 )
(command "insert" "mroads" '(10 -32) 1 1 0 )
(command "insert" "mroads" '(22 -32) 1 1 0 )
(command "insert" "mroads" '(18 -32) 1 1 0 )
(command "insert" "mroads" '(33 -24) 1 1 0 )
(command "insert" "mroads" '(62 -32) 1 1 0 )
(command "insert" "mroads" '(110 -30) 1 1 0 )
(command "insert" "mroads" '(34 -31) 1 1 0 )
(command "insert" "mroads" '(8 -22) 1 1 0 )
(command "insert" "mroads" '(23 -17) 1 1 0 )
(command "insert" "mroads" '(70 -32) 1 1 0 )
(command "insert" "mroads" '(35 -30) 1 1 0 )
(command "insert" "mroads" '(98 -32) 1 1 0 )
(command "insert" "mroads" '(36 -25) 1 1 0 )
(command "insert" "mroads" '(10 -20) 1 1 0 )
(command "insert" "mroads" '(25 -20) 1 1 0 )
(command "insert" "mroads" '(82 -31) 1 1 0 )
(command "insert" "mroads" '(106 -32) 1 1 0 )
(command "insert" "mroads" '(37 -28) 1 1 0 )
(command "insert" "mroads" '(26 -19) 1 1 0 )
(command "insert" "mroads" '(38 -19) 1 1 0 )
(command "insert" "mroads" '(3 -15) 1 1 0 )
(command "insert" "mroads" '(39 -26) 1 1 0 )
(command "insert" "mroads" '(51 -31) 1 1 0 )
(command "insert" "mroads" '(3 -21) 1 1 0 )
(command "insert" "mroads" '(25 -32) 1 1 0 )
(command "insert" "mroads" '(90 -30) 1 1 0 )
(command "insert" "mroads" '(30 -31) 1 1 0 )
(command "insert" "mroads" '(4 -22) 1 1 0 )
(command "insert" "mroads" '(91 -31) 1 1 0 )
(command "insert" "mroads" '(31 -30) 1 1 0 )
(command "insert" "mroads" '(5 -23) 1 1 0 )
(command "insert" "mroads" '(20 -17) 1 1 0 )
(command "insert" "mroads" '(16 -17) 1 1 0 )
(command "insert" "mroads" '(21 -20) 1 1 0 )
(command "insert" "mroads" '(32 -20) 1 1 0 )
(command "insert" "mroads" '(33 -17) 1 1 0 )
(command "insert" "mroads" '(34 -22) 1 1 0 )
(command "insert" "mroads" '(8 -29) 1 1 0 )
(command "insert" "mroads" '(61 -31) 1 1 0 )
(command "insert" "mroads" '(86 -30) 1 1 0 )
(command "insert" "mroads" '(10 -31) 1 1 0 )
(command "insert" "mroads" '(6 -19) 1 1 0 )
(command "insert" "mroads" '(87 -31) 1 1 0 )
(command "insert" "mroads" '(11 -30) 1 1 0 )
(command "insert" "mroads" '(76 -32) 1 1 0 )
(command "insert" "mroads" '(27 -19) 1 1 0 )
(command "insert" "mroads" '(39 -19) 1 1 0 )
(command "insert" "mroads" '(28 -20) 1 1 0 )
(command "insert" "mroads" '(3 -26) 1 1 0 )
(command "insert" "mroads" '(40 -15) 1 1 0 )
(command "insert" "mroads" '(4 -29) 1 1 0 )
(command "insert" "mroads" '(19 -31) 1 1 0 )
(command "insert" "mroads" '(7 -26) 1 1 0 )
(command "insert" "mroads" '(5 -16) 1 1 0 )
(command "insert" "mroads" '(3 -32) 1 1 0 )
(command "insert" "mroads" '(66 -30) 1 1 0 )
(command "insert" "mroads" '(6 -31) 1 1 0 )
(command "insert" "mroads" '(67 -31) 1 1 0 )
(command "insert" "mroads" '(7 -30) 1 1 0 )
(command "insert" "mroads" '(22 -18) 1 1 0 )
(command "insert" "mroads" '(55 -32) 1 1 0 )
(command "insert" "mroads" '(18 -18) 1 1 0 )
(command "insert" "mroads" '(83 -32) 1 1 0 )
(command "insert" "mroads" '(114 -30) 1 1 0 )
(command "insert" "mroads" '(34 -17) 1 1 0 )
(command "insert" "mroads" '(91 -32) 1 1 0 )
(command "insert" "mroads" '(14 -30) 1 1 0 )
(command "insert" "mroads" '(36 -15) 1 1 0 )
(command "insert" "mroads" '(15 -31) 1 1 0 )
(command "insert" "mroads" '(35 -18) 1 1 0 )
(command "insert" "mroads" '(12 -16) 1 1 0 )
(command "insert" "mroads" '(36 -21) 1 1 0 )
(command "insert" "mroads" '(1 -29) 1 1 0 )
(command "insert" "mroads" '(63 -31) 1 1 0 )
(command "insert" "mroads" '(28 -19) 1 1 0 )
(command "insert" "mroads" '(2 -26) 1 1 0 )
(command "insert" "mroads" '(26 -15) 1 1 0 )
(command "insert" "mroads" '(12 -15) 1 1 0 )
(command "insert" "mroads" '(29 -18) 1 1 0 )
(command "insert" "mroads" '(5 -25) 1 1 0 )
(command "insert" "mroads" '(16 -15) 1 1 0 )
(command "insert" "mroads" '(6 -22) 1 1 0 )
(command "insert" "mroads" '(30 -19) 1 1 0 )
(command "insert" "mroads" '(41 -25) 1 1 0 )
(command "insert" "mroads" '(56 -31) 1 1 0 )
(command "insert" "mroads" '(9 -32) 1 1 0 )
(command "insert" "mroads" '(42 -30) 1 1 0 )
(command "insert" "mroads" '(23 -16) 1 1 0 )
(command "insert" "mroads" '(43 -31) 1 1 0 )
(command "insert" "mroads" '(17 -32) 1 1 0 )
(command "insert" "mroads" '(22 -15) 1 1 0 )
(command "insert" "mroads" '(61 -32) 1 1 0 )
(command "insert" "mroads" '(52 -30) 1 1 0 )
(command "insert" "mroads" '(105 -30) 1 1 0 )
(command "insert" "mroads" '(69 -32) 1 1 0 )
(command "insert" "mroads" '(34 -24) 1 1 0 )
(command "insert" "mroads" '(8 -17) 1 1 0 )
(command "insert" "mroads" '(97 -32) 1 1 0 )
(command "insert" "mroads" '(35 -27) 1 1 0 )
(command "insert" "mroads" '(24 -20) 1 1 0 )
(command "insert" "mroads" '(105 -32) 1 1 0 )
(command "insert" "mroads" '(36 -28) 1 1 0 )
(command "insert" "mroads" '(1 -22) 1 1 0 )
(command "insert" "mroads" '(6 -29) 1 1 0 )
(command "insert" "mroads" '(37 -17) 1 1 0 )
(command "insert" "mroads" '(2 -21) 1 1 0 )
(command "insert" "mroads" '(38 -30) 1 1 0 )
(command "insert" "mroads" '(53 -30) 1 1 0 )
(command "insert" "mroads" '(112 -32) 1 1 0 )
(command "insert" "mroads" '(39 -31) 1 1 0 )
(command "insert" "mroads" '(100 -31) 1 1 0 )
(command "insert" "mroads" '(24 -32) 1 1 0 )
(command "insert" "mroads" '(101 -30) 1 1 0 )
(command "insert" "mroads" '(19 -19) 1 1 0 )
(command "insert" "mroads" '(31 -19) 1 1 0 )
(command "insert" "mroads" '(20 -20) 1 1 0 )
(command "insert" "mroads" '(47 -31) 1 1 0 )
(command "insert" "mroads" '(32 -31) 1 1 0 )
(command "insert" "mroads" '(18 -30) 1 1 0 )
(command "insert" "mroads" '(33 -30) 1 1 0 )
(command "insert" "mroads" '(34 -29) 1 1 0 )
(command "insert" "mroads" '(8 -24) 1 1 0 )
(command "insert" "mroads" '(39 -32) 1 1 0 )
(command "insert" "mroads" '(80 -31) 1 1 0 )
(command "insert" "mroads" '(81 -30) 1 1 0 )
(command "insert" "mroads" '(36 -27) 1 1 0 )
(command "insert" "mroads" '(10 -18) 1 1 0 )
(command "insert" "mroads" '(75 -32) 1 1 0 )
(command "insert" "mroads" '(37 -26) 1 1 0 )
(command "insert" "mroads" '(26 -17) 1 1 0 )
(command "insert" "mroads" '(38 -17) 1 1 0 )
(command "insert" "mroads" '(39 -20) 1 1 0 )
(command "insert" "mroads" '(88 -30) 1 1 0 )
(command "insert" "mroads" '(28 -31) 1 1 0 )
(command "insert" "mroads" '(89 -31) 1 1 0 )
(command "insert" "mroads" '(29 -30) 1 1 0 )
(command "insert" "mroads" '(3 -23) 1 1 0 )
(command "insert" "mroads" '(4 -16) 1 1 0 )
(command "insert" "mroads" '(2 -32) 1 1 0 )
(command "insert" "mroads" '(76 -31) 1 1 0 )
(command "insert" "mroads" '(46 -32) 1 1 0 )
(command "insert" "mroads" '(20 -19) 1 1 0 )
(command "insert" "mroads" '(33 -29) 1 1 0 )
(command "insert" "mroads" '(77 -30) 1 1 0 )
(command "insert" "mroads" '(6 -26) 1 1 0 )
(command "insert" "mroads" '(21 -18) 1 1 0 )
(command "insert" "mroads" '(54 -32) 1 1 0 )
(command "insert" "mroads" '(33 -23) 1 1 0 )
(command "insert" "mroads" '(90 -32) 1 1 0 )
(command "insert" "mroads" '(84 -30) 1 1 0 )
(command "insert" "mroads" '(8 -31) 1 1 0 )
(command "insert" "mroads" '(95 -31) 1 1 0 )
(command "insert" "mroads" '(85 -31) 1 1 0 )
(command "insert" "mroads" '(9 -30) 1 1 0 )
(command "insert" "mroads" '(15 -16) 1 1 0 )
(command "insert" "mroads" '(11 -16) 1 1 0 )
(command "insert" "mroads" '(1 -26) 1 1 0 )
(command "insert" "mroads" '(40 -21) 1 1 0 )
(command "insert" "mroads" '(73 -31) 1 1 0 )
(command "insert" "mroads" '(3 -28) 1 1 0 )
(command "insert" "mroads" '(64 -30) 1 1 0 )
(command "insert" "mroads" '(4 -31) 1 1 0 )
(command "insert" "mroads" '(65 -31) 1 1 0 )
(command "insert" "mroads" '(5 -30) 1 1 0 )
(command "insert" "mroads" '(40 -23) 1 1 0 )
(command "insert" "mroads" '(112 -30) 1 1 0 )
(command "insert" "mroads" '(8 -32) 1 1 0 )
(command "insert" "mroads" '(41 -22) 1 1 0 )
(command "insert" "mroads" '(22 -16) 1 1 0 )
(command "insert" "mroads" '(113 -31) 1 1 0 )
(command "insert" "mroads" '(18 -16) 1 1 0 )
(command "insert" "mroads" '(16 -32) 1 1 0 )
(command "insert" "mroads" '(60 -32) 1 1 0 )
(command "insert" "mroads" '(68 -32) 1 1 0 )
(command "insert" "mroads" '(96 -32) 1 1 0 )
(command "insert" "mroads" '(60 -30) 1 1 0 )
(command "insert" "mroads" '(104 -32) 1 1 0 )
(command "insert" "mroads" '(35 -20) 1 1 0 )
(command "insert" "mroads" '(24 -15) 1 1 0 )
(command "insert" "mroads" '(36 -23) 1 1 0 )
(command "insert" "mroads" '(108 -30) 1 1 0 )
(command "insert" "mroads" '(37 -22) 1 1 0 )
(command "insert" "mroads" '(2 -24) 1 1 0 )
(command "insert" "mroads" '(109 -31) 1 1 0 )
(command "insert" "mroads" '(29 -16) 1 1 0 )
(command "insert" "mroads" '(30 -15) 1 1 0 )
(command "insert" "mroads" '(25 -18) 1 1 0 )
(command "insert" "mroads" '(40 -30) 1 1 0 )
(command "insert" "mroads" '(30 -17) 1 1 0 )
(command "insert" "mroads" '(7 -17) 1 1 0 )
(command "insert" "mroads" '(31 -20) 1 1 0 )
(command "insert" "mroads" '(20 -15) 1 1 0 )
(command "insert" "mroads" '(33 -31) 1 1 0 )
(command "insert" "mroads" '(23 -18) 1 1 0 )
(command "insert" "mroads" '(47 -32) 1 1 0 )
(command "insert" "mroads" '(33 -27) 1 1 0 )
(command "insert" "mroads" '(38 -32) 1 1 0 )
(command "insert" "mroads" '(10 -15) 1 1 0 )
(command "insert" "mroads" '(8 -19) 1 1 0 )
(command "insert" "mroads" '(35 -29) 1 1 0 )
(command "insert" "mroads" '(9 -18) 1 1 0 )
(command "insert" "mroads" '(74 -32) 1 1 0 )
(command "insert" "mroads" '(52 -32) 1 1 0 )
(command "insert" "mroads" '(36 -30) 1 1 0 )
(command "insert" "mroads" '(51 -30) 1 1 0 )
(command "insert" "mroads" '(41 -27) 1 1 0 )
(command "insert" "mroads" '(82 -32) 1 1 0 )
(command "insert" "mroads" '(37 -31) 1 1 0 )
(command "insert" "mroads" '(26 -20) 1 1 0 )
(command "insert" "mroads" '(7 -19) 1 1 0 )
(command "insert" "mroads" '(98 -31) 1 1 0 )
(command "insert" "mroads" '(38 -28) 1 1 0 )
(command "insert" "mroads" '(40 -19) 1 1 0 )
(command "insert" "mroads" '(99 -30) 1 1 0 )
(command "insert" "mroads" '(39 -25) 1 1 0 )
(command "insert" "mroads" '(3 -16) 1 1 0 )
(command "insert" "mroads" '(1 -32) 1 1 0 )
(command "insert" "mroads" '(6 -15) 1 1 0 )
(command "insert" "mroads" '(46 -31) 1 1 0 )
(command "insert" "mroads" '(53 -32) 1 1 0 )
(command "insert" "mroads" '(16 -30) 1 1 0 )
(command "insert" "mroads" '(47 -30) 1 1 0 )
(command "insert" "mroads" '(17 -31) 1 1 0 )
(command "insert" "mroads" '(32 -17) 1 1 0 )
(command "insert" "mroads" '(7 -28) 1 1 0 )
(command "insert" "mroads" '(89 -32) 1 1 0 )
(command "insert" "mroads" '(7 -24) 1 1 0 )
(command "insert" "mroads" '(94 -31) 1 1 0 )
(command "insert" "mroads" '(33 -28) 1 1 0 )
(command "insert" "mroads" '(95 -30) 1 1 0 )
(command "insert" "mroads" '(34 -27) 1 1 0 )
(command "insert" "mroads" '(8 -26) 1 1 0 )
(command "insert" "mroads" '(14 -16) 1 1 0 )
(command "insert" "mroads" '(10 -16) 1 1 0 )
(command "insert" "mroads" '(37 -24) 1 1 0 )
(command "insert" "mroads" '(68 -30) 1 1 0 )
(command "insert" "mroads" '(26 -31) 1 1 0 )
(command "insert" "mroads" '(26 -18) 1 1 0 )
(command "insert" "mroads" '(38 -23) 1 1 0 )
(command "insert" "mroads" '(83 -30) 1 1 0 )
(command "insert" "mroads" '(27 -30) 1 1 0 )
(command "insert" "mroads" '(39 -22) 1 1 0 )
(command "insert" "mroads" '(13 -31) 1 1 0 )
(command "insert" "mroads" '(74 -31) 1 1 0 )
(command "insert" "mroads" '(3 -25) 1 1 0 )
(command "insert" "mroads" '(75 -30) 1 1 0 )
(command "insert" "mroads" '(4 -18) 1 1 0 )
(command "insert" "mroads" '(62 -30) 1 1 0 )
(command "insert" "mroads" '(5 -19) 1 1 0 )
(command "insert" "mroads" '(23 -32) 1 1 0 )
(command "insert" "mroads" '(6 -24) 1 1 0 )
(command "insert" "mroads" '(21 -16) 1 1 0 )
(command "insert" "mroads" '(17 -16) 1 1 0 )
(command "insert" "mroads" '(41 -19) 1 1 0 )
(command "insert" "mroads" '(31 -32) 1 1 0 )
(command "insert" "mroads" '(59 -32) 1 1 0 )
(command "insert" "mroads" '(33 -21) 1 1 0 )
(command "insert" "mroads" '(23 -30) 1 1 0 )
(command "insert" "mroads" '(34 -18) 1 1 0 )
(command "insert" "mroads" '(67 -32) 1 1 0 )
(command "insert" "mroads" '(6 -20) 1 1 0 )
(command "insert" "mroads" '(70 -31) 1 1 0 )
(command "insert" "mroads" '(33 -15) 1 1 0 )
(command "insert" "mroads" '(71 -30) 1 1 0 )
(command "insert" "mroads" '(11 -18) 1 1 0 )
(command "insert" "mroads" '(35 -17) 1 1 0 )
(command "insert" "mroads" '(1 -24) 1 1 0 )
(command "insert" "mroads" '(39 -15) 1 1 0 )
(command "insert" "mroads" '(28 -16) 1 1 0 )
(command "insert" "mroads" '(2 -31) 1 1 0 )
(command "insert" "mroads" '(12 -30) 1 1 0 )
(command "insert" "mroads" '(41 -31) 1 1 0 )
(command "insert" "mroads" '(79 -31) 1 1 0 )
(command "insert" "mroads" '(3 -30) 1 1 0 )
(command "insert" "mroads" '(40 -17) 1 1 0 )
(command "insert" "mroads" '(4 -25) 1 1 0 )
(command "insert" "mroads" '(50 -31) 1 1 0 )
(command "insert" "mroads" '(5 -28) 1 1 0 )
(command "insert" "mroads" '(29 -15) 1 1 0 )
(command "insert" "mroads" '(40 -25) 1 1 0 )
(command "insert" "mroads" '(41 -20) 1 1 0 )
(command "insert" "mroads" '(58 -30) 1 1 0 )
(command "insert" "mroads" '(37 -32) 1 1 0 )
(command "insert" "mroads" '(59 -31) 1 1 0 )
(command "insert" "mroads" '(41 -16) 1 1 0 )
(command "insert" "mroads" '(45 -32) 1 1 0 )
(command "insert" "mroads" '(73 -32) 1 1 0 )
(command "insert" "mroads" '(106 -30) 1 1 0 )
(command "insert" "mroads" '(35 -22) 1 1 0 )
(command "insert" "mroads" '(24 -17) 1 1 0 )
(command "insert" "mroads" '(107 -31) 1 1 0 )
(command "insert" "mroads" '(81 -32) 1 1 0 )
(command "insert" "mroads" '(36 -17) 1 1 0 )
(command "insert" "mroads" '(13 -17) 1 1 0 )
(command "insert" "mroads" '(37 -20) 1 1 0 )
(command "insert" "mroads" '(2 -22) 1 1 0 )
(command "insert" "mroads" '(72 -30) 1 1 0 )
(command "insert" "mroads" '(38 -27) 1 1 0 )
(command "insert" "mroads" '(54 -30) 1 1 0 )
(command "insert" "mroads" '(34 -23) 1 1 0 )
(command "insert" "mroads" '(55 -31) 1 1 0 )
(command "insert" "mroads" '(116 -31) 1 1 0 )
(command "insert" "mroads" '(102 -30) 1 1 0 )
(command "insert" "mroads" '(41 -29) 1 1 0 )
(command "insert" "mroads" '(103 -31) 1 1 0 )
(command "insert" "mroads" '(88 -32) 1 1 0 )
(command "insert" "mroads" '(84 -31) 1 1 0 )
(command "insert" "mroads" '(8 -15) 1 1 0 )
(command "insert" "mroads" '(33 -25) 1 1 0 )
(command "insert" "mroads" '(34 -30) 1 1 0 )
(command "insert" "mroads" '(8 -21) 1 1 0 )
(command "insert" "mroads" '(35 -31) 1 1 0 )
(command "insert" "mroads" '(9 -16) 1 1 0 )
(command "insert" "mroads" '(14 -15) 1 1 0 )
(command "insert" "mroads" '(40 -28) 1 1 0 )
(command "insert" "mroads" '(96 -31) 1 1 0 )
(command "insert" "mroads" '(36 -24) 1 1 0 )
(command "insert" "mroads" '(78 -31) 1 1 0 )
(command "insert" "mroads" '(82 -30) 1 1 0 )
(command "insert" "mroads" '(97 -30) 1 1 0 )
(command "insert" "mroads" '(37 -29) 1 1 0 )
(command "insert" "mroads" '(31 -31) 1 1 0 )
(command "insert" "mroads" '(38 -18) 1 1 0 )
(command "insert" "mroads" '(103 -32) 1 1 0 )
(command "insert" "mroads" '(39 -27) 1 1 0 )
(command "insert" "mroads" '(4 -15) 1 1 0 )
(command "insert" "mroads" '(7 -23) 1 1 0 )
(command "insert" "mroads" '(3 -18) 1 1 0 )
(command "insert" "mroads" '(30 -30) 1 1 0 )
(command "insert" "mroads" '(4 -21) 1 1 0 )
(command "insert" "mroads" '(79 -30) 1 1 0 )
(command "insert" "mroads" '(20 -16) 1 1 0 )
(command "insert" "mroads" '(92 -31) 1 1 0 )
(command "insert" "mroads" '(16 -16) 1 1 0 )
(command "insert" "mroads" '(30 -32) 1 1 0 )
(command "insert" "mroads" '(93 -30) 1 1 0 )
(command "insert" "mroads" '(58 -32) 1 1 0 )
(command "insert" "mroads" '(32 -19) 1 1 0 )
(command "insert" "mroads" '(33 -18) 1 1 0 )
(command "insert" "mroads" '(66 -32) 1 1 0 )
(command "insert" "mroads" '(110 -32) 1 1 0 )
(command "insert" "mroads" '(34 -25) 1 1 0 )
(command "insert" "mroads" '(8 -28) 1 1 0 )
(command "insert" "mroads" '(57 -30) 1 1 0 )
(command "insert" "mroads" '(24 -31) 1 1 0 )
(command "insert" "mroads" '(10 -30) 1 1 0 )
(command "insert" "mroads" '(25 -30) 1 1 0 )
(command "insert" "mroads" '(11 -31) 1 1 0 )
(command "insert" "mroads" '(72 -31) 1 1 0 )
(command "insert" "mroads" '(27 -16) 1 1 0 )
(command "insert" "mroads" '(49 -32) 1 1 0 )
(command "insert" "mroads" '(73 -30) 1 1 0 )
(command "insert" "mroads" '(3 -27) 1 1 0 )
(command "insert" "mroads" '(4 -28) 1 1 0 )
(command "insert" "mroads" '(41 -15) 1 1 0 )
(command "insert" "mroads" '(5 -17) 1 1 0 )
(command "insert" "mroads" '(20 -31) 1 1 0 )
(command "insert" "mroads" '(6 -30) 1 1 0 )
(command "insert" "mroads" '(21 -30) 1 1 0 )
(command "insert" "mroads" '(7 -31) 1 1 0 )
(command "insert" "mroads" '(68 -31) 1 1 0 )
(command "insert" "mroads" '(36 -32) 1 1 0 )
(command "insert" "mroads" '(69 -30) 1 1 0 )
(command "insert" "mroads" '(34 -16) 1 1 0 )
(command "insert" "mroads" '(44 -32) 1 1 0 )
(command "insert" "mroads" '(72 -32) 1 1 0 )
(command "insert" "mroads" '(6 -16) 1 1 0 )
(command "insert" "mroads" '(80 -32) 1 1 0 )
(command "insert" "mroads" '(11 -20) 1 1 0 )
(command "insert" "mroads" '(35 -19) 1 1 0 )
(command "insert" "mroads" '(36 -20) 1 1 0 )
(command "insert" "mroads" '(1 -30) 1 1 0 )
(command "insert" "mroads" '(28 -18) 1 1 0 )
(command "insert" "mroads" '(2 -29) 1 1 0 )
(command "insert" "mroads" '(48 -31) 1 1 0 )
(command "insert" "mroads" '(29 -19) 1 1 0 )
(command "insert" "mroads" '(27 -15) 1 1 0 )
(command "insert" "mroads" '(49 -30) 1 1 0 )
(command "insert" "mroads" '(4 -27) 1 1 0 )
(command "insert" "mroads" '(32 -32) 1 1 0 )
(command "insert" "mroads" '(5 -26) 1 1 0 )
(command "insert" "mroads" '(51 -32) 1 1 0 )
(command "insert" "mroads" '(40 -27) 1 1 0 )
(command "insert" "mroads" '(30 -18) 1 1 0 )
(command "insert" "mroads" '(17 -15) 1 1 0 )
(command "insert" "mroads" '(41 -26) 1 1 0 )
(command "insert" "mroads" '(56 -30) 1 1 0 )
(command "insert" "mroads" '(57 -31) 1 1 0 )
(command "insert" "mroads" '(86 -31) 1 1 0 )
(command "insert" "mroads" '(104 -30) 1 1 0 )
(command "insert" "mroads" '(44 -31) 1 1 0 )
(command "insert" "mroads" '(23 -15) 1 1 0 )
(command "insert" "mroads" '(105 -31) 1 1 0 )
(command "insert" "mroads" '(45 -30) 1 1 0 )
(command "insert" "mroads" '(8 -16) 1 1 0 )
(command "insert" "mroads" '(35 -24) 1 1 0 )
(command "insert" "mroads" '(50 -32) 1 1 0 )
(command "insert" "mroads" '(24 -19) 1 1 0 )
(command "insert" "mroads" '(36 -19) 1 1 0 )
(command "insert" "mroads" '(1 -23) 1 1 0 )
(command "insert" "mroads" '(104 -31) 1 1 0 )
(command "insert" "mroads" '(13 -15) 1 1 0 )
(command "insert" "mroads" '(37 -18) 1 1 0 )
(command "insert" "mroads" '(102 -32) 1 1 0 )
(command "insert" "mroads" '(38 -25) 1 1 0 )
(command "insert" "mroads" '(53 -31) 1 1 0 )
(command "insert" "mroads" '(78 -30) 1 1 0 )
(command "insert" "mroads" '(39 -28) 1 1 0 )
(command "insert" "mroads" '(84 -32) 1 1 0 )
(command "insert" "mroads" '(100 -30) 1 1 0 )
(command "insert" "mroads" '(115 -30) 1 1 0 )
(command "insert" "mroads" '(25 -17) 1 1 0 )
(command "insert" "mroads" '(101 -31) 1 1 0 )
(command "insert" "mroads" '(21 -32) 1 1 0 )
(command "insert" "mroads" '(19 -16) 1 1 0 )
(command "insert" "mroads" '(31 -16) 1 1 0 )
(command "insert" "mroads" '(29 -32) 1 1 0 )
(command "insert" "mroads" '(41 -17) 1 1 0 )
(command "insert" "mroads" '(32 -30) 1 1 0 )
(command "insert" "mroads" '(65 -32) 1 1 0 )
(command "insert" "mroads" '(52 -31) 1 1 0 )
(command "insert" "mroads" '(7 -20) 1 1 0 )
(command "insert" "mroads" '(110 -31) 1 1 0 )
(command "insert" "mroads" '(34 -28) 1 1 0 )
(command "insert" "mroads" '(8 -23) 1 1 0 )
(command "insert" "mroads" '(80 -30) 1 1 0 )
(command "insert" "mroads" '(111 -30) 1 1 0 )
(command "insert" "mroads" '(57 -32) 1 1 0 )
(command "insert" "mroads" '(81 -31) 1 1 0 )
(command "insert" "mroads" '(36 -26) 1 1 0 )
(command "insert" "mroads" '(40 -24) 1 1 0 )
(command "insert" "mroads" '(37 -27) 1 1 0 )
(command "insert" "mroads" '(26 -16) 1 1 0 )
(command "insert" "mroads" '(38 -16) 1 1 0 )
(command "insert" "mroads" '(39 -21) 1 1 0 )
(command "insert" "mroads" '(28 -30) 1 1 0 )
(command "insert" "mroads" '(29 -31) 1 1 0 )
(command "insert" "mroads" '(3 -20) 1 1 0 )
(command "insert" "mroads" '(90 -31) 1 1 0 )
(command "insert" "mroads" '(4 -23) 1 1 0 )
(command "insert" "mroads" '(76 -30) 1 1 0 )
(command "insert" "mroads" '(91 -30) 1 1 0 )
(command "insert" "mroads" '(7 -27) 1 1 0 )
(command "insert" "mroads" '(5 -22) 1 1 0 )
(command "insert" "mroads" '(20 -18) 1 1 0 )
(command "insert" "mroads" '(77 -31) 1 1 0 )
(command "insert" "mroads" '(21 -19) 1 1 0 )
(command "insert" "mroads" '(7 -32) 1 1 0 )
(command "insert" "mroads" '(35 -32) 1 1 0 )
(command "insert" "mroads" '(113 -30) 1 1 0 )
(command "insert" "mroads" '(33 -16) 1 1 0 )
(command "insert" "mroads" '(43 -32) 1 1 0 )
(command "insert" "mroads" '(8 -30) 1 1 0 )
(command "insert" "mroads" '(40 -16) 1 1 0 )
(command "insert" "mroads" '(87 -32) 1 1 0 )
(command "insert" "mroads" '(9 -31) 1 1 0 )
(command "insert" "mroads" '(95 -32) 1 1 0 )
(command "insert" "mroads" '(15 -17) 1 1 0 )
(command "insert" "mroads" '(87 -30) 1 1 0 )
(command "insert" "mroads" '(11 -17) 1 1 0 )
(command "insert" "mroads" '(27 -18) 1 1 0 )
(command "insert" "mroads" '(1 -27) 1 1 0 )
(command "insert" "mroads" '(39 -18) 1 1 0 )
(command "insert" "mroads" '(14 -32) 1 1 0 )
(command "insert" "mroads" '(3 -29) 1 1 0 )
(command "insert" "mroads" '(4 -30) 1 1 0 )
(command "insert" "mroads" '(19 -30) 1 1 0 )
(command "layer" "m" "Res" "" )
(command "insert" "Res" '(76 -34) 1 1 0 )
(command "insert" "Res" '(77 -34) 1 1 0 )
(command "insert" "Res" '(77 -33) 1 1 0 )
(command "insert" "Res" '(75 -34) 1 1 0 )
(command "insert" "Res" '(77 -35) 1 1 0 )
(command "insert" "Res" '(75 -35) 1 1 0 )
(command "insert" "Res" '(75 -33) 1 1 0 )
(command "insert" "Res" '(76 -33) 1 1 0 )
(command "insert" "Res" '(76 -35) 1 1 0 )
(command "layer" "m" "ped" "" )
(command "insert" "ped" '(164 -29) 1 1 0 )
(command "insert" "ped" '(169 -27) 1 1 0 )
(command "insert" "ped" '(162 -28) 1 1 0 )
(command "insert" "ped" '(165 -27) 1 1 0 )
(command "insert" "ped" '(173 -27) 1 1 0 )
(command "insert" "ped" '(175 -28) 1 1 0 )
(command "insert" "ped" '(164 -26) 1 1 0 )
(command "insert" "ped" '(176 -27) 1 1 0 )
(command "insert" "ped" '(162 -25) 1 1 0 )
(command "insert" "ped" '(163 -29) 1 1 0 )
(command "insert" "ped" '(166 -27) 1 1 0 )
(command "insert" "ped" '(168 -27) 1 1 0 )
(command "insert" "ped" '(170 -29) 1 1 0 )
(command "insert" "ped" '(175 -27) 1 1 0 )
(command "insert" "ped" '(162 -29) 1 1 0 )
(command "insert" "ped" '(163 -25) 1 1 0 )
(command "insert" "ped" '(172 -27) 1 1 0 )
(command "insert" "ped" '(166 -28) 1 1 0 )
(command "insert" "ped" '(171 -28) 1 1 0 )
(command "insert" "ped" '(164 -27) 1 1 0 )
(command "insert" "ped" '(176 -28) 1 1 0 )
(command "insert" "ped" '(169 -29) 1 1 0 )
(command "insert" "ped" '(163 -28) 1 1 0 )
(command "insert" "ped" '(168 -28) 1 1 0 )
(command "insert" "ped" '(167 -29) 1 1 0 )
(command "insert" "ped" '(162 -26) 1 1 0 )
(command "insert" "ped" '(163 -24) 1 1 0 )
(command "insert" "ped" '(166 -29) 1 1 0 )
(command "insert" "ped" '(165 -28) 1 1 0 )
(command "insert" "ped" '(176 -29) 1 1 0 )
(command "insert" "ped" '(169 -28) 1 1 0 )
(command "insert" "ped" '(174 -27) 1 1 0 )
(command "insert" "ped" '(172 -29) 1 1 0 )
(command "insert" "ped" '(170 -27) 1 1 0 )
(command "insert" "ped" '(171 -27) 1 1 0 )
(command "insert" "ped" '(164 -24) 1 1 0 )
(command "insert" "ped" '(167 -28) 1 1 0 )
(command "insert" "ped" '(172 -28) 1 1 0 )
(command "insert" "ped" '(162 -27) 1 1 0 )
(command "insert" "ped" '(165 -29) 1 1 0 )
(command "insert" "ped" '(162 -24) 1 1 0 )
(command "insert" "ped" '(174 -28) 1 1 0 )
(command "insert" "ped" '(164 -28) 1 1 0 )
(command "insert" "ped" '(163 -27) 1 1 0 )
(command "insert" "ped" '(167 -27) 1 1 0 )
(command "insert" "ped" '(173 -28) 1 1 0 )
(command "insert" "ped" '(175 -29) 1 1 0 )
(command "insert" "ped" '(164 -25) 1 1 0 )
(command "insert" "ped" '(171 -29) 1 1 0 )
(command "insert" "ped" '(168 -29) 1 1 0 )
(command "insert" "ped" '(163 -26) 1 1 0 )
(command "insert" "ped" '(170 -28) 1 1 0 )
(command "insert" "ped" '(174 -29) 1 1 0 )
(command "insert" "ped" '(173 -29) 1 1 0 )
(command "layer" "m" "Res" "" )
(command "insert" "Res" '(211 -50) 1 1 0 )
(command "insert" "Res" '(211 -49) 1 1 0 )
(command "insert" "Res" '(218 -59) 1 1 0 )
(command "insert" "Res" '(213 -59) 1 1 0 )
(command "insert" "Res" '(212 -53) 1 1 0 )
(command "insert" "Res" '(210 -46) 1 1 0 )
(command "insert" "Res" '(214 -48) 1 1 0 )
(command "insert" "Res" '(216 -57) 1 1 0 )
(command "insert" "Res" '(215 -53) 1 1 0 )
(command "insert" "Res" '(215 -59) 1 1 0 )
(command "insert" "Res" '(212 -50) 1 1 0 )
(command "insert" "Res" '(214 -53) 1 1 0 )
(command "insert" "Res" '(213 -51) 1 1 0 )
(command "insert" "Res" '(212 -45) 1 1 0 )
(command "insert" "Res" '(211 -56) 1 1 0 )
(command "insert" "Res" '(210 -54) 1 1 0 )
(command "insert" "Res" '(215 -48) 1 1 0 )
(command "insert" "Res" '(215 -61) 1 1 0 )
(command "insert" "Res" '(214 -47) 1 1 0 )
(command "insert" "Res" '(213 -62) 1 1 0 )
(command "insert" "Res" '(215 -46) 1 1 0 )
(command "insert" "Res" '(210 -51) 1 1 0 )
(command "insert" "Res" '(214 -61) 1 1 0 )
(command "insert" "Res" '(208 -46) 1 1 0 )
(command "insert" "Res" '(211 -52) 1 1 0 )
(command "insert" "Res" '(218 -57) 1 1 0 )
(command "insert" "Res" '(209 -47) 1 1 0 )
(command "insert" "Res" '(213 -57) 1 1 0 )
(command "insert" "Res" '(212 -55) 1 1 0 )
(command "insert" "Res" '(216 -59) 1 1 0 )
(command "insert" "Res" '(217 -58) 1 1 0 )
(command "insert" "Res" '(213 -49) 1 1 0 )
(command "insert" "Res" '(212 -47) 1 1 0 )
(command "insert" "Res" '(215 -45) 1 1 0 )
(command "insert" "Res" '(210 -52) 1 1 0 )
(command "insert" "Res" '(215 -50) 1 1 0 )
(command "insert" "Res" '(214 -62) 1 1 0 )
(command "insert" "Res" '(213 -46) 1 1 0 )
(command "insert" "Res" '(211 -51) 1 1 0 )
(command "insert" "Res" '(214 -45) 1 1 0 )
(command "insert" "Res" '(218 -58) 1 1 0 )
(command "insert" "Res" '(213 -60) 1 1 0 )
(command "insert" "Res" '(212 -52) 1 1 0 )
(command "insert" "Res" '(210 -49) 1 1 0 )
(command "insert" "Res" '(214 -51) 1 1 0 )
(command "insert" "Res" '(211 -54) 1 1 0 )
(command "insert" "Res" '(209 -45) 1 1 0 )
(command "insert" "Res" '(207 -46) 1 1 0 )
(command "insert" "Res" '(212 -49) 1 1 0 )
(command "insert" "Res" '(214 -52) 1 1 0 )
(command "insert" "Res" '(213 -52) 1 1 0 )
(command "insert" "Res" '(215 -49) 1 1 0 )
(command "insert" "Res" '(214 -59) 1 1 0 )
(command "insert" "Res" '(211 -46) 1 1 0 )
(command "insert" "Res" '(214 -46) 1 1 0 )
(command "insert" "Res" '(215 -47) 1 1 0 )
(command "insert" "Res" '(210 -50) 1 1 0 )
(command "insert" "Res" '(214 -60) 1 1 0 )
(command "insert" "Res" '(208 -45) 1 1 0 )
(command "insert" "Res" '(211 -53) 1 1 0 )
(command "insert" "Res" '(207 -45) 1 1 0 )
(command "insert" "Res" '(213 -58) 1 1 0 )
(command "insert" "Res" '(212 -54) 1 1 0 )
(command "insert" "Res" '(210 -47) 1 1 0 )
(command "insert" "Res" '(214 -49) 1 1 0 )
(command "insert" "Res" '(210 -53) 1 1 0 )
(command "insert" "Res" '(216 -58) 1 1 0 )
(command "insert" "Res" '(215 -52) 1 1 0 )
(command "insert" "Res" '(211 -48) 1 1 0 )
(command "insert" "Res" '(217 -59) 1 1 0 )
(command "insert" "Res" '(212 -51) 1 1 0 )
(command "insert" "Res" '(211 -45) 1 1 0 )
(command "insert" "Res" '(215 -57) 1 1 0 )
(command "insert" "Res" '(213 -50) 1 1 0 )
(command "insert" "Res" '(212 -46) 1 1 0 )
(command "insert" "Res" '(210 -55) 1 1 0 )
(command "insert" "Res" '(215 -51) 1 1 0 )
(command "insert" "Res" '(214 -57) 1 1 0 )
(command "insert" "Res" '(213 -47) 1 1 0 )
(command "insert" "Res" '(215 -58) 1 1 0 )
(command "insert" "Res" '(212 -56) 1 1 0 )
(command "insert" "Res" '(215 -60) 1 1 0 )
(command "insert" "Res" '(213 -61) 1 1 0 )
(command "insert" "Res" '(210 -48) 1 1 0 )
(command "insert" "Res" '(214 -50) 1 1 0 )
(command "insert" "Res" '(208 -47) 1 1 0 )
(command "insert" "Res" '(211 -55) 1 1 0 )
(command "insert" "Res" '(209 -46) 1 1 0 )
(command "insert" "Res" '(207 -47) 1 1 0 )
(command "insert" "Res" '(212 -48) 1 1 0 )
(command "insert" "Res" '(210 -45) 1 1 0 )
(command "insert" "Res" '(213 -53) 1 1 0 )
(command "insert" "Res" '(210 -56) 1 1 0 )
(command "insert" "Res" '(214 -58) 1 1 0 )
(command "insert" "Res" '(217 -57) 1 1 0 )
(command "insert" "Res" '(211 -47) 1 1 0 )
(command "insert" "Res" '(213 -48) 1 1 0 )
(command "insert" "Res" '(215 -62) 1 1 0 )
(command "insert" "Res" '(213 -45) 1 1 0 )
(command "layer" "m" "edge" "" )
(command "insert" "edge" '(54 -2) 1 1 0 )
(command "insert" "edge" '(55 -2) 1 1 0 )
(command "insert" "edge" '(56 -2) 1 1 0 )
(command "insert" "edge" '(55 -1) 1 1 0 )
(command "insert" "edge" '(56 -1) 1 1 0 )
(command "insert" "edge" '(54 -1) 1 1 0 )
(command "layer" "m" "Res" "" )
(command "insert" "Res" '(161 -56) 1 1 0 )
(command "insert" "Res" '(161 -45) 1 1 0 )
(command "insert" "Res" '(158 -55) 1 1 0 )
(command "insert" "Res" '(159 -54) 1 1 0 )
(command "insert" "Res" '(154 -49) 1 1 0 )
(command "insert" "Res" '(153 -47) 1 1 0 )
(command "insert" "Res" '(154 -44) 1 1 0 )
(command "insert" "Res" '(160 -55) 1 1 0 )
(command "insert" "Res" '(161 -54) 1 1 0 )
(command "insert" "Res" '(167 -58) 1 1 0 )
(command "insert" "Res" '(158 -46) 1 1 0 )
(command "insert" "Res" '(156 -42) 1 1 0 )
(command "insert" "Res" '(160 -45) 1 1 0 )
(command "insert" "Res" '(159 -47) 1 1 0 )
(command "insert" "Res" '(157 -43) 1 1 0 )
(command "insert" "Res" '(159 -56) 1 1 0 )
(command "insert" "Res" '(153 -53) 1 1 0 )
(command "insert" "Res" '(152 -43) 1 1 0 )
(command "insert" "Res" '(159 -53) 1 1 0 )
(command "insert" "Res" '(155 -54) 1 1 0 )
(command "insert" "Res" '(154 -50) 1 1 0 )
(command "insert" "Res" '(153 -42) 1 1 0 )
(command "insert" "Res" '(160 -52) 1 1 0 )
(command "insert" "Res" '(155 -44) 1 1 0 )
(command "insert" "Res" '(161 -49) 1 1 0 )
(command "insert" "Res" '(167 -57) 1 1 0 )
(command "insert" "Res" '(158 -43) 1 1 0 )
(command "insert" "Res" '(156 -47) 1 1 0 )
(command "insert" "Res" '(162 -54) 1 1 0 )
(command "insert" "Res" '(157 -46) 1 1 0 )
(command "insert" "Res" '(163 -56) 1 1 0 )
(command "insert" "Res" '(154 -56) 1 1 0 )
(command "insert" "Res" '(153 -48) 1 1 0 )
(command "insert" "Res" '(151 -42) 1 1 0 )
(command "insert" "Res" '(155 -53) 1 1 0 )
(command "insert" "Res" '(154 -55) 1 1 0 )
(command "insert" "Res" '(156 -54) 1 1 0 )
(command "insert" "Res" '(160 -49) 1 1 0 )
(command "insert" "Res" '(166 -57) 1 1 0 )
(command "insert" "Res" '(157 -55) 1 1 0 )
(command "insert" "Res" '(155 -43) 1 1 0 )
(command "insert" "Res" '(150 -43) 1 1 0 )
(command "insert" "Res" '(156 -44) 1 1 0 )
(command "insert" "Res" '(159 -50) 1 1 0 )
(command "insert" "Res" '(163 -55) 1 1 0 )
(command "insert" "Res" '(153 -51) 1 1 0 )
(command "insert" "Res" '(165 -56) 1 1 0 )
(command "insert" "Res" '(155 -48) 1 1 0 )
(command "insert" "Res" '(166 -55) 1 1 0 )
(command "insert" "Res" '(167 -54) 1 1 0 )
(command "insert" "Res" '(166 -58) 1 1 0 )
(command "insert" "Res" '(159 -49) 1 1 0 )
(command "insert" "Res" '(153 -46) 1 1 0 )
(command "insert" "Res" '(165 -59) 1 1 0 )
(command "insert" "Res" '(154 -45) 1 1 0 )
(command "insert" "Res" '(156 -56) 1 1 0 )
(command "insert" "Res" '(161 -53) 1 1 0 )
(command "insert" "Res" '(158 -47) 1 1 0 )
(command "insert" "Res" '(156 -43) 1 1 0 )
(command "insert" "Res" '(160 -46) 1 1 0 )
(command "insert" "Res" '(159 -46) 1 1 0 )
(command "insert" "Res" '(157 -42) 1 1 0 )
(command "insert" "Res" '(161 -47) 1 1 0 )
(command "insert" "Res" '(153 -52) 1 1 0 )
(command "insert" "Res" '(152 -44) 1 1 0 )
(command "insert" "Res" '(159 -52) 1 1 0 )
(command "insert" "Res" '(154 -51) 1 1 0 )
(command "insert" "Res" '(154 -46) 1 1 0 )
(command "insert" "Res" '(160 -53) 1 1 0 )
(command "insert" "Res" '(155 -47) 1 1 0 )
(command "insert" "Res" '(161 -48) 1 1 0 )
(command "insert" "Res" '(160 -56) 1 1 0 )
(command "insert" "Res" '(167 -56) 1 1 0 )
(command "insert" "Res" '(162 -55) 1 1 0 )
(command "insert" "Res" '(159 -45) 1 1 0 )
(command "insert" "Res" '(157 -45) 1 1 0 )
(command "insert" "Res" '(153 -55) 1 1 0 )
(command "insert" "Res" '(155 -52) 1 1 0 )
(command "insert" "Res" '(154 -52) 1 1 0 )
(command "insert" "Res" '(156 -55) 1 1 0 )
(command "insert" "Res" '(160 -50) 1 1 0 )
(command "insert" "Res" '(157 -54) 1 1 0 )
(command "insert" "Res" '(155 -42) 1 1 0 )
(command "insert" "Res" '(161 -51) 1 1 0 )
(command "insert" "Res" '(156 -45) 1 1 0 )
(command "insert" "Res" '(162 -56) 1 1 0 )
(command "insert" "Res" '(158 -56) 1 1 0 )
(command "insert" "Res" '(163 -54) 1 1 0 )
(command "insert" "Res" '(153 -50) 1 1 0 )
(command "insert" "Res" '(155 -51) 1 1 0 )
(command "insert" "Res" '(150 -44) 1 1 0 )
(command "insert" "Res" '(166 -59) 1 1 0 )
(command "insert" "Res" '(153 -56) 1 1 0 )
(command "insert" "Res" '(159 -48) 1 1 0 )
(command "insert" "Res" '(153 -45) 1 1 0 )
(command "insert" "Res" '(165 -58) 1 1 0 )
(command "insert" "Res" '(164 -54) 1 1 0 )
(command "insert" "Res" '(154 -42) 1 1 0 )
(command "insert" "Res" '(165 -55) 1 1 0 )
(command "insert" "Res" '(161 -52) 1 1 0 )
(command "insert" "Res" '(158 -44) 1 1 0 )
(command "insert" "Res" '(160 -47) 1 1 0 )
(command "insert" "Res" '(161 -46) 1 1 0 )
(command "insert" "Res" '(158 -54) 1 1 0 )
(command "insert" "Res" '(159 -55) 1 1 0 )
(command "insert" "Res" '(164 -56) 1 1 0 )
(command "insert" "Res" '(154 -48) 1 1 0 )
(command "insert" "Res" '(154 -47) 1 1 0 )
(command "insert" "Res" '(160 -54) 1 1 0 )
(command "insert" "Res" '(155 -46) 1 1 0 )
(command "insert" "Res" '(161 -55) 1 1 0 )
(command "insert" "Res" '(167 -59) 1 1 0 )
(command "insert" "Res" '(151 -43) 1 1 0 )
(command "insert" "Res" '(157 -44) 1 1 0 )
(command "insert" "Res" '(153 -54) 1 1 0 )
(command "insert" "Res" '(152 -42) 1 1 0 )
(command "insert" "Res" '(155 -55) 1 1 0 )
(command "insert" "Res" '(154 -53) 1 1 0 )
(command "insert" "Res" '(153 -43) 1 1 0 )
(command "insert" "Res" '(155 -56) 1 1 0 )
(command "insert" "Res" '(160 -51) 1 1 0 )
(command "insert" "Res" '(155 -45) 1 1 0 )
(command "insert" "Res" '(161 -50) 1 1 0 )
(command "insert" "Res" '(158 -42) 1 1 0 )
(command "insert" "Res" '(156 -46) 1 1 0 )
(command "insert" "Res" '(151 -44) 1 1 0 )
(command "insert" "Res" '(157 -47) 1 1 0 )
(command "insert" "Res" '(153 -49) 1 1 0 )
(command "insert" "Res" '(155 -50) 1 1 0 )
(command "insert" "Res" '(154 -54) 1 1 0 )
(command "insert" "Res" '(160 -48) 1 1 0 )
(command "insert" "Res" '(166 -56) 1 1 0 )
(command "insert" "Res" '(157 -56) 1 1 0 )
(command "insert" "Res" '(150 -42) 1 1 0 )
(command "insert" "Res" '(159 -51) 1 1 0 )
(command "insert" "Res" '(153 -44) 1 1 0 )
(command "insert" "Res" '(165 -57) 1 1 0 )
(command "insert" "Res" '(164 -55) 1 1 0 )
(command "insert" "Res" '(155 -49) 1 1 0 )
(command "insert" "Res" '(154 -43) 1 1 0 )
(command "insert" "Res" '(166 -54) 1 1 0 )
(command "insert" "Res" '(165 -54) 1 1 0 )
(command "insert" "Res" '(167 -55) 1 1 0 )
(command "insert" "Res" '(158 -45) 1 1 0 )
(command "layer" "m" "edge" "" )
(command "insert" "edge" '(44 -2) 1 1 0 )
(command "insert" "edge" '(47 -2) 1 1 0 )
(command "insert" "edge" '(45 -1) 1 1 0 )
(command "insert" "edge" '(40 -1) 1 1 0 )
(command "insert" "edge" '(38 -1) 1 1 0 )
(command "insert" "edge" '(46 -1) 1 1 0 )
(command "insert" "edge" '(43 -1) 1 1 0 )
(command "insert" "edge" '(40 -2) 1 1 0 )
(command "insert" "edge" '(45 -2) 1 1 0 )
(command "insert" "edge" '(36 -1) 1 1 0 )
(command "insert" "edge" '(42 -2) 1 1 0 )
(command "insert" "edge" '(37 -1) 1 1 0 )
(command "insert" "edge" '(44 -1) 1 1 0 )
(command "insert" "edge" '(41 -1) 1 1 0 )
(command "insert" "edge" '(39 -1) 1 1 0 )
(command "insert" "edge" '(37 -2) 1 1 0 )
(command "insert" "edge" '(43 -2) 1 1 0 )
(command "insert" "edge" '(47 -1) 1 1 0 )
(command "insert" "edge" '(41 -2) 1 1 0 )
(command "insert" "edge" '(38 -2) 1 1 0 )
(command "insert" "edge" '(42 -1) 1 1 0 )
(command "insert" "edge" '(36 -2) 1 1 0 )
(command "insert" "edge" '(46 -2) 1 1 0 )
(command "insert" "edge" '(39 -2) 1 1 0 )
(command "layer" "m" "Commmer" "" )
(command "insert" "Commmer" '(68 -38) 1 1 0 )
(command "insert" "Commmer" '(72 -33) 1 1 0 )
(command "insert" "Commmer" '(70 -33) 1 1 0 )
(command "insert" "Commmer" '(67 -33) 1 1 0 )
(command "insert" "Commmer" '(68 -35) 1 1 0 )
(command "insert" "Commmer" '(69 -34) 1 1 0 )
(command "insert" "Commmer" '(66 -36) 1 1 0 )
(command "insert" "Commmer" '(71 -35) 1 1 0 )
(command "insert" "Commmer" '(72 -34) 1 1 0 )
(command "insert" "Commmer" '(67 -36) 1 1 0 )
(command "insert" "Commmer" '(73 -35) 1 1 0 )
(command "insert" "Commmer" '(66 -33) 1 1 0 )
(command "insert" "Commmer" '(70 -34) 1 1 0 )
(command "insert" "Commmer" '(74 -33) 1 1 0 )
(command "insert" "Commmer" '(69 -33) 1 1 0 )
(command "insert" "Commmer" '(66 -37) 1 1 0 )
(command "insert" "Commmer" '(71 -34) 1 1 0 )
(command "insert" "Commmer" '(72 -35) 1 1 0 )
(command "insert" "Commmer" '(67 -35) 1 1 0 )
(command "insert" "Commmer" '(73 -34) 1 1 0 )
(command "insert" "Commmer" '(68 -36) 1 1 0 )
(command "insert" "Commmer" '(70 -35) 1 1 0 )
(command "insert" "Commmer" '(67 -38) 1 1 0 )
(command "insert" "Commmer" '(66 -34) 1 1 0 )
(command "insert" "Commmer" '(68 -33) 1 1 0 )
(command "insert" "Commmer" '(74 -34) 1 1 0 )
(command "insert" "Commmer" '(67 -34) 1 1 0 )
(command "insert" "Commmer" '(66 -38) 1 1 0 )
(command "insert" "Commmer" '(73 -33) 1 1 0 )
(command "insert" "Commmer" '(71 -33) 1 1 0 )
(command "insert" "Commmer" '(68 -37) 1 1 0 )
(command "insert" "Commmer" '(66 -35) 1 1 0 )
(command "insert" "Commmer" '(68 -34) 1 1 0 )
(command "insert" "Commmer" '(67 -37) 1 1 0 )
(command "insert" "Commmer" '(74 -35) 1 1 0 )
(command "insert" "Commmer" '(69 -35) 1 1 0 )
(command "layer" "m" "Res" "" )
(command "insert" "Res" '(258 -93) 1 1 0 )
(command "insert" "Res" '(258 -95) 1 1 0 )
(command "insert" "Res" '(259 -97) 1 1 0 )
(command "insert" "Res" '(259 -94) 1 1 0 )
(command "insert" "Res" '(258 -96) 1 1 0 )
(command "insert" "Res" '(258 -98) 1 1 0 )
(command "insert" "Res" '(260 -95) 1 1 0 )
(command "insert" "Res" '(260 -97) 1 1 0 )
(command "insert" "Res" '(260 -93) 1 1 0 )
(command "insert" "Res" '(259 -98) 1 1 0 )
(command "insert" "Res" '(259 -96) 1 1 0 )
(command "insert" "Res" '(258 -94) 1 1 0 )
(command "insert" "Res" '(258 -97) 1 1 0 )
(command "insert" "Res" '(259 -95) 1 1 0 )
(command "insert" "Res" '(259 -93) 1 1 0 )
(command "insert" "Res" '(260 -98) 1 1 0 )
(command "insert" "Res" '(260 -94) 1 1 0 )
(command "insert" "Res" '(260 -96) 1 1 0 )
(command "layer" "m" "Commmer" "" )
(command "insert" "Commmer" '(256 -97) 1 1 0 )
(command "insert" "Commmer" '(257 -98) 1 1 0 )
(command "insert" "Commmer" '(254 -97) 1 1 0 )
(command "insert" "Commmer" '(256 -95) 1 1 0 )
(command "insert" "Commmer" '(255 -94) 1 1 0 )
(command "insert" "Commmer" '(257 -94) 1 1 0 )
(command "insert" "Commmer" '(253 -96) 1 1 0 )
(command "insert" "Commmer" '(256 -96) 1 1 0 )
(command "insert" "Commmer" '(252 -97) 1 1 0 )
(command "insert" "Commmer" '(257 -93) 1 1 0 )
(command "insert" "Commmer" '(256 -94) 1 1 0 )
(command "insert" "Commmer" '(257 -97) 1 1 0 )
(command "insert" "Commmer" '(255 -97) 1 1 0 )
(command "insert" "Commmer" '(255 -93) 1 1 0 )
(command "insert" "Commmer" '(254 -96) 1 1 0 )
(command "insert" "Commmer" '(253 -97) 1 1 0 )
(command "insert" "Commmer" '(255 -96) 1 1 0 )
(command "insert" "Commmer" '(254 -98) 1 1 0 )
(command "insert" "Commmer" '(256 -98) 1 1 0 )
(command "insert" "Commmer" '(255 -95) 1 1 0 )
(command "insert" "Commmer" '(252 -98) 1 1 0 )
(command "insert" "Commmer" '(255 -98) 1 1 0 )
(command "insert" "Commmer" '(252 -96) 1 1 0 )
(command "insert" "Commmer" '(253 -98) 1 1 0 )
(command "insert" "Commmer" '(257 -96) 1 1 0 )
(command "insert" "Commmer" '(257 -95) 1 1 0 )
(command "insert" "Commmer" '(256 -93) 1 1 0 )
(command "layer" "m" "Res" "" )
(command "insert" "Res" '(219 -64) 1 1 0 )
(command "insert" "Res" '(220 -63) 1 1 0 )
(command "insert" "Res" '(219 -65) 1 1 0 )
(command "insert" "Res" '(221 -63) 1 1 0 )
(command "insert" "Res" '(221 -64) 1 1 0 )
(command "insert" "Res" '(221 -65) 1 1 0 )
(command "insert" "Res" '(220 -65) 1 1 0 )
(command "insert" "Res" '(220 -64) 1 1 0 )
(command "insert" "Res" '(219 -63) 1 1 0 )
(command "layer" "m" "Commmer" "" )
(command "insert" "Commmer" '(216 -83) 1 1 0 )
(command "insert" "Commmer" '(220 -80) 1 1 0 )
(command "insert" "Commmer" '(217 -82) 1 1 0 )
(command "insert" "Commmer" '(219 -79) 1 1 0 )
(command "insert" "Commmer" '(214 -81) 1 1 0 )
(command "insert" "Commmer" '(214 -83) 1 1 0 )
(command "insert" "Commmer" '(220 -78) 1 1 0 )
(command "insert" "Commmer" '(221 -79) 1 1 0 )
(command "insert" "Commmer" '(213 -82) 1 1 0 )
(command "insert" "Commmer" '(221 -80) 1 1 0 )
(command "insert" "Commmer" '(218 -82) 1 1 0 )
(command "insert" "Commmer" '(215 -83) 1 1 0 )
(command "insert" "Commmer" '(217 -81) 1 1 0 )
(command "insert" "Commmer" '(219 -78) 1 1 0 )
(command "insert" "Commmer" '(215 -81) 1 1 0 )
(command "insert" "Commmer" '(217 -83) 1 1 0 )
(command "insert" "Commmer" '(216 -82) 1 1 0 )
(command "insert" "Commmer" '(219 -80) 1 1 0 )
(command "insert" "Commmer" '(216 -81) 1 1 0 )
(command "insert" "Commmer" '(220 -79) 1 1 0 )
(command "insert" "Commmer" '(214 -82) 1 1 0 )
(command "insert" "Commmer" '(218 -81) 1 1 0 )
(command "insert" "Commmer" '(221 -78) 1 1 0 )
(command "insert" "Commmer" '(213 -81) 1 1 0 )
(command "insert" "Commmer" '(218 -83) 1 1 0 )
(command "insert" "Commmer" '(215 -82) 1 1 0 )
(command "insert" "Commmer" '(213 -83) 1 1 0 )
(command "layer" "m" "Res" "" )
(command "insert" "Res" '(22 -34) 1 1 0 )
(command "insert" "Res" '(18 -35) 1 1 0 )
(command "insert" "Res" '(21 -33) 1 1 0 )
(command "insert" "Res" '(23 -33) 1 1 0 )
(command "insert" "Res" '(23 -34) 1 1 0 )
(command "insert" "Res" '(21 -35) 1 1 0 )
(command "insert" "Res" '(19 -35) 1 1 0 )
(command "insert" "Res" '(22 -33) 1 1 0 )
(command "insert" "Res" '(19 -33) 1 1 0 )
(command "insert" "Res" '(22 -35) 1 1 0 )
(command "insert" "Res" '(20 -35) 1 1 0 )
(command "insert" "Res" '(18 -34) 1 1 0 )
(command "insert" "Res" '(21 -34) 1 1 0 )
(command "insert" "Res" '(23 -35) 1 1 0 )
(command "insert" "Res" '(19 -34) 1 1 0 )
(command "insert" "Res" '(20 -33) 1 1 0 )
(command "insert" "Res" '(20 -34) 1 1 0 )
(command "insert" "Res" '(18 -33) 1 1 0 )
(command "layer" "m" "edge" "" )
(command "insert" "edge" '(270 -107) 1 1 0 )
(command "insert" "edge" '(293 -105) 1 1 0 )
(command "insert" "edge" '(294 -105) 1 1 0 )
(command "insert" "edge" '(273 -105) 1 1 0 )
(command "insert" "edge" '(296 -107) 1 1 0 )
(command "insert" "edge" '(285 -106) 1 1 0 )
(command "insert" "edge" '(291 -107) 1 1 0 )
(command "insert" "edge" '(286 -107) 1 1 0 )
(command "insert" "edge" '(288 -106) 1 1 0 )
(command "insert" "edge" '(282 -106) 1 1 0 )
(command "insert" "edge" '(268 -106) 1 1 0 )
(command "insert" "edge" '(278 -106) 1 1 0 )
(command "insert" "edge" '(281 -105) 1 1 0 )
(command "insert" "edge" '(279 -106) 1 1 0 )
(command "insert" "edge" '(294 -106) 1 1 0 )
(command "insert" "edge" '(276 -106) 1 1 0 )
(command "insert" "edge" '(295 -106) 1 1 0 )
(command "insert" "edge" '(289 -106) 1 1 0 )
(command "insert" "edge" '(270 -105) 1 1 0 )
(command "insert" "edge" '(269 -106) 1 1 0 )
(command "insert" "edge" '(292 -106) 1 1 0 )
(command "insert" "edge" '(272 -106) 1 1 0 )
(command "insert" "edge" '(286 -105) 1 1 0 )
(command "insert" "edge" '(284 -105) 1 1 0 )
(command "insert" "edge" '(279 -105) 1 1 0 )
(command "insert" "edge" '(283 -106) 1 1 0 )
(command "insert" "edge" '(277 -106) 1 1 0 )
(command "insert" "edge" '(280 -106) 1 1 0 )
(command "insert" "edge" '(295 -105) 1 1 0 )
(command "insert" "edge" '(270 -106) 1 1 0 )
(command "insert" "edge" '(293 -106) 1 1 0 )
(command "insert" "edge" '(273 -106) 1 1 0 )
(command "insert" "edge" '(290 -107) 1 1 0 )
(command "insert" "edge" '(296 -106) 1 1 0 )
(command "insert" "edge" '(271 -106) 1 1 0 )
(command "insert" "edge" '(285 -107) 1 1 0 )
(command "insert" "edge" '(286 -106) 1 1 0 )
(command "insert" "edge" '(288 -105) 1 1 0 )
(command "insert" "edge" '(283 -105) 1 1 0 )
(command "insert" "edge" '(268 -105) 1 1 0 )
(command "insert" "edge" '(287 -106) 1 1 0 )
(command "insert" "edge" '(281 -106) 1 1 0 )
(command "insert" "edge" '(267 -106) 1 1 0 )
(command "insert" "edge" '(284 -107) 1 1 0 )
(command "insert" "edge" '(279 -107) 1 1 0 )
(command "insert" "edge" '(276 -105) 1 1 0 )
(command "insert" "edge" '(271 -105) 1 1 0 )
(command "insert" "edge" '(295 -107) 1 1 0 )
(command "insert" "edge" '(275 -106) 1 1 0 )
(command "insert" "edge" '(289 -107) 1 1 0 )
(command "insert" "edge" '(274 -107) 1 1 0 )
(command "insert" "edge" '(269 -107) 1 1 0 )
(command "insert" "edge" '(292 -105) 1 1 0 )
(command "insert" "edge" '(290 -105) 1 1 0 )
(command "insert" "edge" '(287 -105) 1 1 0 )
(command "insert" "edge" '(272 -105) 1 1 0 )
(command "insert" "edge" '(285 -105) 1 1 0 )
(command "insert" "edge" '(291 -106) 1 1 0 )
(command "insert" "edge" '(267 -105) 1 1 0 )
(command "insert" "edge" '(288 -107) 1 1 0 )
(command "insert" "edge" '(282 -107) 1 1 0 )
(command "insert" "edge" '(283 -107) 1 1 0 )
(command "insert" "edge" '(268 -107) 1 1 0 )
(command "insert" "edge" '(277 -107) 1 1 0 )
(command "insert" "edge" '(278 -107) 1 1 0 )
(command "insert" "edge" '(280 -105) 1 1 0 )
(command "insert" "edge" '(275 -105) 1 1 0 )
(command "insert" "edge" '(293 -107) 1 1 0 )
(command "insert" "edge" '(294 -107) 1 1 0 )
(command "insert" "edge" '(273 -107) 1 1 0 )
(command "insert" "edge" '(276 -107) 1 1 0 )
(command "insert" "edge" '(290 -106) 1 1 0 )
(command "insert" "edge" '(296 -105) 1 1 0 )
(command "insert" "edge" '(271 -107) 1 1 0 )
(command "insert" "edge" '(291 -105) 1 1 0 )
(command "insert" "edge" '(289 -105) 1 1 0 )
(command "insert" "edge" '(274 -105) 1 1 0 )
(command "insert" "edge" '(269 -105) 1 1 0 )
(command "insert" "edge" '(292 -107) 1 1 0 )
(command "insert" "edge" '(287 -107) 1 1 0 )
(command "insert" "edge" '(272 -107) 1 1 0 )
(command "insert" "edge" '(281 -107) 1 1 0 )
(command "insert" "edge" '(267 -107) 1 1 0 )
(command "insert" "edge" '(284 -106) 1 1 0 )
(command "insert" "edge" '(282 -105) 1 1 0 )
(command "insert" "edge" '(277 -105) 1 1 0 )
(command "insert" "edge" '(278 -105) 1 1 0 )
(command "insert" "edge" '(280 -107) 1 1 0 )
(command "insert" "edge" '(275 -107) 1 1 0 )
(command "insert" "edge" '(274 -106) 1 1 0 )
(command "layer" "m" "alley" "" )
(command "insert" "alley" '(51 -40) 1 1 0 )
(command "insert" "alley" '(67 -44) 1 1 0 )
(command "insert" "alley" '(65 -44) 1 1 0 )
(command "insert" "alley" '(68 -47) 1 1 0 )
(command "insert" "alley" '(66 -43) 1 1 0 )
(command "insert" "alley" '(58 -41) 1 1 0 )
(command "insert" "alley" '(57 -39) 1 1 0 )
(command "insert" "alley" '(54 -41) 1 1 0 )
(command "insert" "alley" '(52 -40) 1 1 0 )
(command "insert" "alley" '(60 -39) 1 1 0 )
(command "insert" "alley" '(59 -41) 1 1 0 )
(command "insert" "alley" '(63 -42) 1 1 0 )
(command "insert" "alley" '(51 -39) 1 1 0 )
(command "insert" "alley" '(48 -40) 1 1 0 )
(command "insert" "alley" '(67 -43) 1 1 0 )
(command "insert" "alley" '(53 -40) 1 1 0 )
(command "insert" "alley" '(50 -39) 1 1 0 )
(command "insert" "alley" '(68 -44) 1 1 0 )
(command "insert" "alley" '(54 -39) 1 1 0 )
(command "insert" "alley" '(66 -44) 1 1 0 )
(command "insert" "alley" '(67 -46) 1 1 0 )
(command "insert" "alley" '(49 -40) 1 1 0 )
(command "insert" "alley" '(56 -40) 1 1 0 )
(command "insert" "alley" '(61 -41) 1 1 0 )
(command "insert" "alley" '(64 -43) 1 1 0 )
(command "insert" "alley" '(65 -42) 1 1 0 )
(command "insert" "alley" '(50 -40) 1 1 0 )
(command "insert" "alley" '(57 -40) 1 1 0 )
(command "insert" "alley" '(48 -39) 1 1 0 )
(command "insert" "alley" '(51 -41) 1 1 0 )
(command "insert" "alley" '(67 -45) 1 1 0 )
(command "insert" "alley" '(62 -41) 1 1 0 )
(command "insert" "alley" '(60 -41) 1 1 0 )
(command "insert" "alley" '(68 -46) 1 1 0 )
(command "insert" "alley" '(66 -42) 1 1 0 )
(command "insert" "alley" '(63 -44) 1 1 0 )
(command "insert" "alley" '(58 -40) 1 1 0 )
(command "insert" "alley" '(54 -40) 1 1 0 )
(command "insert" "alley" '(58 -39) 1 1 0 )
(command "insert" "alley" '(68 -43) 1 1 0 )
(command "insert" "alley" '(63 -43) 1 1 0 )
(command "insert" "alley" '(61 -39) 1 1 0 )
(command "insert" "alley" '(55 -40) 1 1 0 )
(command "insert" "alley" '(53 -41) 1 1 0 )
(command "insert" "alley" '(52 -39) 1 1 0 )
(command "insert" "alley" '(66 -47) 1 1 0 )
(command "insert" "alley" '(64 -44) 1 1 0 )
(command "insert" "alley" '(55 -39) 1 1 0 )
(command "insert" "alley" '(67 -47) 1 1 0 )
(command "insert" "alley" '(49 -41) 1 1 0 )
(command "insert" "alley" '(56 -39) 1 1 0 )
(command "insert" "alley" '(59 -39) 1 1 0 )
(command "insert" "alley" '(52 -41) 1 1 0 )
(command "insert" "alley" '(64 -42) 1 1 0 )
(command "insert" "alley" '(59 -40) 1 1 0 )
(command "insert" "alley" '(65 -43) 1 1 0 )
(command "insert" "alley" '(62 -39) 1 1 0 )
(command "insert" "alley" '(57 -41) 1 1 0 )
(command "insert" "alley" '(49 -39) 1 1 0 )
(command "insert" "alley" '(48 -41) 1 1 0 )
(command "insert" "alley" '(67 -42) 1 1 0 )
(command "insert" "alley" '(62 -40) 1 1 0 )
(command "insert" "alley" '(60 -40) 1 1 0 )
(command "insert" "alley" '(68 -45) 1 1 0 )
(command "insert" "alley" '(66 -45) 1 1 0 )
(command "insert" "alley" '(56 -41) 1 1 0 )
(command "insert" "alley" '(68 -42) 1 1 0 )
(command "insert" "alley" '(53 -39) 1 1 0 )
(command "insert" "alley" '(61 -40) 1 1 0 )
(command "insert" "alley" '(55 -41) 1 1 0 )
(command "insert" "alley" '(50 -41) 1 1 0 )
(command "insert" "alley" '(66 -46) 1 1 0 )
(command "layer" "m" "Commmer" "" )
(command "insert" "Commmer" '(184 -82) 1 1 0 )
(command "insert" "Commmer" '(201 -86) 1 1 0 )
(command "insert" "Commmer" '(196 -91) 1 1 0 )
(command "insert" "Commmer" '(196 -86) 1 1 0 )
(command "insert" "Commmer" '(185 -79) 1 1 0 )
(command "insert" "Commmer" '(199 -93) 1 1 0 )
(command "insert" "Commmer" '(183 -89) 1 1 0 )
(command "insert" "Commmer" '(189 -81) 1 1 0 )
(command "insert" "Commmer" '(183 -81) 1 1 0 )
(command "insert" "Commmer" '(195 -84) 1 1 0 )
(command "insert" "Commmer" '(184 -79) 1 1 0 )
(command "insert" "Commmer" '(191 -88) 1 1 0 )
(command "insert" "Commmer" '(197 -86) 1 1 0 )
(command "insert" "Commmer" '(202 -91) 1 1 0 )
(command "insert" "Commmer" '(199 -87) 1 1 0 )
(command "insert" "Commmer" '(187 -86) 1 1 0 )
(command "insert" "Commmer" '(188 -88) 1 1 0 )
(command "insert" "Commmer" '(183 -83) 1 1 0 )
(command "insert" "Commmer" '(199 -96) 1 1 0 )
(command "insert" "Commmer" '(200 -97) 1 1 0 )
(command "insert" "Commmer" '(198 -97) 1 1 0 )
(command "insert" "Commmer" '(194 -84) 1 1 0 )
(command "insert" "Commmer" '(184 -89) 1 1 0 )
(command "insert" "Commmer" '(190 -81) 1 1 0 )
(command "insert" "Commmer" '(184 -76) 1 1 0 )
(command "insert" "Commmer" '(197 -92) 1 1 0 )
(command "insert" "Commmer" '(186 -83) 1 1 0 )
(command "insert" "Commmer" '(200 -90) 1 1 0 )
(command "insert" "Commmer" '(181 -88) 1 1 0 )
(command "insert" "Commmer" '(188 -82) 1 1 0 )
(command "insert" "Commmer" '(185 -80) 1 1 0 )
(command "insert" "Commmer" '(186 -78) 1 1 0 )
(command "insert" "Commmer" '(193 -86) 1 1 0 )
(command "insert" "Commmer" '(199 -90) 1 1 0 )
(command "insert" "Commmer" '(187 -85) 1 1 0 )
(command "insert" "Commmer" '(198 -95) 1 1 0 )
(command "insert" "Commmer" '(189 -87) 1 1 0 )
(command "insert" "Commmer" '(183 -76) 1 1 0 )
(command "insert" "Commmer" '(190 -82) 1 1 0 )
(command "insert" "Commmer" '(186 -89) 1 1 0 )
(command "insert" "Commmer" '(201 -90) 1 1 0 )
(command "insert" "Commmer" '(186 -84) 1 1 0 )
(command "insert" "Commmer" '(191 -82) 1 1 0 )
(command "insert" "Commmer" '(188 -87) 1 1 0 )
(command "insert" "Commmer" '(202 -90) 1 1 0 )
(command "insert" "Commmer" '(203 -92) 1 1 0 )
(command "insert" "Commmer" '(199 -89) 1 1 0 )
(command "insert" "Commmer" '(187 -80) 1 1 0 )
(command "insert" "Commmer" '(202 -85) 1 1 0 )
(command "insert" "Commmer" '(198 -88) 1 1 0 )
(command "insert" "Commmer" '(190 -88) 1 1 0 )
(command "insert" "Commmer" '(184 -83) 1 1 0 )
(command "insert" "Commmer" '(201 -85) 1 1 0 )
(command "insert" "Commmer" '(185 -89) 1 1 0 )
(command "insert" "Commmer" '(203 -86) 1 1 0 )
(command "insert" "Commmer" '(191 -81) 1 1 0 )
(command "insert" "Commmer" '(188 -84) 1 1 0 )
(command "insert" "Commmer" '(185 -78) 1 1 0 )
(command "insert" "Commmer" '(203 -91) 1 1 0 )
(command "insert" "Commmer" '(199 -92) 1 1 0 )
(command "insert" "Commmer" '(202 -86) 1 1 0 )
(command "insert" "Commmer" '(183 -88) 1 1 0 )
(command "insert" "Commmer" '(180 -88) 1 1 0 )
(command "insert" "Commmer" '(184 -80) 1 1 0 )
(command "insert" "Commmer" '(200 -94) 1 1 0 )
(command "insert" "Commmer" '(200 -88) 1 1 0 )
(command "insert" "Commmer" '(197 -85) 1 1 0 )
(command "insert" "Commmer" '(203 -85) 1 1 0 )
(command "insert" "Commmer" '(196 -84) 1 1 0 )
(command "insert" "Commmer" '(188 -89) 1 1 0 )
(command "insert" "Commmer" '(202 -92) 1 1 0 )
(command "insert" "Commmer" '(183 -82) 1 1 0 )
(command "insert" "Commmer" '(200 -98) 1 1 0 )
(command "insert" "Commmer" '(189 -83) 1 1 0 )
(command "insert" "Commmer" '(187 -79) 1 1 0 )
(command "insert" "Commmer" '(194 -85) 1 1 0 )
(command "insert" "Commmer" '(184 -77) 1 1 0 )
(command "insert" "Commmer" '(197 -91) 1 1 0 )
(command "insert" "Commmer" '(186 -80) 1 1 0 )
(command "insert" "Commmer" '(200 -91) 1 1 0 )
(command "insert" "Commmer" '(188 -83) 1 1 0 )
(command "insert" "Commmer" '(185 -87) 1 1 0 )
(command "insert" "Commmer" '(186 -79) 1 1 0 )
(command "insert" "Commmer" '(193 -85) 1 1 0 )
(command "insert" "Commmer" '(187 -84) 1 1 0 )
(command "insert" "Commmer" '(192 -84) 1 1 0 )
(command "insert" "Commmer" '(198 -92) 1 1 0 )
(command "insert" "Commmer" '(187 -89) 1 1 0 )
(command "insert" "Commmer" '(194 -86) 1 1 0 )
(command "insert" "Commmer" '(195 -92) 1 1 0 )
(command "insert" "Commmer" '(183 -79) 1 1 0 )
(command "insert" "Commmer" '(184 -87) 1 1 0 )
(command "insert" "Commmer" '(190 -83) 1 1 0 )
(command "insert" "Commmer" '(186 -85) 1 1 0 )
(command "insert" "Commmer" '(198 -98) 1 1 0 )
(command "insert" "Commmer" '(182 -88) 1 1 0 )
(command "insert" "Commmer" '(188 -80) 1 1 0 )
(command "insert" "Commmer" '(185 -82) 1 1 0 )
(command "insert" "Commmer" '(181 -87) 1 1 0 )
(command "insert" "Commmer" '(199 -88) 1 1 0 )
(command "insert" "Commmer" '(187 -83) 1 1 0 )
(command "insert" "Commmer" '(198 -89) 1 1 0 )
(command "insert" "Commmer" '(188 -78) 1 1 0 )
(command "insert" "Commmer" '(189 -89) 1 1 0 )
(command "insert" "Commmer" '(190 -89) 1 1 0 )
(command "insert" "Commmer" '(195 -91) 1 1 0 )
(command "insert" "Commmer" '(180 -87) 1 1 0 )
(command "insert" "Commmer" '(185 -83) 1 1 0 )
(command "insert" "Commmer" '(201 -84) 1 1 0 )
(command "insert" "Commmer" '(185 -88) 1 1 0 )
(command "insert" "Commmer" '(186 -86) 1 1 0 )
(command "insert" "Commmer" '(188 -85) 1 1 0 )
(command "insert" "Commmer" '(185 -77) 1 1 0 )
(command "insert" "Commmer" '(203 -90) 1 1 0 )
(command "insert" "Commmer" '(198 -87) 1 1 0 )
(command "insert" "Commmer" '(199 -95) 1 1 0 )
(command "insert" "Commmer" '(198 -90) 1 1 0 )
(command "insert" "Commmer" '(180 -89) 1 1 0 )
(command "insert" "Commmer" '(195 -86) 1 1 0 )
(command "insert" "Commmer" '(184 -81) 1 1 0 )
(command "insert" "Commmer" '(200 -95) 1 1 0 )
(command "insert" "Commmer" '(196 -90) 1 1 0 )
(command "insert" "Commmer" '(197 -84) 1 1 0 )
(command "insert" "Commmer" '(203 -84) 1 1 0 )
(command "insert" "Commmer" '(191 -87) 1 1 0 )
(command "insert" "Commmer" '(196 -85) 1 1 0 )
(command "insert" "Commmer" '(199 -98) 1 1 0 )
(command "insert" "Commmer" '(189 -82) 1 1 0 )
(command "insert" "Commmer" '(187 -78) 1 1 0 )
(command "insert" "Commmer" '(192 -86) 1 1 0 )
(command "insert" "Commmer" '(183 -75) 1 1 0 )
(command "insert" "Commmer" '(200 -92) 1 1 0 )
(command "insert" "Commmer" '(190 -87) 1 1 0 )
(command "insert" "Commmer" '(195 -85) 1 1 0 )
(command "insert" "Commmer" '(184 -78) 1 1 0 )
(command "insert" "Commmer" '(197 -90) 1 1 0 )
(command "insert" "Commmer" '(186 -81) 1 1 0 )
(command "insert" "Commmer" '(191 -89) 1 1 0 )
(command "insert" "Commmer" '(193 -84) 1 1 0 )
(command "insert" "Commmer" '(200 -93) 1 1 0 )
(command "insert" "Commmer" '(187 -87) 1 1 0 )
(command "insert" "Commmer" '(185 -75) 1 1 0 )
(command "insert" "Commmer" '(183 -80) 1 1 0 )
(command "insert" "Commmer" '(198 -93) 1 1 0 )
(command "insert" "Commmer" '(199 -97) 1 1 0 )
(command "insert" "Commmer" '(187 -88) 1 1 0 )
(command "insert" "Commmer" '(200 -96) 1 1 0 )
(command "insert" "Commmer" '(198 -96) 1 1 0 )
(command "insert" "Commmer" '(183 -78) 1 1 0 )
(command "insert" "Commmer" '(184 -88) 1 1 0 )
(command "insert" "Commmer" '(184 -75) 1 1 0 )
(command "insert" "Commmer" '(186 -82) 1 1 0 )
(command "insert" "Commmer" '(200 -89) 1 1 0 )
(command "insert" "Commmer" '(181 -89) 1 1 0 )
(command "insert" "Commmer" '(182 -89) 1 1 0 )
(command "insert" "Commmer" '(196 -92) 1 1 0 )
(command "insert" "Commmer" '(188 -81) 1 1 0 )
(command "insert" "Commmer" '(185 -81) 1 1 0 )
(command "insert" "Commmer" '(199 -91) 1 1 0 )
(command "insert" "Commmer" '(187 -82) 1 1 0 )
(command "insert" "Commmer" '(201 -92) 1 1 0 )
(command "insert" "Commmer" '(183 -87) 1 1 0 )
(command "insert" "Commmer" '(200 -87) 1 1 0 )
(command "insert" "Commmer" '(198 -94) 1 1 0 )
(command "insert" "Commmer" '(188 -79) 1 1 0 )
(command "insert" "Commmer" '(189 -88) 1 1 0 )
(command "insert" "Commmer" '(192 -85) 1 1 0 )
(command "insert" "Commmer" '(195 -90) 1 1 0 )
(command "insert" "Commmer" '(183 -77) 1 1 0 )
(command "insert" "Commmer" '(186 -88) 1 1 0 )
(command "insert" "Commmer" '(201 -91) 1 1 0 )
(command "insert" "Commmer" '(182 -87) 1 1 0 )
(command "insert" "Commmer" '(186 -87) 1 1 0 )
(command "insert" "Commmer" '(191 -83) 1 1 0 )
(command "insert" "Commmer" '(188 -86) 1 1 0 )
(command "insert" "Commmer" '(185 -76) 1 1 0 )
(command "insert" "Commmer" '(199 -94) 1 1 0 )
(command "insert" "Commmer" '(187 -81) 1 1 0 )
(command "insert" "Commmer" '(202 -84) 1 1 0 )
(command "insert" "Commmer" '(198 -91) 1 1 0 )
(command "layer" "m" "Commmer" "" )
(command "insert" "Commmer" '(206 -74) 1 1 0 )
(command "insert" "Commmer" '(204 -73) 1 1 0 )
(command "insert" "Commmer" '(205 -72) 1 1 0 )
(command "insert" "Commmer" '(205 -73) 1 1 0 )
(command "insert" "Commmer" '(204 -74) 1 1 0 )
(command "insert" "Commmer" '(206 -73) 1 1 0 )
(command "insert" "Commmer" '(205 -74) 1 1 0 )
(command "insert" "Commmer" '(206 -72) 1 1 0 )
(command "insert" "Commmer" '(204 -72) 1 1 0 )
(command "layer" "m" "ped" "" )
(command "insert" "ped" '(239 -44) 1 1 0 )
(command "insert" "ped" '(238 -42) 1 1 0 )
(command "insert" "ped" '(234 -43) 1 1 0 )
(command "insert" "ped" '(235 -43) 1 1 0 )
(command "insert" "ped" '(236 -44) 1 1 0 )
(command "insert" "ped" '(235 -42) 1 1 0 )
(command "insert" "ped" '(239 -42) 1 1 0 )
(command "insert" "ped" '(236 -43) 1 1 0 )
(command "insert" "ped" '(239 -43) 1 1 0 )
(command "insert" "ped" '(235 -44) 1 1 0 )
(command "insert" "ped" '(238 -43) 1 1 0 )
(command "insert" "ped" '(237 -44) 1 1 0 )
(command "insert" "ped" '(234 -42) 1 1 0 )
(command "insert" "ped" '(237 -42) 1 1 0 )
(command "insert" "ped" '(234 -44) 1 1 0 )
(command "insert" "ped" '(238 -44) 1 1 0 )
(command "insert" "ped" '(236 -42) 1 1 0 )
(command "insert" "ped" '(237 -43) 1 1 0 )
(command "layer" "m" "Res" "" )
(command "insert" "Res" '(68 -29) 1 1 0 )
(command "insert" "Res" '(66 -29) 1 1 0 )
(command "insert" "Res" '(68 -28) 1 1 0 )
(command "insert" "Res" '(66 -28) 1 1 0 )
(command "insert" "Res" '(68 -27) 1 1 0 )
(command "insert" "Res" '(67 -28) 1 1 0 )
(command "insert" "Res" '(67 -29) 1 1 0 )
(command "insert" "Res" '(66 -27) 1 1 0 )
(command "insert" "Res" '(67 -27) 1 1 0 )
(command "layer" "m" "Commmer" "" )
(command "insert" "Commmer" '(53 -25) 1 1 0 )
(command "insert" "Commmer" '(56 -29) 1 1 0 )
(command "insert" "Commmer" '(59 -27) 1 1 0 )
(command "insert" "Commmer" '(52 -24) 1 1 0 )
(command "insert" "Commmer" '(55 -28) 1 1 0 )
(command "insert" "Commmer" '(53 -29) 1 1 0 )
(command "insert" "Commmer" '(52 -28) 1 1 0 )
(command "insert" "Commmer" '(55 -27) 1 1 0 )
(command "insert" "Commmer" '(53 -24) 1 1 0 )
(command "insert" "Commmer" '(52 -25) 1 1 0 )
(command "insert" "Commmer" '(58 -27) 1 1 0 )
(command "insert" "Commmer" '(53 -28) 1 1 0 )
(command "insert" "Commmer" '(51 -29) 1 1 0 )
(command "insert" "Commmer" '(58 -28) 1 1 0 )
(command "insert" "Commmer" '(52 -29) 1 1 0 )
(command "insert" "Commmer" '(57 -27) 1 1 0 )
(command "insert" "Commmer" '(56 -27) 1 1 0 )
(command "insert" "Commmer" '(59 -29) 1 1 0 )
(command "insert" "Commmer" '(52 -26) 1 1 0 )
(command "insert" "Commmer" '(53 -27) 1 1 0 )
(command "insert" "Commmer" '(54 -27) 1 1 0 )
(command "insert" "Commmer" '(58 -29) 1 1 0 )
(command "insert" "Commmer" '(51 -27) 1 1 0 )
(command "insert" "Commmer" '(51 -25) 1 1 0 )
(command "insert" "Commmer" '(54 -28) 1 1 0 )
(command "insert" "Commmer" '(59 -28) 1 1 0 )
(command "insert" "Commmer" '(52 -27) 1 1 0 )
(command "insert" "Commmer" '(57 -29) 1 1 0 )
(command "insert" "Commmer" '(51 -28) 1 1 0 )
(command "insert" "Commmer" '(56 -28) 1 1 0 )
(command "insert" "Commmer" '(55 -29) 1 1 0 )
(command "insert" "Commmer" '(51 -24) 1 1 0 )
(command "insert" "Commmer" '(53 -26) 1 1 0 )
(command "insert" "Commmer" '(54 -29) 1 1 0 )
(command "insert" "Commmer" '(51 -26) 1 1 0 )
(command "insert" "Commmer" '(57 -28) 1 1 0 )
(command "layer" "m" "alley" "" )
(command "insert" "alley" '(89 -42) 1 1 0 )
(command "insert" "alley" '(74 -40) 1 1 0 )
(command "insert" "alley" '(84 -44) 1 1 0 )
(command "insert" "alley" '(74 -39) 1 1 0 )
(command "insert" "alley" '(80 -40) 1 1 0 )
(command "insert" "alley" '(78 -39) 1 1 0 )
(command "insert" "alley" '(83 -46) 1 1 0 )
(command "insert" "alley" '(77 -39) 1 1 0 )
(command "insert" "alley" '(85 -44) 1 1 0 )
(command "insert" "alley" '(80 -45) 1 1 0 )
(command "insert" "alley" '(78 -40) 1 1 0 )
(command "insert" "alley" '(79 -45) 1 1 0 )
(command "insert" "alley" '(87 -42) 1 1 0 )
(command "insert" "alley" '(82 -47) 1 1 0 )
(command "insert" "alley" '(78 -45) 1 1 0 )
(command "insert" "alley" '(88 -42) 1 1 0 )
(command "insert" "alley" '(79 -40) 1 1 0 )
(command "insert" "alley" '(72 -39) 1 1 0 )
(command "insert" "alley" '(83 -45) 1 1 0 )
(command "insert" "alley" '(86 -43) 1 1 0 )
(command "insert" "alley" '(80 -39) 1 1 0 )
(command "insert" "alley" '(75 -39) 1 1 0 )
(command "insert" "alley" '(80 -42) 1 1 0 )
(command "insert" "alley" '(75 -40) 1 1 0 )
(command "insert" "alley" '(86 -44) 1 1 0 )
(command "insert" "alley" '(81 -43) 1 1 0 )
(command "insert" "alley" '(73 -41) 1 1 0 )
(command "insert" "alley" '(84 -43) 1 1 0 )
(command "insert" "alley" '(85 -42) 1 1 0 )
(command "insert" "alley" '(80 -47) 1 1 0 )
(command "insert" "alley" '(78 -46) 1 1 0 )
(command "insert" "alley" '(81 -46) 1 1 0 )
(command "insert" "alley" '(79 -47) 1 1 0 )
(command "insert" "alley" '(76 -40) 1 1 0 )
(command "insert" "alley" '(82 -45) 1 1 0 )
(command "insert" "alley" '(89 -43) 1 1 0 )
(command "insert" "alley" '(79 -42) 1 1 0 )
(command "insert" "alley" '(72 -41) 1 1 0 )
(command "insert" "alley" '(83 -47) 1 1 0 )
(command "insert" "alley" '(79 -39) 1 1 0 )
(command "insert" "alley" '(77 -40) 1 1 0 )
(command "insert" "alley" '(87 -44) 1 1 0 )
(command "insert" "alley" '(80 -44) 1 1 0 )
(command "insert" "alley" '(78 -43) 1 1 0 )
(command "insert" "alley" '(87 -43) 1 1 0 )
(command "insert" "alley" '(82 -46) 1 1 0 )
(command "insert" "alley" '(78 -44) 1 1 0 )
(command "insert" "alley" '(81 -44) 1 1 0 )
(command "insert" "alley" '(79 -41) 1 1 0 )
(command "insert" "alley" '(83 -42) 1 1 0 )
(command "insert" "alley" '(86 -42) 1 1 0 )
(command "insert" "alley" '(82 -43) 1 1 0 )
(command "insert" "alley" '(74 -41) 1 1 0 )
(command "insert" "alley" '(73 -39) 1 1 0 )
(command "insert" "alley" '(88 -44) 1 1 0 )
(command "insert" "alley" '(80 -41) 1 1 0 )
(command "insert" "alley" '(76 -39) 1 1 0 )
(command "insert" "alley" '(75 -41) 1 1 0 )
(command "insert" "alley" '(89 -44) 1 1 0 )
(command "insert" "alley" '(84 -42) 1 1 0 )
(command "insert" "alley" '(85 -43) 1 1 0 )
(command "insert" "alley" '(80 -46) 1 1 0 )
(command "insert" "alley" '(78 -41) 1 1 0 )
(command "insert" "alley" '(81 -47) 1 1 0 )
(command "insert" "alley" '(79 -44) 1 1 0 )
(command "insert" "alley" '(82 -44) 1 1 0 )
(command "insert" "alley" '(79 -43) 1 1 0 )
(command "insert" "alley" '(72 -40) 1 1 0 )
(command "insert" "alley" '(83 -44) 1 1 0 )
(command "insert" "alley" '(77 -41) 1 1 0 )
(command "insert" "alley" '(88 -43) 1 1 0 )
(command "insert" "alley" '(80 -43) 1 1 0 )
(command "insert" "alley" '(78 -42) 1 1 0 )
(command "insert" "alley" '(81 -42) 1 1 0 )
(command "insert" "alley" '(73 -40) 1 1 0 )
(command "insert" "alley" '(78 -47) 1 1 0 )
(command "insert" "alley" '(81 -45) 1 1 0 )
(command "insert" "alley" '(79 -46) 1 1 0 )
(command "insert" "alley" '(76 -41) 1 1 0 )
(command "insert" "alley" '(83 -43) 1 1 0 )
(command "insert" "alley" '(82 -42) 1 1 0 )
(command "layer" "m" "Commmer" "" )
(command "insert" "Commmer" '(51 -2) 1 1 0 )
(command "insert" "Commmer" '(53 -1) 1 1 0 )
(command "insert" "Commmer" '(52 -2) 1 1 0 )
(command "insert" "Commmer" '(51 -1) 1 1 0 )
(command "insert" "Commmer" '(52 -1) 1 1 0 )
(command "insert" "Commmer" '(53 -2) 1 1 0 )
(command "layer" "m" "alley" "" )
(command "insert" "alley" '(113 -50) 1 1 0 )
(command "insert" "alley" '(112 -48) 1 1 0 )
(command "insert" "alley" '(115 -49) 1 1 0 )
(command "insert" "alley" '(114 -49) 1 1 0 )
(command "insert" "alley" '(113 -48) 1 1 0 )
(command "insert" "alley" '(116 -49) 1 1 0 )
(command "insert" "alley" '(111 -49) 1 1 0 )
(command "insert" "alley" '(112 -49) 1 1 0 )
(command "insert" "alley" '(115 -50) 1 1 0 )
(command "insert" "alley" '(115 -48) 1 1 0 )
(command "insert" "alley" '(113 -49) 1 1 0 )
(command "insert" "alley" '(114 -48) 1 1 0 )
(command "insert" "alley" '(111 -50) 1 1 0 )
(command "insert" "alley" '(114 -50) 1 1 0 )
(command "insert" "alley" '(116 -50) 1 1 0 )
(command "insert" "alley" '(111 -48) 1 1 0 )
(command "insert" "alley" '(112 -50) 1 1 0 )
(command "insert" "alley" '(116 -48) 1 1 0 )
(command "layer" "m" "Commmer" "" )
(command "insert" "Commmer" '(32 -1) 1 1 0 )
(command "insert" "Commmer" '(23 -1) 1 1 0 )
(command "insert" "Commmer" '(21 -2) 1 1 0 )
(command "insert" "Commmer" '(16 -2) 1 1 0 )
(command "insert" "Commmer" '(15 -1) 1 1 0 )
(command "insert" "Commmer" '(28 -1) 1 1 0 )
(command "insert" "Commmer" '(25 -1) 1 1 0 )
(command "insert" "Commmer" '(27 -2) 1 1 0 )
(command "insert" "Commmer" '(32 -2) 1 1 0 )
(command "insert" "Commmer" '(18 -1) 1 1 0 )
(command "insert" "Commmer" '(31 -1) 1 1 0 )
(command "insert" "Commmer" '(22 -2) 1 1 0 )
(command "insert" "Commmer" '(21 -1) 1 1 0 )
(command "insert" "Commmer" '(23 -2) 1 1 0 )
(command "insert" "Commmer" '(17 -2) 1 1 0 )
(command "insert" "Commmer" '(28 -2) 1 1 0 )
(command "insert" "Commmer" '(34 -1) 1 1 0 )
(command "insert" "Commmer" '(24 -1) 1 1 0 )
(command "insert" "Commmer" '(33 -2) 1 1 0 )
(command "insert" "Commmer" '(30 -1) 1 1 0 )
(command "insert" "Commmer" '(27 -1) 1 1 0 )
(command "insert" "Commmer" '(18 -2) 1 1 0 )
(command "insert" "Commmer" '(20 -1) 1 1 0 )
(command "insert" "Commmer" '(17 -1) 1 1 0 )
(command "insert" "Commmer" '(19 -2) 1 1 0 )
(command "insert" "Commmer" '(29 -2) 1 1 0 )
(command "insert" "Commmer" '(24 -2) 1 1 0 )
(command "insert" "Commmer" '(34 -2) 1 1 0 )
(command "insert" "Commmer" '(35 -1) 1 1 0 )
(command "insert" "Commmer" '(26 -2) 1 1 0 )
(command "insert" "Commmer" '(33 -1) 1 1 0 )
(command "insert" "Commmer" '(35 -2) 1 1 0 )
(command "insert" "Commmer" '(26 -1) 1 1 0 )
(command "insert" "Commmer" '(15 -2) 1 1 0 )
(command "insert" "Commmer" '(20 -2) 1 1 0 )
(command "insert" "Commmer" '(30 -2) 1 1 0 )
(command "insert" "Commmer" '(16 -1) 1 1 0 )
(command "insert" "Commmer" '(29 -1) 1 1 0 )
(command "insert" "Commmer" '(31 -2) 1 1 0 )
(command "insert" "Commmer" '(25 -2) 1 1 0 )
(command "insert" "Commmer" '(22 -1) 1 1 0 )
(command "insert" "Commmer" '(19 -1) 1 1 0 )
(command "layer" "m" "edge" "" )
(command "insert" "edge" '(240 -107) 1 1 0 )
(command "insert" "edge" '(249 -107) 1 1 0 )
(command "insert" "edge" '(241 -106) 1 1 0 )
(command "insert" "edge" '(250 -105) 1 1 0 )
(command "insert" "edge" '(245 -105) 1 1 0 )
(command "insert" "edge" '(246 -105) 1 1 0 )
(command "insert" "edge" '(238 -106) 1 1 0 )
(command "insert" "edge" '(248 -107) 1 1 0 )
(command "insert" "edge" '(251 -105) 1 1 0 )
(command "insert" "edge" '(243 -107) 1 1 0 )
(command "insert" "edge" '(242 -106) 1 1 0 )
(command "insert" "edge" '(249 -106) 1 1 0 )
(command "insert" "edge" '(241 -105) 1 1 0 )
(command "insert" "edge" '(247 -107) 1 1 0 )
(command "insert" "edge" '(244 -105) 1 1 0 )
(command "insert" "edge" '(250 -106) 1 1 0 )
(command "insert" "edge" '(243 -106) 1 1 0 )
(command "insert" "edge" '(246 -106) 1 1 0 )
(command "insert" "edge" '(242 -107) 1 1 0 )
(command "insert" "edge" '(249 -105) 1 1 0 )
(command "insert" "edge" '(237 -107) 1 1 0 )
(command "insert" "edge" '(238 -107) 1 1 0 )
(command "insert" "edge" '(247 -106) 1 1 0 )
(command "insert" "edge" '(240 -105) 1 1 0 )
(command "insert" "edge" '(239 -105) 1 1 0 )
(command "insert" "edge" '(244 -106) 1 1 0 )
(command "insert" "edge" '(250 -107) 1 1 0 )
(command "insert" "edge" '(239 -106) 1 1 0 )
(command "insert" "edge" '(245 -107) 1 1 0 )
(command "insert" "edge" '(246 -107) 1 1 0 )
(command "insert" "edge" '(238 -105) 1 1 0 )
(command "insert" "edge" '(237 -106) 1 1 0 )
(command "insert" "edge" '(248 -105) 1 1 0 )
(command "insert" "edge" '(243 -105) 1 1 0 )
(command "insert" "edge" '(240 -106) 1 1 0 )
(command "insert" "edge" '(241 -107) 1 1 0 )
(command "insert" "edge" '(244 -107) 1 1 0 )
(command "insert" "edge" '(247 -105) 1 1 0 )
(command "insert" "edge" '(239 -107) 1 1 0 )
(command "insert" "edge" '(251 -106) 1 1 0 )
(command "insert" "edge" '(245 -106) 1 1 0 )
(command "insert" "edge" '(242 -105) 1 1 0 )
(command "insert" "edge" '(237 -105) 1 1 0 )
(command "insert" "edge" '(248 -106) 1 1 0 )
(command "insert" "edge" '(251 -107) 1 1 0 )
(command "layer" "m" "edge" "" )
(command "insert" "edge" '(54 -2) 1 1 0 )
(command "insert" "edge" '(55 -2) 1 1 0 )
(command "insert" "edge" '(56 -2) 1 1 0 )
(command "insert" "edge" '(55 -1) 1 1 0 )
(command "insert" "edge" '(56 -1) 1 1 0 )
(command "insert" "edge" '(54 -1) 1 1 0 )
(command "layer" "m" "Res" "" )
(command "insert" "Res" '(99 -24) 1 1 0 )
(command "insert" "Res" '(95 -29) 1 1 0 )
(command "insert" "Res" '(97 -25) 1 1 0 )
(command "insert" "Res" '(96 -24) 1 1 0 )
(command "insert" "Res" '(94 -29) 1 1 0 )
(command "insert" "Res" '(101 -25) 1 1 0 )
(command "insert" "Res" '(95 -24) 1 1 0 )
(command "insert" "Res" '(97 -28) 1 1 0 )
(command "insert" "Res" '(100 -24) 1 1 0 )
(command "insert" "Res" '(93 -25) 1 1 0 )
(command "insert" "Res" '(94 -25) 1 1 0 )
(command "insert" "Res" '(98 -27) 1 1 0 )
(command "insert" "Res" '(99 -27) 1 1 0 )
(command "insert" "Res" '(98 -28) 1 1 0 )
(command "insert" "Res" '(95 -28) 1 1 0 )
(command "insert" "Res" '(97 -24) 1 1 0 )
(command "insert" "Res" '(100 -28) 1 1 0 )
(command "insert" "Res" '(93 -29) 1 1 0 )
(command "insert" "Res" '(96 -25) 1 1 0 )
(command "insert" "Res" '(96 -29) 1 1 0 )
(command "insert" "Res" '(101 -24) 1 1 0 )
(command "insert" "Res" '(101 -29) 1 1 0 )
(command "insert" "Res" '(95 -27) 1 1 0 )
(command "insert" "Res" '(100 -25) 1 1 0 )
(command "insert" "Res" '(93 -24) 1 1 0 )
(command "insert" "Res" '(98 -24) 1 1 0 )
(command "insert" "Res" '(99 -26) 1 1 0 )
(command "insert" "Res" '(100 -29) 1 1 0 )
(command "insert" "Res" '(93 -28) 1 1 0 )
(command "insert" "Res" '(94 -26) 1 1 0 )
(command "insert" "Res" '(96 -26) 1 1 0 )
(command "insert" "Res" '(97 -27) 1 1 0 )
(command "insert" "Res" '(98 -29) 1 1 0 )
(command "insert" "Res" '(95 -26) 1 1 0 )
(command "insert" "Res" '(100 -26) 1 1 0 )
(command "insert" "Res" '(98 -25) 1 1 0 )
(command "insert" "Res" '(101 -27) 1 1 0 )
(command "insert" "Res" '(101 -28) 1 1 0 )
(command "insert" "Res" '(93 -27) 1 1 0 )
(command "insert" "Res" '(94 -27) 1 1 0 )
(command "insert" "Res" '(96 -27) 1 1 0 )
(command "insert" "Res" '(99 -25) 1 1 0 )
(command "insert" "Res" '(97 -26) 1 1 0 )
(command "insert" "Res" '(100 -27) 1 1 0 )
(command "insert" "Res" '(94 -28) 1 1 0 )
(command "insert" "Res" '(99 -29) 1 1 0 )
(command "insert" "Res" '(101 -26) 1 1 0 )
(command "insert" "Res" '(95 -25) 1 1 0 )
(command "insert" "Res" '(99 -28) 1 1 0 )
(command "insert" "Res" '(97 -29) 1 1 0 )
(command "insert" "Res" '(96 -28) 1 1 0 )
(command "insert" "Res" '(93 -26) 1 1 0 )
(command "insert" "Res" '(94 -24) 1 1 0 )
(command "insert" "Res" '(98 -26) 1 1 0 )
(command "layer" "m" "Commmer" "" )
(command "insert" "Commmer" '(209 -50) 1 1 0 )
(command "insert" "Commmer" '(200 -46) 1 1 0 )
(command "insert" "Commmer" '(201 -47) 1 1 0 )
(command "insert" "Commmer" '(204 -45) 1 1 0 )
(command "insert" "Commmer" '(196 -47) 1 1 0 )
(command "insert" "Commmer" '(199 -45) 1 1 0 )
(command "insert" "Commmer" '(197 -46) 1 1 0 )
(command "insert" "Commmer" '(198 -45) 1 1 0 )
(command "insert" "Commmer" '(207 -48) 1 1 0 )
(command "insert" "Commmer" '(209 -49) 1 1 0 )
(command "insert" "Commmer" '(200 -47) 1 1 0 )
(command "insert" "Commmer" '(203 -45) 1 1 0 )
(command "insert" "Commmer" '(195 -47) 1 1 0 )
(command "insert" "Commmer" '(208 -48) 1 1 0 )
(command "insert" "Commmer" '(201 -46) 1 1 0 )
(command "insert" "Commmer" '(204 -46) 1 1 0 )
(command "insert" "Commmer" '(202 -45) 1 1 0 )
(command "insert" "Commmer" '(205 -47) 1 1 0 )
(command "insert" "Commmer" '(197 -45) 1 1 0 )
(command "insert" "Commmer" '(206 -45) 1 1 0 )
(command "insert" "Commmer" '(209 -48) 1 1 0 )
(command "insert" "Commmer" '(195 -46) 1 1 0 )
(command "insert" "Commmer" '(198 -46) 1 1 0 )
(command "insert" "Commmer" '(208 -49) 1 1 0 )
(command "insert" "Commmer" '(201 -45) 1 1 0 )
(command "insert" "Commmer" '(204 -47) 1 1 0 )
(command "insert" "Commmer" '(199 -47) 1 1 0 )
(command "insert" "Commmer" '(205 -46) 1 1 0 )
(command "insert" "Commmer" '(196 -45) 1 1 0 )
(command "insert" "Commmer" '(202 -46) 1 1 0 )
(command "insert" "Commmer" '(207 -50) 1 1 0 )
(command "insert" "Commmer" '(206 -46) 1 1 0 )
(command "insert" "Commmer" '(203 -47) 1 1 0 )
(command "insert" "Commmer" '(198 -47) 1 1 0 )
(command "insert" "Commmer" '(208 -50) 1 1 0 )
(command "insert" "Commmer" '(199 -46) 1 1 0 )
(command "insert" "Commmer" '(200 -45) 1 1 0 )
(command "insert" "Commmer" '(205 -45) 1 1 0 )
(command "insert" "Commmer" '(195 -45) 1 1 0 )
(command "insert" "Commmer" '(196 -46) 1 1 0 )
(command "insert" "Commmer" '(202 -47) 1 1 0 )
(command "insert" "Commmer" '(197 -47) 1 1 0 )
(command "insert" "Commmer" '(206 -47) 1 1 0 )
(command "insert" "Commmer" '(203 -46) 1 1 0 )
(command "insert" "Commmer" '(207 -49) 1 1 0 )
(command "layer" "m" "alley" "" )
(command "insert" "alley" '(101 -41) 1 1 0 )
(command "insert" "alley" '(100 -39) 1 1 0 )
(command "insert" "alley" '(100 -40) 1 1 0 )
(command "insert" "alley" '(98 -42) 1 1 0 )
(command "insert" "alley" '(99 -41) 1 1 0 )
(command "insert" "alley" '(98 -44) 1 1 0 )
(command "insert" "alley" '(99 -39) 1 1 0 )
(command "insert" "alley" '(96 -44) 1 1 0 )
(command "insert" "alley" '(101 -40) 1 1 0 )
(command "insert" "alley" '(97 -43) 1 1 0 )
(command "insert" "alley" '(100 -41) 1 1 0 )
(command "insert" "alley" '(97 -44) 1 1 0 )
(command "insert" "alley" '(101 -39) 1 1 0 )
(command "insert" "alley" '(98 -43) 1 1 0 )
(command "insert" "alley" '(99 -40) 1 1 0 )
(command "insert" "alley" '(96 -43) 1 1 0 )
(command "insert" "alley" '(97 -42) 1 1 0 )
(command "insert" "alley" '(96 -42) 1 1 0 )
(command "layer" "m" "ped" "" )
(command "insert" "ped" '(80 -11) 1 1 0 )
(command "insert" "ped" '(78 -10) 1 1 0 )
(command "insert" "ped" '(81 -10) 1 1 0 )
(command "insert" "ped" '(72 -11) 1 1 0 )
(command "insert" "ped" '(75 -9) 1 1 0 )
(command "insert" "ped" '(79 -10) 1 1 0 )
(command "insert" "ped" '(73 -10) 1 1 0 )
(command "insert" "ped" '(76 -11) 1 1 0 )
(command "insert" "ped" '(77 -10) 1 1 0 )
(command "insert" "ped" '(82 -10) 1 1 0 )
(command "insert" "ped" '(78 -11) 1 1 0 )
(command "insert" "ped" '(83 -9) 1 1 0 )
(command "insert" "ped" '(81 -9) 1 1 0 )
(command "insert" "ped" '(74 -10) 1 1 0 )
(command "insert" "ped" '(73 -9) 1 1 0 )
(command "insert" "ped" '(79 -9) 1 1 0 )
(command "insert" "ped" '(77 -9) 1 1 0 )
(command "insert" "ped" '(82 -11) 1 1 0 )
(command "insert" "ped" '(74 -11) 1 1 0 )
(command "insert" "ped" '(75 -11) 1 1 0 )
(command "insert" "ped" '(80 -9) 1 1 0 )
(command "insert" "ped" '(72 -9) 1 1 0 )
(command "insert" "ped" '(78 -9) 1 1 0 )
(command "insert" "ped" '(76 -9) 1 1 0 )
(command "insert" "ped" '(83 -11) 1 1 0 )
(command "insert" "ped" '(75 -10) 1 1 0 )
(command "insert" "ped" '(80 -10) 1 1 0 )
(command "insert" "ped" '(81 -11) 1 1 0 )
(command "insert" "ped" '(72 -10) 1 1 0 )
(command "insert" "ped" '(79 -11) 1 1 0 )
(command "insert" "ped" '(73 -11) 1 1 0 )
(command "insert" "ped" '(82 -9) 1 1 0 )
(command "insert" "ped" '(76 -10) 1 1 0 )
(command "insert" "ped" '(83 -10) 1 1 0 )
(command "insert" "ped" '(74 -9) 1 1 0 )
(command "insert" "ped" '(77 -11) 1 1 0 )
(command "layer" "m" "edge" "" )
(command "insert" "edge" '(2 -39) 1 1 0 )
(command "insert" "edge" '(1 -44) 1 1 0 )
(command "insert" "edge" '(2 -43) 1 1 0 )
(command "insert" "edge" '(1 -46) 1 1 0 )
(command "insert" "edge" '(2 -47) 1 1 0 )
(command "insert" "edge" '(2 -45) 1 1 0 )
(command "insert" "edge" '(1 -39) 1 1 0 )
(command "insert" "edge" '(1 -42) 1 1 0 )
(command "insert" "edge" '(1 -47) 1 1 0 )
(command "insert" "edge" '(2 -46) 1 1 0 )
(command "insert" "edge" '(2 -41) 1 1 0 )
(command "insert" "edge" '(2 -40) 1 1 0 )
(command "insert" "edge" '(1 -40) 1 1 0 )
(command "insert" "edge" '(2 -42) 1 1 0 )
(command "insert" "edge" '(1 -41) 1 1 0 )
(command "insert" "edge" '(1 -45) 1 1 0 )
(command "insert" "edge" '(1 -43) 1 1 0 )
(command "insert" "edge" '(2 -44) 1 1 0 )
(command "layer" "m" "Res" "" )
(command "insert" "Res" '(286 -59) 1 1 0 )
(command "insert" "Res" '(286 -58) 1 1 0 )
(command "insert" "Res" '(287 -58) 1 1 0 )
(command "insert" "Res" '(287 -59) 1 1 0 )
(command "insert" "Res" '(287 -57) 1 1 0 )
(command "insert" "Res" '(285 -57) 1 1 0 )
(command "insert" "Res" '(286 -57) 1 1 0 )
(command "insert" "Res" '(285 -58) 1 1 0 )
(command "insert" "Res" '(285 -59) 1 1 0 )
(command "layer" "m" "ped" "" )
(command "insert" "ped" '(288 -54) 1 1 0 )
(command "insert" "ped" '(289 -56) 1 1 0 )
(command "insert" "ped" '(292 -60) 1 1 0 )
(command "insert" "ped" '(289 -55) 1 1 0 )
(command "insert" "ped" '(288 -57) 1 1 0 )
(command "insert" "ped" '(291 -62) 1 1 0 )
(command "insert" "ped" '(292 -57) 1 1 0 )
(command "insert" "ped" '(290 -56) 1 1 0 )
(command "insert" "ped" '(293 -60) 1 1 0 )
(command "insert" "ped" '(291 -58) 1 1 0 )
(command "insert" "ped" '(288 -55) 1 1 0 )
(command "insert" "ped" '(292 -61) 1 1 0 )
(command "insert" "ped" '(289 -54) 1 1 0 )
(command "insert" "ped" '(288 -58) 1 1 0 )
(command "insert" "ped" '(289 -59) 1 1 0 )
(command "insert" "ped" '(292 -58) 1 1 0 )
(command "insert" "ped" '(290 -57) 1 1 0 )
(command "insert" "ped" '(293 -59) 1 1 0 )
(command "insert" "ped" '(292 -62) 1 1 0 )
(command "insert" "ped" '(288 -59) 1 1 0 )
(command "insert" "ped" '(291 -57) 1 1 0 )
(command "insert" "ped" '(289 -58) 1 1 0 )
(command "insert" "ped" '(291 -61) 1 1 0 )
(command "insert" "ped" '(292 -59) 1 1 0 )
(command "insert" "ped" '(290 -54) 1 1 0 )
(command "insert" "ped" '(291 -60) 1 1 0 )
(command "insert" "ped" '(290 -58) 1 1 0 )
(command "insert" "ped" '(293 -62) 1 1 0 )
(command "insert" "ped" '(289 -57) 1 1 0 )
(command "insert" "ped" '(288 -56) 1 1 0 )
(command "insert" "ped" '(291 -59) 1 1 0 )
(command "insert" "ped" '(290 -55) 1 1 0 )
(command "insert" "ped" '(293 -57) 1 1 0 )
(command "insert" "ped" '(293 -58) 1 1 0 )
(command "insert" "ped" '(290 -59) 1 1 0 )
(command "insert" "ped" '(293 -61) 1 1 0 )
(command "layer" "m" "Center" "" )
(command "insert" "Center" '(244 -45) 1 1 0 )
(command "insert" "Center" '(250 -46) 1 1 0 )
(command "insert" "Center" '(247 -42) 1 1 0 )
(command "insert" "Center" '(251 -47) 1 1 0 )
(command "insert" "Center" '(240 -44) 1 1 0 )
(command "insert" "Center" '(245 -43) 1 1 0 )
(command "insert" "Center" '(246 -47) 1 1 0 )
(command "insert" "Center" '(244 -42) 1 1 0 )
(command "insert" "Center" '(247 -46) 1 1 0 )
(command "insert" "Center" '(248 -45) 1 1 0 )
(command "insert" "Center" '(243 -45) 1 1 0 )
(command "insert" "Center" '(246 -43) 1 1 0 )
(command "insert" "Center" '(244 -46) 1 1 0 )
(command "insert" "Center" '(242 -42) 1 1 0 )
(command "insert" "Center" '(250 -47) 1 1 0 )
(command "insert" "Center" '(245 -47) 1 1 0 )
(command "insert" "Center" '(242 -44) 1 1 0 )
(command "insert" "Center" '(251 -46) 1 1 0 )
(command "insert" "Center" '(246 -44) 1 1 0 )
(command "insert" "Center" '(241 -43) 1 1 0 )
(command "insert" "Center" '(244 -43) 1 1 0 )
(command "insert" "Center" '(243 -43) 1 1 0 )
(command "insert" "Center" '(248 -46) 1 1 0 )
(command "insert" "Center" '(243 -44) 1 1 0 )
(command "insert" "Center" '(249 -47) 1 1 0 )
(command "insert" "Center" '(245 -42) 1 1 0 )
(command "insert" "Center" '(244 -47) 1 1 0 )
(command "insert" "Center" '(247 -45) 1 1 0 )
(command "insert" "Center" '(248 -42) 1 1 0 )
(command "insert" "Center" '(245 -46) 1 1 0 )
(command "insert" "Center" '(240 -43) 1 1 0 )
(command "insert" "Center" '(246 -45) 1 1 0 )
(command "insert" "Center" '(241 -42) 1 1 0 )
(command "insert" "Center" '(248 -47) 1 1 0 )
(command "insert" "Center" '(251 -45) 1 1 0 )
(command "insert" "Center" '(243 -47) 1 1 0 )
(command "insert" "Center" '(249 -46) 1 1 0 )
(command "insert" "Center" '(247 -44) 1 1 0 )
(command "insert" "Center" '(248 -43) 1 1 0 )
(command "insert" "Center" '(245 -45) 1 1 0 )
(command "insert" "Center" '(240 -42) 1 1 0 )
(command "insert" "Center" '(244 -44) 1 1 0 )
(command "insert" "Center" '(247 -43) 1 1 0 )
(command "insert" "Center" '(250 -45) 1 1 0 )
(command "insert" "Center" '(243 -46) 1 1 0 )
(command "insert" "Center" '(246 -46) 1 1 0 )
(command "insert" "Center" '(249 -45) 1 1 0 )
(command "insert" "Center" '(247 -47) 1 1 0 )
(command "insert" "Center" '(241 -44) 1 1 0 )
(command "insert" "Center" '(248 -44) 1 1 0 )
(command "insert" "Center" '(243 -42) 1 1 0 )
(command "insert" "Center" '(246 -42) 1 1 0 )
(command "insert" "Center" '(242 -43) 1 1 0 )
(command "insert" "Center" '(245 -44) 1 1 0 )
(command "layer" "m" "Res" "" )
(command "insert" "Res" '(13 -33) 1 1 0 )
(command "insert" "Res" '(13 -35) 1 1 0 )
(command "insert" "Res" '(9 -34) 1 1 0 )
(command "insert" "Res" '(11 -35) 1 1 0 )
(command "insert" "Res" '(14 -33) 1 1 0 )
(command "insert" "Res" '(11 -33) 1 1 0 )
(command "insert" "Res" '(14 -35) 1 1 0 )
(command "insert" "Res" '(13 -34) 1 1 0 )
(command "insert" "Res" '(12 -35) 1 1 0 )
(command "insert" "Res" '(10 -34) 1 1 0 )
(command "insert" "Res" '(12 -33) 1 1 0 )
(command "insert" "Res" '(9 -33) 1 1 0 )
(command "insert" "Res" '(11 -34) 1 1 0 )
(command "insert" "Res" '(9 -35) 1 1 0 )
(command "insert" "Res" '(10 -33) 1 1 0 )
(command "insert" "Res" '(12 -34) 1 1 0 )
(command "insert" "Res" '(14 -34) 1 1 0 )
(command "insert" "Res" '(10 -35) 1 1 0 )
(command "layer" "m" "ped" "" )
(command "insert" "ped" '(1 -3) 1 1 0 )
(command "insert" "ped" '(2 -18) 1 1 0 )
(command "insert" "ped" '(2 -8) 1 1 0 )
(command "insert" "ped" '(1 -17) 1 1 0 )
(command "insert" "ped" '(2 -1) 1 1 0 )
(command "insert" "ped" '(1 -15) 1 1 0 )
(command "insert" "ped" '(6 -2) 1 1 0 )
(command "insert" "ped" '(1 -6) 1 1 0 )
(command "insert" "ped" '(2 -12) 1 1 0 )
(command "insert" "ped" '(5 -1) 1 1 0 )
(command "insert" "ped" '(2 -5) 1 1 0 )
(command "insert" "ped" '(1 -11) 1 1 0 )
(command "insert" "ped" '(1 -20) 1 1 0 )
(command "insert" "ped" '(1 -2) 1 1 0 )
(command "insert" "ped" '(2 -19) 1 1 0 )
(command "insert" "ped" '(2 -9) 1 1 0 )
(command "insert" "ped" '(8 -1) 1 1 0 )
(command "insert" "ped" '(1 -16) 1 1 0 )
(command "insert" "ped" '(1 -14) 1 1 0 )
(command "insert" "ped" '(1 -5) 1 1 0 )
(command "insert" "ped" '(2 -13) 1 1 0 )
(command "insert" "ped" '(7 -2) 1 1 0 )
(command "insert" "ped" '(2 -2) 1 1 0 )
(command "insert" "ped" '(1 -10) 1 1 0 )
(command "insert" "ped" '(4 -1) 1 1 0 )
(command "insert" "ped" '(1 -1) 1 1 0 )
(command "insert" "ped" '(2 -16) 1 1 0 )
(command "insert" "ped" '(3 -2) 1 1 0 )
(command "insert" "ped" '(2 -6) 1 1 0 )
(command "insert" "ped" '(8 -2) 1 1 0 )
(command "insert" "ped" '(7 -1) 1 1 0 )
(command "insert" "ped" '(1 -13) 1 1 0 )
(command "insert" "ped" '(2 -20) 1 1 0 )
(command "insert" "ped" '(1 -4) 1 1 0 )
(command "insert" "ped" '(2 -10) 1 1 0 )
(command "insert" "ped" '(1 -19) 1 1 0 )
(command "insert" "ped" '(2 -3) 1 1 0 )
(command "insert" "ped" '(1 -9) 1 1 0 )
(command "insert" "ped" '(4 -2) 1 1 0 )
(command "insert" "ped" '(2 -14) 1 1 0 )
(command "insert" "ped" '(2 -17) 1 1 0 )
(command "insert" "ped" '(2 -7) 1 1 0 )
(command "insert" "ped" '(1 -12) 1 1 0 )
(command "insert" "ped" '(6 -1) 1 1 0 )
(command "insert" "ped" '(3 -1) 1 1 0 )
(command "insert" "ped" '(2 -11) 1 1 0 )
(command "insert" "ped" '(1 -18) 1 1 0 )
(command "insert" "ped" '(1 -8) 1 1 0 )
(command "insert" "ped" '(1 -7) 1 1 0 )
(command "insert" "ped" '(2 -15) 1 1 0 )
(command "insert" "ped" '(5 -2) 1 1 0 )
(command "insert" "ped" '(2 -4) 1 1 0 )
(command "layer" "m" "Commmer" "" )
(command "insert" "Commmer" '(32 -1) 1 1 0 )
(command "insert" "Commmer" '(35 -1) 1 1 0 )
(command "insert" "Commmer" '(21 -2) 1 1 0 )
(command "insert" "Commmer" '(16 -2) 1 1 0 )
(command "insert" "Commmer" '(26 -2) 1 1 0 )
(command "insert" "Commmer" '(28 -1) 1 1 0 )
(command "insert" "Commmer" '(25 -1) 1 1 0 )
(command "insert" "Commmer" '(34 -2) 1 1 0 )
(command "insert" "Commmer" '(27 -2) 1 1 0 )
(command "insert" "Commmer" '(32 -2) 1 1 0 )
(command "insert" "Commmer" '(18 -1) 1 1 0 )
(command "insert" "Commmer" '(31 -1) 1 1 0 )
(command "insert" "Commmer" '(22 -2) 1 1 0 )
(command "insert" "Commmer" '(21 -1) 1 1 0 )
(command "insert" "Commmer" '(23 -2) 1 1 0 )
(command "insert" "Commmer" '(17 -2) 1 1 0 )
(command "insert" "Commmer" '(28 -2) 1 1 0 )
(command "insert" "Commmer" '(34 -1) 1 1 0 )
(command "insert" "Commmer" '(24 -1) 1 1 0 )
(command "insert" "Commmer" '(33 -2) 1 1 0 )
(command "insert" "Commmer" '(30 -1) 1 1 0 )
(command "insert" "Commmer" '(27 -1) 1 1 0 )
(command "insert" "Commmer" '(18 -2) 1 1 0 )
(command "insert" "Commmer" '(20 -1) 1 1 0 )
(command "insert" "Commmer" '(17 -1) 1 1 0 )
(command "insert" "Commmer" '(19 -2) 1 1 0 )
(command "insert" "Commmer" '(29 -2) 1 1 0 )
(command "insert" "Commmer" '(24 -2) 1 1 0 )
(command "insert" "Commmer" '(23 -1) 1 1 0 )
(command "insert" "Commmer" '(15 -1) 1 1 0 )
(command "insert" "Commmer" '(33 -1) 1 1 0 )
(command "insert" "Commmer" '(35 -2) 1 1 0 )
(command "insert" "Commmer" '(26 -1) 1 1 0 )
(command "insert" "Commmer" '(15 -2) 1 1 0 )
(command "insert" "Commmer" '(20 -2) 1 1 0 )
(command "insert" "Commmer" '(30 -2) 1 1 0 )
(command "insert" "Commmer" '(16 -1) 1 1 0 )
(command "insert" "Commmer" '(29 -1) 1 1 0 )
(command "insert" "Commmer" '(31 -2) 1 1 0 )
(command "insert" "Commmer" '(25 -2) 1 1 0 )
(command "insert" "Commmer" '(22 -1) 1 1 0 )
(command "insert" "Commmer" '(19 -1) 1 1 0 )
(command "layer" "m" "Commmer" "" )
(command "insert" "Commmer" '(157 -50) 1 1 0 )
(command "insert" "Commmer" '(158 -53) 1 1 0 )
(command "insert" "Commmer" '(157 -49) 1 1 0 )
(command "insert" "Commmer" '(157 -52) 1 1 0 )
(command "insert" "Commmer" '(156 -53) 1 1 0 )
(command "insert" "Commmer" '(158 -49) 1 1 0 )
(command "insert" "Commmer" '(158 -51) 1 1 0 )
(command "insert" "Commmer" '(156 -49) 1 1 0 )
(command "insert" "Commmer" '(156 -50) 1 1 0 )
(command "insert" "Commmer" '(156 -51) 1 1 0 )
(command "insert" "Commmer" '(156 -48) 1 1 0 )
(command "insert" "Commmer" '(158 -52) 1 1 0 )
(command "insert" "Commmer" '(157 -51) 1 1 0 )
(command "insert" "Commmer" '(157 -53) 1 1 0 )
(command "insert" "Commmer" '(156 -52) 1 1 0 )
(command "insert" "Commmer" '(158 -48) 1 1 0 )
(command "insert" "Commmer" '(158 -50) 1 1 0 )
(command "insert" "Commmer" '(157 -48) 1 1 0 )
(command "layer" "m" "alley" "" )
(command "insert" "alley" '(79 -34) 1 1 0 )
(command "insert" "alley" '(79 -35) 1 1 0 )
(command "insert" "alley" '(80 -35) 1 1 0 )
(command "insert" "alley" '(80 -34) 1 1 0 )
(command "insert" "alley" '(79 -33) 1 1 0 )
(command "insert" "alley" '(80 -33) 1 1 0 )
(command "insert" "alley" '(78 -33) 1 1 0 )
(command "insert" "alley" '(78 -35) 1 1 0 )
(command "insert" "alley" '(78 -34) 1 1 0 )
(command "layer" "m" "alley" "" )
(command "insert" "alley" '(99 -34) 1 1 0 )
(command "insert" "alley" '(99 -35) 1 1 0 )
(command "insert" "alley" '(101 -34) 1 1 0 )
(command "insert" "alley" '(99 -33) 1 1 0 )
(command "insert" "alley" '(100 -35) 1 1 0 )
(command "insert" "alley" '(100 -34) 1 1 0 )
(command "insert" "alley" '(101 -33) 1 1 0 )
(command "insert" "alley" '(100 -33) 1 1 0 )
(command "insert" "alley" '(101 -35) 1 1 0 )
(command "layer" "m" "Commmer" "" )
(command "insert" "Commmer" '(86 -34) 1 1 0 )
(command "insert" "Commmer" '(82 -35) 1 1 0 )
(command "insert" "Commmer" '(90 -33) 1 1 0 )
(command "insert" "Commmer" '(85 -33) 1 1 0 )
(command "insert" "Commmer" '(89 -38) 1 1 0 )
(command "insert" "Commmer" '(87 -34) 1 1 0 )
(command "insert" "Commmer" '(88 -35) 1 1 0 )
(command "insert" "Commmer" '(83 -35) 1 1 0 )
(command "insert" "Commmer" '(89 -34) 1 1 0 )
(command "insert" "Commmer" '(87 -38) 1 1 0 )
(command "insert" "Commmer" '(88 -36) 1 1 0 )
(command "insert" "Commmer" '(91 -35) 1 1 0 )
(command "insert" "Commmer" '(86 -35) 1 1 0 )
(command "insert" "Commmer" '(89 -37) 1 1 0 )
(command "insert" "Commmer" '(84 -33) 1 1 0 )
(command "insert" "Commmer" '(90 -34) 1 1 0 )
(command "insert" "Commmer" '(83 -34) 1 1 0 )
(command "insert" "Commmer" '(81 -35) 1 1 0 )
(command "insert" "Commmer" '(92 -33) 1 1 0 )
(command "insert" "Commmer" '(89 -33) 1 1 0 )
(command "insert" "Commmer" '(87 -33) 1 1 0 )
(command "insert" "Commmer" '(91 -34) 1 1 0 )
(command "insert" "Commmer" '(82 -33) 1 1 0 )
(command "insert" "Commmer" '(87 -37) 1 1 0 )
(command "insert" "Commmer" '(89 -36) 1 1 0 )
(command "insert" "Commmer" '(84 -34) 1 1 0 )
(command "insert" "Commmer" '(88 -37) 1 1 0 )
(command "insert" "Commmer" '(85 -35) 1 1 0 )
(command "insert" "Commmer" '(81 -34) 1 1 0 )
(command "insert" "Commmer" '(92 -34) 1 1 0 )
(command "insert" "Commmer" '(88 -33) 1 1 0 )
(command "insert" "Commmer" '(86 -33) 1 1 0 )
(command "insert" "Commmer" '(83 -33) 1 1 0 )
(command "insert" "Commmer" '(87 -36) 1 1 0 )
(command "insert" "Commmer" '(91 -33) 1 1 0 )
(command "insert" "Commmer" '(84 -35) 1 1 0 )
(command "insert" "Commmer" '(82 -34) 1 1 0 )
(command "insert" "Commmer" '(88 -38) 1 1 0 )
(command "insert" "Commmer" '(90 -35) 1 1 0 )
(command "insert" "Commmer" '(81 -33) 1 1 0 )
(command "insert" "Commmer" '(92 -35) 1 1 0 )
(command "insert" "Commmer" '(87 -35) 1 1 0 )
(command "insert" "Commmer" '(88 -34) 1 1 0 )
(command "insert" "Commmer" '(85 -34) 1 1 0 )
(command "insert" "Commmer" '(89 -35) 1 1 0 )
(command "layer" "m" "Commmer" "" )
(command "insert" "Commmer" '(256 -86) 1 1 0 )
(command "insert" "Commmer" '(254 -79) 1 1 0 )
(command "insert" "Commmer" '(255 -82) 1 1 0 )
(command "insert" "Commmer" '(256 -84) 1 1 0 )
(command "insert" "Commmer" '(256 -82) 1 1 0 )
(command "insert" "Commmer" '(257 -81) 1 1 0 )
(command "insert" "Commmer" '(253 -78) 1 1 0 )
(command "insert" "Commmer" '(255 -86) 1 1 0 )
(command "insert" "Commmer" '(257 -83) 1 1 0 )
(command "insert" "Commmer" '(255 -84) 1 1 0 )
(command "insert" "Commmer" '(257 -86) 1 1 0 )
(command "insert" "Commmer" '(257 -85) 1 1 0 )
(command "insert" "Commmer" '(257 -84) 1 1 0 )
(command "insert" "Commmer" '(256 -81) 1 1 0 )
(command "insert" "Commmer" '(253 -79) 1 1 0 )
(command "insert" "Commmer" '(256 -85) 1 1 0 )
(command "insert" "Commmer" '(254 -78) 1 1 0 )
(command "insert" "Commmer" '(255 -83) 1 1 0 )
(command "insert" "Commmer" '(256 -83) 1 1 0 )
(command "insert" "Commmer" '(252 -80) 1 1 0 )
(command "insert" "Commmer" '(252 -79) 1 1 0 )
(command "insert" "Commmer" '(255 -81) 1 1 0 )
(command "insert" "Commmer" '(257 -82) 1 1 0 )
(command "insert" "Commmer" '(254 -80) 1 1 0 )
(command "insert" "Commmer" '(255 -85) 1 1 0 )
(command "insert" "Commmer" '(253 -80) 1 1 0 )
(command "insert" "Commmer" '(252 -78) 1 1 0 )
(command "layer" "m" "Res" "" )
(command "insert" "Res" '(154 -24) 1 1 0 )
(command "insert" "Res" '(155 -26) 1 1 0 )
(command "insert" "Res" '(158 -26) 1 1 0 )
(command "insert" "Res" '(150 -24) 1 1 0 )
(command "insert" "Res" '(154 -26) 1 1 0 )
(command "insert" "Res" '(155 -24) 1 1 0 )
(command "insert" "Res" '(150 -26) 1 1 0 )
(command "insert" "Res" '(152 -26) 1 1 0 )
(command "insert" "Res" '(153 -25) 1 1 0 )
(command "insert" "Res" '(152 -24) 1 1 0 )
(command "insert" "Res" '(151 -26) 1 1 0 )
(command "insert" "Res" '(156 -26) 1 1 0 )
(command "insert" "Res" '(157 -25) 1 1 0 )
(command "insert" "Res" '(158 -25) 1 1 0 )
(command "insert" "Res" '(151 -24) 1 1 0 )
(command "insert" "Res" '(154 -25) 1 1 0 )
(command "insert" "Res" '(156 -24) 1 1 0 )
(command "insert" "Res" '(153 -26) 1 1 0 )
(command "insert" "Res" '(150 -25) 1 1 0 )
(command "insert" "Res" '(156 -25) 1 1 0 )
(command "insert" "Res" '(153 -24) 1 1 0 )
(command "insert" "Res" '(155 -25) 1 1 0 )
(command "insert" "Res" '(152 -25) 1 1 0 )
(command "insert" "Res" '(157 -24) 1 1 0 )
(command "insert" "Res" '(157 -26) 1 1 0 )
(command "insert" "Res" '(158 -24) 1 1 0 )
(command "insert" "Res" '(151 -25) 1 1 0 )
(command "layer" "m" "Commmer" "" )
(command "insert" "Commmer" '(30 -26) 1 1 0 )
(command "insert" "Commmer" '(32 -26) 1 1 0 )
(command "insert" "Commmer" '(27 -21) 1 1 0 )
(command "insert" "Commmer" '(28 -22) 1 1 0 )
(command "insert" "Commmer" '(31 -26) 1 1 0 )
(command "insert" "Commmer" '(30 -22) 1 1 0 )
(command "insert" "Commmer" '(29 -23) 1 1 0 )
(command "insert" "Commmer" '(31 -23) 1 1 0 )
(command "insert" "Commmer" '(30 -27) 1 1 0 )
(command "insert" "Commmer" '(32 -27) 1 1 0 )
(command "insert" "Commmer" '(28 -23) 1 1 0 )
(command "insert" "Commmer" '(30 -23) 1 1 0 )
(command "insert" "Commmer" '(29 -22) 1 1 0 )
(command "insert" "Commmer" '(30 -28) 1 1 0 )
(command "insert" "Commmer" '(31 -22) 1 1 0 )
(command "insert" "Commmer" '(31 -25) 1 1 0 )
(command "insert" "Commmer" '(30 -24) 1 1 0 )
(command "insert" "Commmer" '(32 -28) 1 1 0 )
(command "insert" "Commmer" '(27 -23) 1 1 0 )
(command "insert" "Commmer" '(31 -29) 1 1 0 )
(command "insert" "Commmer" '(32 -21) 1 1 0 )
(command "insert" "Commmer" '(32 -24) 1 1 0 )
(command "insert" "Commmer" '(29 -21) 1 1 0 )
(command "insert" "Commmer" '(30 -29) 1 1 0 )
(command "insert" "Commmer" '(31 -24) 1 1 0 )
(command "insert" "Commmer" '(30 -25) 1 1 0 )
(command "insert" "Commmer" '(31 -21) 1 1 0 )
(command "insert" "Commmer" '(32 -29) 1 1 0 )
(command "insert" "Commmer" '(27 -22) 1 1 0 )
(command "insert" "Commmer" '(31 -28) 1 1 0 )
(command "insert" "Commmer" '(32 -22) 1 1 0 )
(command "insert" "Commmer" '(30 -21) 1 1 0 )
(command "insert" "Commmer" '(32 -25) 1 1 0 )
(command "insert" "Commmer" '(28 -21) 1 1 0 )
(command "insert" "Commmer" '(31 -27) 1 1 0 )
(command "insert" "Commmer" '(32 -23) 1 1 0 )
(command "layer" "m" "Commmer" "" )
(command "insert" "Commmer" '(272 -49) 1 1 0 )
(command "insert" "Commmer" '(277 -57) 1 1 0 )
(command "insert" "Commmer" '(276 -55) 1 1 0 )
(command "insert" "Commmer" '(276 -52) 1 1 0 )
(command "insert" "Commmer" '(276 -56) 1 1 0 )
(command "insert" "Commmer" '(277 -54) 1 1 0 )
(command "insert" "Commmer" '(270 -50) 1 1 0 )
(command "insert" "Commmer" '(278 -57) 1 1 0 )
(command "insert" "Commmer" '(271 -50) 1 1 0 )
(command "insert" "Commmer" '(274 -52) 1 1 0 )
(command "insert" "Commmer" '(277 -56) 1 1 0 )
(command "insert" "Commmer" '(273 -51) 1 1 0 )
(command "insert" "Commmer" '(276 -57) 1 1 0 )
(command "insert" "Commmer" '(277 -53) 1 1 0 )
(command "insert" "Commmer" '(278 -58) 1 1 0 )
(command "insert" "Commmer" '(272 -50) 1 1 0 )
(command "insert" "Commmer" '(278 -51) 1 1 0 )
(command "insert" "Commmer" '(276 -53) 1 1 0 )
(command "insert" "Commmer" '(278 -53) 1 1 0 )
(command "insert" "Commmer" '(274 -53) 1 1 0 )
(command "insert" "Commmer" '(277 -51) 1 1 0 )
(command "insert" "Commmer" '(271 -49) 1 1 0 )
(command "insert" "Commmer" '(276 -58) 1 1 0 )
(command "insert" "Commmer" '(277 -52) 1 1 0 )
(command "insert" "Commmer" '(270 -48) 1 1 0 )
(command "insert" "Commmer" '(277 -59) 1 1 0 )
(command "insert" "Commmer" '(278 -59) 1 1 0 )
(command "insert" "Commmer" '(273 -53) 1 1 0 )
(command "insert" "Commmer" '(278 -55) 1 1 0 )
(command "insert" "Commmer" '(271 -48) 1 1 0 )
(command "insert" "Commmer" '(276 -59) 1 1 0 )
(command "insert" "Commmer" '(275 -53) 1 1 0 )
(command "insert" "Commmer" '(270 -49) 1 1 0 )
(command "insert" "Commmer" '(272 -48) 1 1 0 )
(command "insert" "Commmer" '(277 -58) 1 1 0 )
(command "insert" "Commmer" '(276 -54) 1 1 0 )
(command "insert" "Commmer" '(278 -54) 1 1 0 )
(command "insert" "Commmer" '(277 -55) 1 1 0 )
(command "insert" "Commmer" '(275 -51) 1 1 0 )
(command "insert" "Commmer" '(273 -52) 1 1 0 )
(command "insert" "Commmer" '(278 -56) 1 1 0 )
(command "insert" "Commmer" '(278 -52) 1 1 0 )
(command "insert" "Commmer" '(274 -51) 1 1 0 )
(command "insert" "Commmer" '(276 -51) 1 1 0 )
(command "insert" "Commmer" '(275 -52) 1 1 0 )
(command "layer" "m" "Res" "" )
(command "insert" "Res" '(142 -39) 1 1 0 )
(command "insert" "Res" '(141 -39) 1 1 0 )
(command "insert" "Res" '(143 -40) 1 1 0 )
(command "insert" "Res" '(143 -39) 1 1 0 )
(command "insert" "Res" '(141 -40) 1 1 0 )
(command "insert" "Res" '(143 -41) 1 1 0 )
(command "insert" "Res" '(141 -41) 1 1 0 )
(command "insert" "Res" '(142 -41) 1 1 0 )
(command "insert" "Res" '(142 -40) 1 1 0 )
(command "layer" "m" "Commmer" "" )
(command "insert" "Commmer" '(297 -90) 1 1 0 )
(command "insert" "Commmer" '(297 -91) 1 1 0 )
(command "insert" "Commmer" '(299 -92) 1 1 0 )
(command "insert" "Commmer" '(297 -92) 1 1 0 )
(command "insert" "Commmer" '(299 -90) 1 1 0 )
(command "insert" "Commmer" '(298 -91) 1 1 0 )
(command "insert" "Commmer" '(299 -91) 1 1 0 )
(command "insert" "Commmer" '(298 -90) 1 1 0 )
(command "insert" "Commmer" '(298 -92) 1 1 0 )
(command "layer" "m" "Res" "" )
(command "insert" "Res" '(167 -46) 1 1 0 )
(command "insert" "Res" '(167 -47) 1 1 0 )
(command "insert" "Res" '(167 -45) 1 1 0 )
(command "insert" "Res" '(165 -45) 1 1 0 )
(command "insert" "Res" '(165 -46) 1 1 0 )
(command "insert" "Res" '(165 -47) 1 1 0 )
(command "insert" "Res" '(166 -45) 1 1 0 )
(command "insert" "Res" '(166 -47) 1 1 0 )
(command "insert" "Res" '(166 -46) 1 1 0 )
(command "layer" "m" "alley" "" )
(command "insert" "alley" '(4 -42) 1 1 0 )
(command "insert" "alley" '(3 -44) 1 1 0 )
(command "insert" "alley" '(5 -43) 1 1 0 )
(command "insert" "alley" '(5 -44) 1 1 0 )
(command "insert" "alley" '(3 -43) 1 1 0 )
(command "insert" "alley" '(4 -44) 1 1 0 )
(command "insert" "alley" '(5 -42) 1 1 0 )
(command "insert" "alley" '(3 -42) 1 1 0 )
(command "insert" "alley" '(4 -43) 1 1 0 )
(command "layer" "m" "Res" "" )
(command "insert" "Res" '(268 -98) 1 1 0 )
(command "insert" "Res" '(268 -97) 1 1 0 )
(command "insert" "Res" '(269 -97) 1 1 0 )
(command "insert" "Res" '(267 -98) 1 1 0 )
(command "insert" "Res" '(268 -96) 1 1 0 )
(command "insert" "Res" '(267 -96) 1 1 0 )
(command "insert" "Res" '(267 -97) 1 1 0 )
(command "insert" "Res" '(269 -98) 1 1 0 )
(command "insert" "Res" '(269 -96) 1 1 0 )
(command "layer" "m" "ped" "" )
(command "insert" "ped" '(1 -3) 1 1 0 )
(command "insert" "ped" '(2 -18) 1 1 0 )
(command "insert" "ped" '(2 -8) 1 1 0 )
(command "insert" "ped" '(1 -17) 1 1 0 )
(command "insert" "ped" '(2 -1) 1 1 0 )
(command "insert" "ped" '(1 -15) 1 1 0 )
(command "insert" "ped" '(6 -2) 1 1 0 )
(command "insert" "ped" '(1 -6) 1 1 0 )
(command "insert" "ped" '(2 -12) 1 1 0 )
(command "insert" "ped" '(5 -1) 1 1 0 )
(command "insert" "ped" '(2 -5) 1 1 0 )
(command "insert" "ped" '(1 -11) 1 1 0 )
(command "insert" "ped" '(7 -2) 1 1 0 )
(command "insert" "ped" '(1 -2) 1 1 0 )
(command "insert" "ped" '(2 -19) 1 1 0 )
(command "insert" "ped" '(2 -9) 1 1 0 )
(command "insert" "ped" '(8 -1) 1 1 0 )
(command "insert" "ped" '(1 -16) 1 1 0 )
(command "insert" "ped" '(1 -14) 1 1 0 )
(command "insert" "ped" '(1 -5) 1 1 0 )
(command "insert" "ped" '(2 -13) 1 1 0 )
(command "insert" "ped" '(1 -20) 1 1 0 )
(command "insert" "ped" '(2 -2) 1 1 0 )
(command "insert" "ped" '(1 -10) 1 1 0 )
(command "insert" "ped" '(4 -1) 1 1 0 )
(command "insert" "ped" '(1 -1) 1 1 0 )
(command "insert" "ped" '(2 -16) 1 1 0 )
(command "insert" "ped" '(3 -2) 1 1 0 )
(command "insert" "ped" '(2 -6) 1 1 0 )
(command "insert" "ped" '(8 -2) 1 1 0 )
(command "insert" "ped" '(7 -1) 1 1 0 )
(command "insert" "ped" '(1 -13) 1 1 0 )
(command "insert" "ped" '(2 -20) 1 1 0 )
(command "insert" "ped" '(1 -4) 1 1 0 )
(command "insert" "ped" '(2 -10) 1 1 0 )
(command "insert" "ped" '(1 -19) 1 1 0 )
(command "insert" "ped" '(2 -3) 1 1 0 )
(command "insert" "ped" '(1 -9) 1 1 0 )
(command "insert" "ped" '(4 -2) 1 1 0 )
(command "insert" "ped" '(2 -14) 1 1 0 )
(command "insert" "ped" '(2 -17) 1 1 0 )
(command "insert" "ped" '(2 -7) 1 1 0 )
(command "insert" "ped" '(1 -12) 1 1 0 )
(command "insert" "ped" '(6 -1) 1 1 0 )
(command "insert" "ped" '(3 -1) 1 1 0 )
(command "insert" "ped" '(2 -11) 1 1 0 )
(command "insert" "ped" '(1 -18) 1 1 0 )
(command "insert" "ped" '(1 -8) 1 1 0 )
(command "insert" "ped" '(1 -7) 1 1 0 )
(command "insert" "ped" '(2 -15) 1 1 0 )
(command "insert" "ped" '(5 -2) 1 1 0 )
(command "insert" "ped" '(2 -4) 1 1 0 )
(command "layer" "m" "Res" "" )
(command "insert" "Res" '(13 -1) 1 1 0 )
(command "insert" "Res" '(13 -2) 1 1 0 )
(command "insert" "Res" '(9 -1) 1 1 0 )
(command "insert" "Res" '(12 -2) 1 1 0 )
(command "insert" "Res" '(9 -2) 1 1 0 )
(command "insert" "Res" '(11 -2) 1 1 0 )
(command "insert" "Res" '(14 -1) 1 1 0 )
(command "insert" "Res" '(11 -1) 1 1 0 )
(command "insert" "Res" '(10 -1) 1 1 0 )
(command "insert" "Res" '(12 -1) 1 1 0 )
(command "insert" "Res" '(14 -2) 1 1 0 )
(command "insert" "Res" '(10 -2) 1 1 0 )
(command "layer" "m" "ped" "" )
(command "insert" "ped" '(26 -21) 1 1 0 )
(command "insert" "ped" '(18 -22) 1 1 0 )
(command "insert" "ped" '(22 -23) 1 1 0 )
(command "insert" "ped" '(21 -21) 1 1 0 )
(command "insert" "ped" '(26 -23) 1 1 0 )
(command "insert" "ped" '(23 -22) 1 1 0 )
(command "insert" "ped" '(21 -23) 1 1 0 )
(command "insert" "ped" '(19 -22) 1 1 0 )
(command "insert" "ped" '(25 -21) 1 1 0 )
(command "insert" "ped" '(24 -22) 1 1 0 )
(command "insert" "ped" '(18 -21) 1 1 0 )
(command "insert" "ped" '(20 -22) 1 1 0 )
(command "insert" "ped" '(18 -23) 1 1 0 )
(command "insert" "ped" '(20 -23) 1 1 0 )
(command "insert" "ped" '(22 -22) 1 1 0 )
(command "insert" "ped" '(21 -22) 1 1 0 )
(command "insert" "ped" '(24 -21) 1 1 0 )
(command "insert" "ped" '(26 -22) 1 1 0 )
(command "insert" "ped" '(23 -23) 1 1 0 )
(command "insert" "ped" '(20 -21) 1 1 0 )
(command "insert" "ped" '(23 -21) 1 1 0 )
(command "insert" "ped" '(24 -23) 1 1 0 )
(command "insert" "ped" '(19 -23) 1 1 0 )
(command "insert" "ped" '(25 -23) 1 1 0 )
(command "insert" "ped" '(25 -22) 1 1 0 )
(command "insert" "ped" '(22 -21) 1 1 0 )
(command "insert" "ped" '(19 -21) 1 1 0 )
(command "layer" "m" "mroads" "" )
(command "insert" "mroads" '(5 -31) 1 1 0 )
(command "insert" "mroads" '(66 -31) 1 1 0 )
(command "insert" "mroads" '(6 -28) 1 1 0 )
(command "insert" "mroads" '(67 -30) 1 1 0 )
(command "insert" "mroads" '(7 -25) 1 1 0 )
(command "insert" "mroads" '(22 -19) 1 1 0 )
(command "insert" "mroads" '(18 -19) 1 1 0 )
(command "insert" "mroads" '(38 -21) 1 1 0 )
(command "insert" "mroads" '(114 -31) 1 1 0 )
(command "insert" "mroads" '(13 -32) 1 1 0 )
(command "insert" "mroads" '(35 -15) 1 1 0 )
(command "insert" "mroads" '(14 -31) 1 1 0 )
(command "insert" "mroads" '(15 -30) 1 1 0 )
(command "insert" "mroads" '(35 -21) 1 1 0 )
(command "insert" "mroads" '(12 -17) 1 1 0 )
(command "insert" "mroads" '(36 -22) 1 1 0 )
(command "insert" "mroads" '(1 -28) 1 1 0 )
(command "insert" "mroads" '(25 -15) 1 1 0 )
(command "insert" "mroads" '(39 -16) 1 1 0 )
(command "insert" "mroads" '(63 -30) 1 1 0 )
(command "insert" "mroads" '(37 -23) 1 1 0 )
(command "insert" "mroads" '(2 -27) 1 1 0 )
(command "insert" "mroads" '(109 -32) 1 1 0 )
(command "insert" "mroads" '(29 -17) 1 1 0 )
(command "insert" "mroads" '(31 -15) 1 1 0 )
(command "insert" "mroads" '(5 -24) 1 1 0 )
(command "insert" "mroads" '(20 -32) 1 1 0 )
(command "insert" "mroads" '(6 -23) 1 1 0 )
(command "insert" "mroads" '(30 -16) 1 1 0 )
(command "insert" "mroads" '(28 -32) 1 1 0 )
(command "insert" "mroads" '(7 -22) 1 1 0 )
(command "insert" "mroads" '(41 -23) 1 1 0 )
(command "insert" "mroads" '(42 -31) 1 1 0 )
(command "insert" "mroads" '(23 -19) 1 1 0 )
(command "insert" "mroads" '(21 -15) 1 1 0 )
(command "insert" "mroads" '(43 -30) 1 1 0 )
(command "insert" "mroads" '(116 -32) 1 1 0 )
(command "insert" "mroads" '(8 -18) 1 1 0 )
(command "insert" "mroads" '(11 -15) 1 1 0 )
(command "insert" "mroads" '(35 -26) 1 1 0 )
(command "insert" "mroads" '(9 -19) 1 1 0 )
(command "insert" "mroads" '(36 -29) 1 1 0 )
(command "insert" "mroads" '(1 -21) 1 1 0 )
(command "insert" "mroads" '(25 -16) 1 1 0 )
(command "insert" "mroads" '(29 -20) 1 1 0 )
(command "insert" "mroads" '(37 -16) 1 1 0 )
(command "insert" "mroads" '(98 -30) 1 1 0 )
(command "insert" "mroads" '(38 -31) 1 1 0 )
(command "insert" "mroads" '(99 -31) 1 1 0 )
(command "insert" "mroads" '(39 -30) 1 1 0 )
(command "insert" "mroads" '(3 -17) 1 1 0 )
(command "insert" "mroads" '(19 -18) 1 1 0 )
(command "insert" "mroads" '(7 -15) 1 1 0 )
(command "insert" "mroads" '(31 -18) 1 1 0 )
(command "insert" "mroads" '(46 -30) 1 1 0 )
(command "insert" "mroads" '(6 -32) 1 1 0 )
(command "insert" "mroads" '(34 -32) 1 1 0 )
(command "insert" "mroads" '(32 -16) 1 1 0 )
(command "insert" "mroads" '(94 -30) 1 1 0 )
(command "insert" "mroads" '(18 -31) 1 1 0 )
(command "insert" "mroads" '(42 -32) 1 1 0 )
(command "insert" "mroads" '(86 -32) 1 1 0 )
(command "insert" "mroads" '(34 -26) 1 1 0 )
(command "insert" "mroads" '(8 -25) 1 1 0 )
(command "insert" "mroads" '(94 -32) 1 1 0 )
(command "insert" "mroads" '(9 -20) 1 1 0 )
(command "insert" "mroads" '(10 -19) 1 1 0 )
(command "insert" "mroads" '(37 -25) 1 1 0 )
(command "insert" "mroads" '(26 -30) 1 1 0 )
(command "insert" "mroads" '(7 -18) 1 1 0 )
(command "insert" "mroads" '(38 -22) 1 1 0 )
(command "insert" "mroads" '(27 -31) 1 1 0 )
(command "insert" "mroads" '(40 -20) 1 1 0 )
(command "insert" "mroads" '(39 -23) 1 1 0 )
(command "insert" "mroads" '(88 -31) 1 1 0 )
(command "insert" "mroads" '(74 -30) 1 1 0 )
(command "insert" "mroads" '(89 -30) 1 1 0 )
(command "insert" "mroads" '(3 -22) 1 1 0 )
(command "insert" "mroads" '(75 -31) 1 1 0 )
(command "insert" "mroads" '(4 -17) 1 1 0 )
(command "insert" "mroads" '(5 -20) 1 1 0 )
(command "insert" "mroads" '(6 -27) 1 1 0 )
(command "insert" "mroads" '(21 -17) 1 1 0 )
(command "insert" "mroads" '(17 -17) 1 1 0 )
(command "insert" "mroads" '(22 -30) 1 1 0 )
(command "insert" "mroads" '(33 -22) 1 1 0 )
(command "insert" "mroads" '(23 -31) 1 1 0 )
(command "insert" "mroads" '(12 -32) 1 1 0 )
(command "insert" "mroads" '(34 -21) 1 1 0 )
(command "insert" "mroads" '(70 -30) 1 1 0 )
(command "insert" "mroads" '(85 -30) 1 1 0 )
(command "insert" "mroads" '(48 -32) 1 1 0 )
(command "insert" "mroads" '(71 -31) 1 1 0 )
(command "insert" "mroads" '(34 -15) 1 1 0 )
(command "insert" "mroads" '(11 -19) 1 1 0 )
(command "insert" "mroads" '(100 -32) 1 1 0 )
(command "insert" "mroads" '(27 -20) 1 1 0 )
(command "insert" "mroads" '(1 -25) 1 1 0 )
(command "insert" "mroads" '(108 -32) 1 1 0 )
(command "insert" "mroads" '(2 -30) 1 1 0 )
(command "insert" "mroads" '(3 -31) 1 1 0 )
(command "insert" "mroads" '(64 -31) 1 1 0 )
(command "insert" "mroads" '(4 -24) 1 1 0 )
(command "insert" "mroads" '(19 -32) 1 1 0 )
(command "insert" "mroads" '(62 -31) 1 1 0 )
(command "insert" "mroads" '(50 -30) 1 1 0 )
(command "insert" "mroads" '(65 -30) 1 1 0 )
(command "insert" "mroads" '(5 -29) 1 1 0 )
(command "insert" "mroads" '(27 -32) 1 1 0 )
(command "insert" "mroads" '(6 -18) 1 1 0 )
(command "insert" "mroads" '(101 -32) 1 1 0 )
(command "insert" "mroads" '(112 -31) 1 1 0 )
(command "insert" "mroads" '(41 -21) 1 1 0 )
(command "insert" "mroads" '(22 -17) 1 1 0 )
(command "insert" "mroads" '(79 -32) 1 1 0 )
(command "insert" "mroads" '(18 -17) 1 1 0 )
(command "insert" "mroads" '(23 -20) 1 1 0 )
(command "insert" "mroads" '(40 -31) 1 1 0 )
(command "insert" "mroads" '(115 -32) 1 1 0 )
(command "insert" "mroads" '(60 -31) 1 1 0 )
(command "insert" "mroads" '(61 -30) 1 1 0 )
(command "insert" "mroads" '(35 -23) 1 1 0 )
(command "insert" "mroads" '(24 -16) 1 1 0 )
(command "insert" "mroads" '(36 -16) 1 1 0 )
(command "insert" "mroads" '(108 -31) 1 1 0 )
(command "insert" "mroads" '(37 -21) 1 1 0 )
(command "insert" "mroads" '(2 -25) 1 1 0 )
(command "insert" "mroads" '(109 -30) 1 1 0 )
(command "insert" "mroads" '(7 -16) 1 1 0 )
(command "insert" "mroads" '(38 -26) 1 1 0 )
(command "insert" "mroads" '(40 -18) 1 1 0 )
(command "insert" "mroads" '(114 -32) 1 1 0 )
(command "insert" "mroads" '(116 -30) 1 1 0 )
(command "insert" "mroads" '(6 -21) 1 1 0 )
(command "insert" "mroads" '(111 -31) 1 1 0 )
(command "insert" "mroads" '(19 -15) 1 1 0 )
(command "insert" "mroads" '(41 -30) 1 1 0 )
(command "insert" "mroads" '(5 -32) 1 1 0 )
(command "insert" "mroads" '(33 -32) 1 1 0 )
(command "insert" "mroads" '(41 -32) 1 1 0 )
(command "insert" "mroads" '(7 -29) 1 1 0 )
(command "insert" "mroads" '(85 -32) 1 1 0 )
(command "insert" "mroads" '(9 -15) 1 1 0 )
(command "insert" "mroads" '(33 -26) 1 1 0 )
(command "insert" "mroads" '(22 -31) 1 1 0 )
(command "insert" "mroads" '(93 -32) 1 1 0 )
(command "insert" "mroads" '(8 -20) 1 1 0 )
(command "insert" "mroads" '(37 -15) 1 1 0 )
(command "insert" "mroads" '(35 -28) 1 1 0 )
(command "insert" "mroads" '(9 -17) 1 1 0 )
(command "insert" "mroads" '(96 -30) 1 1 0 )
(command "insert" "mroads" '(36 -31) 1 1 0 )
(command "insert" "mroads" '(15 -15) 1 1 0 )
(command "insert" "mroads" '(97 -31) 1 1 0 )
(command "insert" "mroads" '(37 -30) 1 1 0 )
(command "insert" "mroads" '(38 -29) 1 1 0 )
(command "insert" "mroads" '(83 -31) 1 1 0 )
(command "insert" "mroads" '(39 -24) 1 1 0 )
(command "insert" "mroads" '(5 -15) 1 1 0 )
(command "insert" "mroads" '(3 -19) 1 1 0 )
(command "insert" "mroads" '(4 -20) 1 1 0 )
(command "insert" "mroads" '(19 -20) 1 1 0 )
(command "insert" "mroads" '(92 -30) 1 1 0 )
(command "insert" "mroads" '(16 -31) 1 1 0 )
(command "insert" "mroads" '(93 -31) 1 1 0 )
(command "insert" "mroads" '(17 -30) 1 1 0 )
(command "insert" "mroads" '(32 -18) 1 1 0 )
(command "insert" "mroads" '(11 -32) 1 1 0 )
(command "insert" "mroads" '(33 -19) 1 1 0 )
(command "insert" "mroads" '(40 -29) 1 1 0 )
(command "insert" "mroads" '(8 -27) 1 1 0 )
(command "insert" "mroads" '(63 -32) 1 1 0 )
(command "insert" "mroads" '(5 -21) 1 1 0 )
(command "insert" "mroads" '(24 -30) 1 1 0 )
(command "insert" "mroads" '(14 -17) 1 1 0 )
(command "insert" "mroads" '(71 -32) 1 1 0 )
(command "insert" "mroads" '(10 -17) 1 1 0 )
(command "insert" "mroads" '(25 -31) 1 1 0 )
(command "insert" "mroads" '(99 -32) 1 1 0 )
(command "insert" "mroads" '(111 -32) 1 1 0 )
(command "insert" "mroads" '(107 -32) 1 1 0 )
(command "insert" "mroads" '(38 -20) 1 1 0 )
(command "insert" "mroads" '(12 -31) 1 1 0 )
(command "insert" "mroads" '(27 -17) 1 1 0 )
(command "insert" "mroads" '(39 -17) 1 1 0 )
(command "insert" "mroads" '(13 -30) 1 1 0 )
(command "insert" "mroads" '(41 -24) 1 1 0 )
(command "insert" "mroads" '(3 -24) 1 1 0 )
(command "insert" "mroads" '(56 -32) 1 1 0 )
(command "insert" "mroads" '(4 -19) 1 1 0 )
(command "insert" "mroads" '(26 -32) 1 1 0 )
(command "insert" "mroads" '(5 -18) 1 1 0 )
(command "insert" "mroads" '(20 -30) 1 1 0 )
(command "insert" "mroads" '(6 -25) 1 1 0 )
(command "insert" "mroads" '(21 -31) 1 1 0 )
(command "insert" "mroads" '(40 -22) 1 1 0 )
(command "insert" "mroads" '(78 -32) 1 1 0 )
(command "insert" "mroads" '(41 -18) 1 1 0 )
(command "insert" "mroads" '(18 -20) 1 1 0 )
(command "insert" "mroads" '(33 -20) 1 1 0 )
(command "insert" "mroads" '(69 -31) 1 1 0 )
(command "insert" "mroads" '(34 -19) 1 1 0 )
(command "insert" "mroads" '(32 -15) 1 1 0 )
(command "insert" "mroads" '(15 -32) 1 1 0 )
(command "insert" "mroads" '(64 -32) 1 1 0 )
(command "insert" "mroads" '(35 -16) 1 1 0 )
(command "insert" "mroads" '(38 -15) 1 1 0 )
(command "insert" "mroads" '(77 -32) 1 1 0 )
(command "insert" "mroads" '(1 -31) 1 1 0 )
(command "insert" "mroads" '(28 -17) 1 1 0 )
(command "insert" "mroads" '(2 -28) 1 1 0 )
(command "insert" "mroads" '(48 -30) 1 1 0 )
(command "insert" "mroads" '(113 -32) 1 1 0 )
(command "insert" "mroads" '(49 -31) 1 1 0 )
(command "insert" "mroads" '(4 -26) 1 1 0 )
(command "insert" "mroads" '(28 -15) 1 1 0 )
(command "insert" "mroads" '(5 -27) 1 1 0 )
(command "insert" "mroads" '(40 -26) 1 1 0 )
(command "insert" "mroads" '(4 -32) 1 1 0 )
(command "insert" "mroads" '(7 -21) 1 1 0 )
(command "insert" "mroads" '(18 -15) 1 1 0 )
(command "insert" "mroads" '(40 -32) 1 1 0 )
(command "insert" "mroads" '(34 -20) 1 1 0 )
(command "insert" "mroads" '(58 -31) 1 1 0 )
(command "insert" "mroads" '(44 -30) 1 1 0 )
(command "insert" "mroads" '(59 -30) 1 1 0 )
(command "insert" "mroads" '(92 -32) 1 1 0 )
(command "insert" "mroads" '(45 -31) 1 1 0 )
(command "insert" "mroads" '(6 -17) 1 1 0 )
(command "insert" "mroads" '(106 -31) 1 1 0 )
(command "insert" "mroads" '(35 -25) 1 1 0 )
(command "insert" "mroads" '(24 -18) 1 1 0 )
(command "insert" "mroads" '(107 -30) 1 1 0 )
(command "insert" "mroads" '(36 -18) 1 1 0 )
(command "insert" "mroads" '(25 -19) 1 1 0 )
(command "insert" "mroads" '(13 -16) 1 1 0 )
(command "insert" "mroads" '(37 -19) 1 1 0 )
(command "insert" "mroads" '(2 -23) 1 1 0 )
(command "insert" "mroads" '(38 -24) 1 1 0 )
(command "insert" "mroads" '(39 -29) 1 1 0 )
(command "insert" "mroads" '(54 -31) 1 1 0 )
(command "insert" "mroads" '(115 -31) 1 1 0 )
(command "insert" "mroads" '(55 -30) 1 1 0 )
(command "insert" "mroads" '(22 -20) 1 1 0 )
(command "insert" "mroads" '(30 -20) 1 1 0 )
(command "insert" "mroads" '(19 -17) 1 1 0 )
(command "insert" "mroads" '(102 -31) 1 1 0 )
(command "insert" "mroads" '(41 -28) 1 1 0 )
(command "insert" "mroads" '(31 -17) 1 1 0 )
(command "insert" "mroads" '(103 -30) 1 1 0 )
(command "insert" "mroads" '(10 -32) 1 1 0 )
(command "insert" "mroads" '(22 -32) 1 1 0 )
(command "insert" "mroads" '(18 -32) 1 1 0 )
(command "insert" "mroads" '(33 -24) 1 1 0 )
(command "insert" "mroads" '(62 -32) 1 1 0 )
(command "insert" "mroads" '(110 -30) 1 1 0 )
(command "insert" "mroads" '(34 -31) 1 1 0 )
(command "insert" "mroads" '(8 -22) 1 1 0 )
(command "insert" "mroads" '(23 -17) 1 1 0 )
(command "insert" "mroads" '(70 -32) 1 1 0 )
(command "insert" "mroads" '(35 -30) 1 1 0 )
(command "insert" "mroads" '(98 -32) 1 1 0 )
(command "insert" "mroads" '(36 -25) 1 1 0 )
(command "insert" "mroads" '(10 -20) 1 1 0 )
(command "insert" "mroads" '(25 -20) 1 1 0 )
(command "insert" "mroads" '(82 -31) 1 1 0 )
(command "insert" "mroads" '(106 -32) 1 1 0 )
(command "insert" "mroads" '(37 -28) 1 1 0 )
(command "insert" "mroads" '(26 -19) 1 1 0 )
(command "insert" "mroads" '(38 -19) 1 1 0 )
(command "insert" "mroads" '(3 -15) 1 1 0 )
(command "insert" "mroads" '(39 -26) 1 1 0 )
(command "insert" "mroads" '(51 -31) 1 1 0 )
(command "insert" "mroads" '(3 -21) 1 1 0 )
(command "insert" "mroads" '(25 -32) 1 1 0 )
(command "insert" "mroads" '(90 -30) 1 1 0 )
(command "insert" "mroads" '(30 -31) 1 1 0 )
(command "insert" "mroads" '(4 -22) 1 1 0 )
(command "insert" "mroads" '(91 -31) 1 1 0 )
(command "insert" "mroads" '(31 -30) 1 1 0 )
(command "insert" "mroads" '(5 -23) 1 1 0 )
(command "insert" "mroads" '(20 -17) 1 1 0 )
(command "insert" "mroads" '(16 -17) 1 1 0 )
(command "insert" "mroads" '(21 -20) 1 1 0 )
(command "insert" "mroads" '(32 -20) 1 1 0 )
(command "insert" "mroads" '(33 -17) 1 1 0 )
(command "insert" "mroads" '(34 -22) 1 1 0 )
(command "insert" "mroads" '(8 -29) 1 1 0 )
(command "insert" "mroads" '(61 -31) 1 1 0 )
(command "insert" "mroads" '(86 -30) 1 1 0 )
(command "insert" "mroads" '(10 -31) 1 1 0 )
(command "insert" "mroads" '(6 -19) 1 1 0 )
(command "insert" "mroads" '(87 -31) 1 1 0 )
(command "insert" "mroads" '(11 -30) 1 1 0 )
(command "insert" "mroads" '(76 -32) 1 1 0 )
(command "insert" "mroads" '(27 -19) 1 1 0 )
(command "insert" "mroads" '(39 -19) 1 1 0 )
(command "insert" "mroads" '(28 -20) 1 1 0 )
(command "insert" "mroads" '(3 -26) 1 1 0 )
(command "insert" "mroads" '(40 -15) 1 1 0 )
(command "insert" "mroads" '(4 -29) 1 1 0 )
(command "insert" "mroads" '(19 -31) 1 1 0 )
(command "insert" "mroads" '(7 -26) 1 1 0 )
(command "insert" "mroads" '(5 -16) 1 1 0 )
(command "insert" "mroads" '(3 -32) 1 1 0 )
(command "insert" "mroads" '(66 -30) 1 1 0 )
(command "insert" "mroads" '(6 -31) 1 1 0 )
(command "insert" "mroads" '(67 -31) 1 1 0 )
(command "insert" "mroads" '(7 -30) 1 1 0 )
(command "insert" "mroads" '(22 -18) 1 1 0 )
(command "insert" "mroads" '(55 -32) 1 1 0 )
(command "insert" "mroads" '(18 -18) 1 1 0 )
(command "insert" "mroads" '(83 -32) 1 1 0 )
(command "insert" "mroads" '(114 -30) 1 1 0 )
(command "insert" "mroads" '(34 -17) 1 1 0 )
(command "insert" "mroads" '(91 -32) 1 1 0 )
(command "insert" "mroads" '(14 -30) 1 1 0 )
(command "insert" "mroads" '(36 -15) 1 1 0 )
(command "insert" "mroads" '(15 -31) 1 1 0 )
(command "insert" "mroads" '(35 -18) 1 1 0 )
(command "insert" "mroads" '(12 -16) 1 1 0 )
(command "insert" "mroads" '(36 -21) 1 1 0 )
(command "insert" "mroads" '(1 -29) 1 1 0 )
(command "insert" "mroads" '(63 -31) 1 1 0 )
(command "insert" "mroads" '(28 -19) 1 1 0 )
(command "insert" "mroads" '(2 -26) 1 1 0 )
(command "insert" "mroads" '(26 -15) 1 1 0 )
(command "insert" "mroads" '(12 -15) 1 1 0 )
(command "insert" "mroads" '(29 -18) 1 1 0 )
(command "insert" "mroads" '(5 -25) 1 1 0 )
(command "insert" "mroads" '(16 -15) 1 1 0 )
(command "insert" "mroads" '(6 -22) 1 1 0 )
(command "insert" "mroads" '(30 -19) 1 1 0 )
(command "insert" "mroads" '(41 -25) 1 1 0 )
(command "insert" "mroads" '(56 -31) 1 1 0 )
(command "insert" "mroads" '(9 -32) 1 1 0 )
(command "insert" "mroads" '(42 -30) 1 1 0 )
(command "insert" "mroads" '(23 -16) 1 1 0 )
(command "insert" "mroads" '(43 -31) 1 1 0 )
(command "insert" "mroads" '(17 -32) 1 1 0 )
(command "insert" "mroads" '(22 -15) 1 1 0 )
(command "insert" "mroads" '(61 -32) 1 1 0 )
(command "insert" "mroads" '(52 -30) 1 1 0 )
(command "insert" "mroads" '(105 -30) 1 1 0 )
(command "insert" "mroads" '(69 -32) 1 1 0 )
(command "insert" "mroads" '(34 -24) 1 1 0 )
(command "insert" "mroads" '(8 -17) 1 1 0 )
(command "insert" "mroads" '(97 -32) 1 1 0 )
(command "insert" "mroads" '(35 -27) 1 1 0 )
(command "insert" "mroads" '(24 -20) 1 1 0 )
(command "insert" "mroads" '(105 -32) 1 1 0 )
(command "insert" "mroads" '(36 -28) 1 1 0 )
(command "insert" "mroads" '(1 -22) 1 1 0 )
(command "insert" "mroads" '(6 -29) 1 1 0 )
(command "insert" "mroads" '(37 -17) 1 1 0 )
(command "insert" "mroads" '(2 -21) 1 1 0 )
(command "insert" "mroads" '(38 -30) 1 1 0 )
(command "insert" "mroads" '(53 -30) 1 1 0 )
(command "insert" "mroads" '(112 -32) 1 1 0 )
(command "insert" "mroads" '(39 -31) 1 1 0 )
(command "insert" "mroads" '(100 -31) 1 1 0 )
(command "insert" "mroads" '(24 -32) 1 1 0 )
(command "insert" "mroads" '(101 -30) 1 1 0 )
(command "insert" "mroads" '(19 -19) 1 1 0 )
(command "insert" "mroads" '(31 -19) 1 1 0 )
(command "insert" "mroads" '(20 -20) 1 1 0 )
(command "insert" "mroads" '(47 -31) 1 1 0 )
(command "insert" "mroads" '(32 -31) 1 1 0 )
(command "insert" "mroads" '(18 -30) 1 1 0 )
(command "insert" "mroads" '(33 -30) 1 1 0 )
(command "insert" "mroads" '(34 -29) 1 1 0 )
(command "insert" "mroads" '(8 -24) 1 1 0 )
(command "insert" "mroads" '(39 -32) 1 1 0 )
(command "insert" "mroads" '(80 -31) 1 1 0 )
(command "insert" "mroads" '(81 -30) 1 1 0 )
(command "insert" "mroads" '(36 -27) 1 1 0 )
(command "insert" "mroads" '(10 -18) 1 1 0 )
(command "insert" "mroads" '(75 -32) 1 1 0 )
(command "insert" "mroads" '(37 -26) 1 1 0 )
(command "insert" "mroads" '(26 -17) 1 1 0 )
(command "insert" "mroads" '(38 -17) 1 1 0 )
(command "insert" "mroads" '(39 -20) 1 1 0 )
(command "insert" "mroads" '(88 -30) 1 1 0 )
(command "insert" "mroads" '(28 -31) 1 1 0 )
(command "insert" "mroads" '(89 -31) 1 1 0 )
(command "insert" "mroads" '(29 -30) 1 1 0 )
(command "insert" "mroads" '(3 -23) 1 1 0 )
(command "insert" "mroads" '(4 -16) 1 1 0 )
(command "insert" "mroads" '(2 -32) 1 1 0 )
(command "insert" "mroads" '(76 -31) 1 1 0 )
(command "insert" "mroads" '(46 -32) 1 1 0 )
(command "insert" "mroads" '(20 -19) 1 1 0 )
(command "insert" "mroads" '(33 -29) 1 1 0 )
(command "insert" "mroads" '(77 -30) 1 1 0 )
(command "insert" "mroads" '(6 -26) 1 1 0 )
(command "insert" "mroads" '(21 -18) 1 1 0 )
(command "insert" "mroads" '(54 -32) 1 1 0 )
(command "insert" "mroads" '(33 -23) 1 1 0 )
(command "insert" "mroads" '(90 -32) 1 1 0 )
(command "insert" "mroads" '(84 -30) 1 1 0 )
(command "insert" "mroads" '(8 -31) 1 1 0 )
(command "insert" "mroads" '(95 -31) 1 1 0 )
(command "insert" "mroads" '(85 -31) 1 1 0 )
(command "insert" "mroads" '(9 -30) 1 1 0 )
(command "insert" "mroads" '(15 -16) 1 1 0 )
(command "insert" "mroads" '(11 -16) 1 1 0 )
(command "insert" "mroads" '(1 -26) 1 1 0 )
(command "insert" "mroads" '(40 -21) 1 1 0 )
(command "insert" "mroads" '(73 -31) 1 1 0 )
(command "insert" "mroads" '(3 -28) 1 1 0 )
(command "insert" "mroads" '(64 -30) 1 1 0 )
(command "insert" "mroads" '(4 -31) 1 1 0 )
(command "insert" "mroads" '(65 -31) 1 1 0 )
(command "insert" "mroads" '(5 -30) 1 1 0 )
(command "insert" "mroads" '(40 -23) 1 1 0 )
(command "insert" "mroads" '(112 -30) 1 1 0 )
(command "insert" "mroads" '(8 -32) 1 1 0 )
(command "insert" "mroads" '(41 -22) 1 1 0 )
(command "insert" "mroads" '(22 -16) 1 1 0 )
(command "insert" "mroads" '(113 -31) 1 1 0 )
(command "insert" "mroads" '(18 -16) 1 1 0 )
(command "insert" "mroads" '(16 -32) 1 1 0 )
(command "insert" "mroads" '(60 -32) 1 1 0 )
(command "insert" "mroads" '(68 -32) 1 1 0 )
(command "insert" "mroads" '(96 -32) 1 1 0 )
(command "insert" "mroads" '(60 -30) 1 1 0 )
(command "insert" "mroads" '(104 -32) 1 1 0 )
(command "insert" "mroads" '(35 -20) 1 1 0 )
(command "insert" "mroads" '(24 -15) 1 1 0 )
(command "insert" "mroads" '(36 -23) 1 1 0 )
(command "insert" "mroads" '(108 -30) 1 1 0 )
(command "insert" "mroads" '(37 -22) 1 1 0 )
(command "insert" "mroads" '(2 -24) 1 1 0 )
(command "insert" "mroads" '(109 -31) 1 1 0 )
(command "insert" "mroads" '(29 -16) 1 1 0 )
(command "insert" "mroads" '(30 -15) 1 1 0 )
(command "insert" "mroads" '(25 -18) 1 1 0 )
(command "insert" "mroads" '(40 -30) 1 1 0 )
(command "insert" "mroads" '(30 -17) 1 1 0 )
(command "insert" "mroads" '(7 -17) 1 1 0 )
(command "insert" "mroads" '(31 -20) 1 1 0 )
(command "insert" "mroads" '(20 -15) 1 1 0 )
(command "insert" "mroads" '(33 -31) 1 1 0 )
(command "insert" "mroads" '(23 -18) 1 1 0 )
(command "insert" "mroads" '(47 -32) 1 1 0 )
(command "insert" "mroads" '(33 -27) 1 1 0 )
(command "insert" "mroads" '(38 -32) 1 1 0 )
(command "insert" "mroads" '(10 -15) 1 1 0 )
(command "insert" "mroads" '(8 -19) 1 1 0 )
(command "insert" "mroads" '(35 -29) 1 1 0 )
(command "insert" "mroads" '(9 -18) 1 1 0 )
(command "insert" "mroads" '(74 -32) 1 1 0 )
(command "insert" "mroads" '(52 -32) 1 1 0 )
(command "insert" "mroads" '(36 -30) 1 1 0 )
(command "insert" "mroads" '(51 -30) 1 1 0 )
(command "insert" "mroads" '(41 -27) 1 1 0 )
(command "insert" "mroads" '(82 -32) 1 1 0 )
(command "insert" "mroads" '(37 -31) 1 1 0 )
(command "insert" "mroads" '(26 -20) 1 1 0 )
(command "insert" "mroads" '(7 -19) 1 1 0 )
(command "insert" "mroads" '(98 -31) 1 1 0 )
(command "insert" "mroads" '(38 -28) 1 1 0 )
(command "insert" "mroads" '(40 -19) 1 1 0 )
(command "insert" "mroads" '(99 -30) 1 1 0 )
(command "insert" "mroads" '(39 -25) 1 1 0 )
(command "insert" "mroads" '(3 -16) 1 1 0 )
(command "insert" "mroads" '(1 -32) 1 1 0 )
(command "insert" "mroads" '(6 -15) 1 1 0 )
(command "insert" "mroads" '(46 -31) 1 1 0 )
(command "insert" "mroads" '(53 -32) 1 1 0 )
(command "insert" "mroads" '(16 -30) 1 1 0 )
(command "insert" "mroads" '(47 -30) 1 1 0 )
(command "insert" "mroads" '(17 -31) 1 1 0 )
(command "insert" "mroads" '(32 -17) 1 1 0 )
(command "insert" "mroads" '(7 -28) 1 1 0 )
(command "insert" "mroads" '(89 -32) 1 1 0 )
(command "insert" "mroads" '(7 -24) 1 1 0 )
(command "insert" "mroads" '(94 -31) 1 1 0 )
(command "insert" "mroads" '(33 -28) 1 1 0 )
(command "insert" "mroads" '(95 -30) 1 1 0 )
(command "insert" "mroads" '(34 -27) 1 1 0 )
(command "insert" "mroads" '(8 -26) 1 1 0 )
(command "insert" "mroads" '(14 -16) 1 1 0 )
(command "insert" "mroads" '(10 -16) 1 1 0 )
(command "insert" "mroads" '(37 -24) 1 1 0 )
(command "insert" "mroads" '(68 -30) 1 1 0 )
(command "insert" "mroads" '(26 -31) 1 1 0 )
(command "insert" "mroads" '(26 -18) 1 1 0 )
(command "insert" "mroads" '(38 -23) 1 1 0 )
(command "insert" "mroads" '(83 -30) 1 1 0 )
(command "insert" "mroads" '(27 -30) 1 1 0 )
(command "insert" "mroads" '(39 -22) 1 1 0 )
(command "insert" "mroads" '(13 -31) 1 1 0 )
(command "insert" "mroads" '(74 -31) 1 1 0 )
(command "insert" "mroads" '(3 -25) 1 1 0 )
(command "insert" "mroads" '(75 -30) 1 1 0 )
(command "insert" "mroads" '(4 -18) 1 1 0 )
(command "insert" "mroads" '(62 -30) 1 1 0 )
(command "insert" "mroads" '(5 -19) 1 1 0 )
(command "insert" "mroads" '(23 -32) 1 1 0 )
(command "insert" "mroads" '(6 -24) 1 1 0 )
(command "insert" "mroads" '(21 -16) 1 1 0 )
(command "insert" "mroads" '(17 -16) 1 1 0 )
(command "insert" "mroads" '(41 -19) 1 1 0 )
(command "insert" "mroads" '(31 -32) 1 1 0 )
(command "insert" "mroads" '(59 -32) 1 1 0 )
(command "insert" "mroads" '(33 -21) 1 1 0 )
(command "insert" "mroads" '(23 -30) 1 1 0 )
(command "insert" "mroads" '(34 -18) 1 1 0 )
(command "insert" "mroads" '(67 -32) 1 1 0 )
(command "insert" "mroads" '(6 -20) 1 1 0 )
(command "insert" "mroads" '(70 -31) 1 1 0 )
(command "insert" "mroads" '(33 -15) 1 1 0 )
(command "insert" "mroads" '(71 -30) 1 1 0 )
(command "insert" "mroads" '(11 -18) 1 1 0 )
(command "insert" "mroads" '(35 -17) 1 1 0 )
(command "insert" "mroads" '(1 -24) 1 1 0 )
(command "insert" "mroads" '(39 -15) 1 1 0 )
(command "insert" "mroads" '(28 -16) 1 1 0 )
(command "insert" "mroads" '(2 -31) 1 1 0 )
(command "insert" "mroads" '(12 -30) 1 1 0 )
(command "insert" "mroads" '(41 -31) 1 1 0 )
(command "insert" "mroads" '(79 -31) 1 1 0 )
(command "insert" "mroads" '(3 -30) 1 1 0 )
(command "insert" "mroads" '(40 -17) 1 1 0 )
(command "insert" "mroads" '(4 -25) 1 1 0 )
(command "insert" "mroads" '(50 -31) 1 1 0 )
(command "insert" "mroads" '(5 -28) 1 1 0 )
(command "insert" "mroads" '(29 -15) 1 1 0 )
(command "insert" "mroads" '(40 -25) 1 1 0 )
(command "insert" "mroads" '(41 -20) 1 1 0 )
(command "insert" "mroads" '(58 -30) 1 1 0 )
(command "insert" "mroads" '(37 -32) 1 1 0 )
(command "insert" "mroads" '(59 -31) 1 1 0 )
(command "insert" "mroads" '(41 -16) 1 1 0 )
(command "insert" "mroads" '(45 -32) 1 1 0 )
(command "insert" "mroads" '(73 -32) 1 1 0 )
(command "insert" "mroads" '(106 -30) 1 1 0 )
(command "insert" "mroads" '(35 -22) 1 1 0 )
(command "insert" "mroads" '(24 -17) 1 1 0 )
(command "insert" "mroads" '(107 -31) 1 1 0 )
(command "insert" "mroads" '(81 -32) 1 1 0 )
(command "insert" "mroads" '(36 -17) 1 1 0 )
(command "insert" "mroads" '(13 -17) 1 1 0 )
(command "insert" "mroads" '(37 -20) 1 1 0 )
(command "insert" "mroads" '(2 -22) 1 1 0 )
(command "insert" "mroads" '(72 -30) 1 1 0 )
(command "insert" "mroads" '(38 -27) 1 1 0 )
(command "insert" "mroads" '(54 -30) 1 1 0 )
(command "insert" "mroads" '(34 -23) 1 1 0 )
(command "insert" "mroads" '(55 -31) 1 1 0 )
(command "insert" "mroads" '(116 -31) 1 1 0 )
(command "insert" "mroads" '(102 -30) 1 1 0 )
(command "insert" "mroads" '(41 -29) 1 1 0 )
(command "insert" "mroads" '(103 -31) 1 1 0 )
(command "insert" "mroads" '(88 -32) 1 1 0 )
(command "insert" "mroads" '(84 -31) 1 1 0 )
(command "insert" "mroads" '(8 -15) 1 1 0 )
(command "insert" "mroads" '(33 -25) 1 1 0 )
(command "insert" "mroads" '(34 -30) 1 1 0 )
(command "insert" "mroads" '(8 -21) 1 1 0 )
(command "insert" "mroads" '(35 -31) 1 1 0 )
(command "insert" "mroads" '(9 -16) 1 1 0 )
(command "insert" "mroads" '(14 -15) 1 1 0 )
(command "insert" "mroads" '(40 -28) 1 1 0 )
(command "insert" "mroads" '(96 -31) 1 1 0 )
(command "insert" "mroads" '(36 -24) 1 1 0 )
(command "insert" "mroads" '(78 -31) 1 1 0 )
(command "insert" "mroads" '(82 -30) 1 1 0 )
(command "insert" "mroads" '(97 -30) 1 1 0 )
(command "insert" "mroads" '(37 -29) 1 1 0 )
(command "insert" "mroads" '(31 -31) 1 1 0 )
(command "insert" "mroads" '(38 -18) 1 1 0 )
(command "insert" "mroads" '(103 -32) 1 1 0 )
(command "insert" "mroads" '(39 -27) 1 1 0 )
(command "insert" "mroads" '(4 -15) 1 1 0 )
(command "insert" "mroads" '(7 -23) 1 1 0 )
(command "insert" "mroads" '(3 -18) 1 1 0 )
(command "insert" "mroads" '(30 -30) 1 1 0 )
(command "insert" "mroads" '(4 -21) 1 1 0 )
(command "insert" "mroads" '(79 -30) 1 1 0 )
(command "insert" "mroads" '(20 -16) 1 1 0 )
(command "insert" "mroads" '(92 -31) 1 1 0 )
(command "insert" "mroads" '(16 -16) 1 1 0 )
(command "insert" "mroads" '(30 -32) 1 1 0 )
(command "insert" "mroads" '(93 -30) 1 1 0 )
(command "insert" "mroads" '(58 -32) 1 1 0 )
(command "insert" "mroads" '(32 -19) 1 1 0 )
(command "insert" "mroads" '(33 -18) 1 1 0 )
(command "insert" "mroads" '(66 -32) 1 1 0 )
(command "insert" "mroads" '(110 -32) 1 1 0 )
(command "insert" "mroads" '(34 -25) 1 1 0 )
(command "insert" "mroads" '(8 -28) 1 1 0 )
(command "insert" "mroads" '(57 -30) 1 1 0 )
(command "insert" "mroads" '(24 -31) 1 1 0 )
(command "insert" "mroads" '(10 -30) 1 1 0 )
(command "insert" "mroads" '(25 -30) 1 1 0 )
(command "insert" "mroads" '(11 -31) 1 1 0 )
(command "insert" "mroads" '(72 -31) 1 1 0 )
(command "insert" "mroads" '(27 -16) 1 1 0 )
(command "insert" "mroads" '(49 -32) 1 1 0 )
(command "insert" "mroads" '(73 -30) 1 1 0 )
(command "insert" "mroads" '(3 -27) 1 1 0 )
(command "insert" "mroads" '(4 -28) 1 1 0 )
(command "insert" "mroads" '(41 -15) 1 1 0 )
(command "insert" "mroads" '(5 -17) 1 1 0 )
(command "insert" "mroads" '(20 -31) 1 1 0 )
(command "insert" "mroads" '(6 -30) 1 1 0 )
(command "insert" "mroads" '(21 -30) 1 1 0 )
(command "insert" "mroads" '(7 -31) 1 1 0 )
(command "insert" "mroads" '(68 -31) 1 1 0 )
(command "insert" "mroads" '(36 -32) 1 1 0 )
(command "insert" "mroads" '(69 -30) 1 1 0 )
(command "insert" "mroads" '(34 -16) 1 1 0 )
(command "insert" "mroads" '(44 -32) 1 1 0 )
(command "insert" "mroads" '(72 -32) 1 1 0 )
(command "insert" "mroads" '(6 -16) 1 1 0 )
(command "insert" "mroads" '(80 -32) 1 1 0 )
(command "insert" "mroads" '(11 -20) 1 1 0 )
(command "insert" "mroads" '(35 -19) 1 1 0 )
(command "insert" "mroads" '(36 -20) 1 1 0 )
(command "insert" "mroads" '(1 -30) 1 1 0 )
(command "insert" "mroads" '(28 -18) 1 1 0 )
(command "insert" "mroads" '(2 -29) 1 1 0 )
(command "insert" "mroads" '(48 -31) 1 1 0 )
(command "insert" "mroads" '(29 -19) 1 1 0 )
(command "insert" "mroads" '(27 -15) 1 1 0 )
(command "insert" "mroads" '(49 -30) 1 1 0 )
(command "insert" "mroads" '(4 -27) 1 1 0 )
(command "insert" "mroads" '(32 -32) 1 1 0 )
(command "insert" "mroads" '(5 -26) 1 1 0 )
(command "insert" "mroads" '(51 -32) 1 1 0 )
(command "insert" "mroads" '(40 -27) 1 1 0 )
(command "insert" "mroads" '(30 -18) 1 1 0 )
(command "insert" "mroads" '(17 -15) 1 1 0 )
(command "insert" "mroads" '(41 -26) 1 1 0 )
(command "insert" "mroads" '(56 -30) 1 1 0 )
(command "insert" "mroads" '(57 -31) 1 1 0 )
(command "insert" "mroads" '(86 -31) 1 1 0 )
(command "insert" "mroads" '(104 -30) 1 1 0 )
(command "insert" "mroads" '(44 -31) 1 1 0 )
(command "insert" "mroads" '(23 -15) 1 1 0 )
(command "insert" "mroads" '(105 -31) 1 1 0 )
(command "insert" "mroads" '(45 -30) 1 1 0 )
(command "insert" "mroads" '(8 -16) 1 1 0 )
(command "insert" "mroads" '(35 -24) 1 1 0 )
(command "insert" "mroads" '(50 -32) 1 1 0 )
(command "insert" "mroads" '(24 -19) 1 1 0 )
(command "insert" "mroads" '(36 -19) 1 1 0 )
(command "insert" "mroads" '(1 -23) 1 1 0 )
(command "insert" "mroads" '(104 -31) 1 1 0 )
(command "insert" "mroads" '(13 -15) 1 1 0 )
(command "insert" "mroads" '(37 -18) 1 1 0 )
(command "insert" "mroads" '(102 -32) 1 1 0 )
(command "insert" "mroads" '(38 -25) 1 1 0 )
(command "insert" "mroads" '(53 -31) 1 1 0 )
(command "insert" "mroads" '(78 -30) 1 1 0 )
(command "insert" "mroads" '(39 -28) 1 1 0 )
(command "insert" "mroads" '(84 -32) 1 1 0 )
(command "insert" "mroads" '(100 -30) 1 1 0 )
(command "insert" "mroads" '(115 -30) 1 1 0 )
(command "insert" "mroads" '(25 -17) 1 1 0 )
(command "insert" "mroads" '(101 -31) 1 1 0 )
(command "insert" "mroads" '(21 -32) 1 1 0 )
(command "insert" "mroads" '(19 -16) 1 1 0 )
(command "insert" "mroads" '(31 -16) 1 1 0 )
(command "insert" "mroads" '(29 -32) 1 1 0 )
(command "insert" "mroads" '(41 -17) 1 1 0 )
(command "insert" "mroads" '(32 -30) 1 1 0 )
(command "insert" "mroads" '(65 -32) 1 1 0 )
(command "insert" "mroads" '(52 -31) 1 1 0 )
(command "insert" "mroads" '(7 -20) 1 1 0 )
(command "insert" "mroads" '(110 -31) 1 1 0 )
(command "insert" "mroads" '(34 -28) 1 1 0 )
(command "insert" "mroads" '(8 -23) 1 1 0 )
(command "insert" "mroads" '(80 -30) 1 1 0 )
(command "insert" "mroads" '(111 -30) 1 1 0 )
(command "insert" "mroads" '(57 -32) 1 1 0 )
(command "insert" "mroads" '(81 -31) 1 1 0 )
(command "insert" "mroads" '(36 -26) 1 1 0 )
(command "insert" "mroads" '(40 -24) 1 1 0 )
(command "insert" "mroads" '(37 -27) 1 1 0 )
(command "insert" "mroads" '(26 -16) 1 1 0 )
(command "insert" "mroads" '(38 -16) 1 1 0 )
(command "insert" "mroads" '(39 -21) 1 1 0 )
(command "insert" "mroads" '(28 -30) 1 1 0 )
(command "insert" "mroads" '(29 -31) 1 1 0 )
(command "insert" "mroads" '(3 -20) 1 1 0 )
(command "insert" "mroads" '(90 -31) 1 1 0 )
(command "insert" "mroads" '(4 -23) 1 1 0 )
(command "insert" "mroads" '(76 -30) 1 1 0 )
(command "insert" "mroads" '(91 -30) 1 1 0 )
(command "insert" "mroads" '(7 -27) 1 1 0 )
(command "insert" "mroads" '(5 -22) 1 1 0 )
(command "insert" "mroads" '(20 -18) 1 1 0 )
(command "insert" "mroads" '(77 -31) 1 1 0 )
(command "insert" "mroads" '(21 -19) 1 1 0 )
(command "insert" "mroads" '(7 -32) 1 1 0 )
(command "insert" "mroads" '(35 -32) 1 1 0 )
(command "insert" "mroads" '(113 -30) 1 1 0 )
(command "insert" "mroads" '(33 -16) 1 1 0 )
(command "insert" "mroads" '(43 -32) 1 1 0 )
(command "insert" "mroads" '(8 -30) 1 1 0 )
(command "insert" "mroads" '(40 -16) 1 1 0 )
(command "insert" "mroads" '(87 -32) 1 1 0 )
(command "insert" "mroads" '(9 -31) 1 1 0 )
(command "insert" "mroads" '(95 -32) 1 1 0 )
(command "insert" "mroads" '(15 -17) 1 1 0 )
(command "insert" "mroads" '(87 -30) 1 1 0 )
(command "insert" "mroads" '(11 -17) 1 1 0 )
(command "insert" "mroads" '(27 -18) 1 1 0 )
(command "insert" "mroads" '(1 -27) 1 1 0 )
(command "insert" "mroads" '(39 -18) 1 1 0 )
(command "insert" "mroads" '(14 -32) 1 1 0 )
(command "insert" "mroads" '(3 -29) 1 1 0 )
(command "insert" "mroads" '(4 -30) 1 1 0 )
(command "insert" "mroads" '(19 -30) 1 1 0 )
(command "layer" "m" "alley" "" )
(command "insert" "alley" '(15 -44) 1 1 0 )
(command "insert" "alley" '(12 -47) 1 1 0 )
(command "insert" "alley" '(16 -42) 1 1 0 )
(command "insert" "alley" '(12 -45) 1 1 0 )
(command "insert" "alley" '(17 -43) 1 1 0 )
(command "insert" "alley" '(15 -43) 1 1 0 )
(command "insert" "alley" '(15 -42) 1 1 0 )
(command "insert" "alley" '(17 -44) 1 1 0 )
(command "insert" "alley" '(14 -46) 1 1 0 )
(command "insert" "alley" '(13 -45) 1 1 0 )
(command "insert" "alley" '(16 -43) 1 1 0 )
(command "insert" "alley" '(12 -46) 1 1 0 )
(command "insert" "alley" '(17 -42) 1 1 0 )
(command "insert" "alley" '(13 -47) 1 1 0 )
(command "insert" "alley" '(14 -45) 1 1 0 )
(command "insert" "alley" '(13 -46) 1 1 0 )
(command "insert" "alley" '(14 -47) 1 1 0 )
(command "insert" "alley" '(16 -44) 1 1 0 )
(command "layer" "m" "ped" "" )
(command "insert" "ped" '(1 -3) 1 1 0 )
(command "insert" "ped" '(2 -18) 1 1 0 )
(command "insert" "ped" '(2 -8) 1 1 0 )
(command "insert" "ped" '(1 -17) 1 1 0 )
(command "insert" "ped" '(2 -1) 1 1 0 )
(command "insert" "ped" '(1 -15) 1 1 0 )
(command "insert" "ped" '(6 -2) 1 1 0 )
(command "insert" "ped" '(1 -6) 1 1 0 )
(command "insert" "ped" '(2 -12) 1 1 0 )
(command "insert" "ped" '(5 -1) 1 1 0 )
(command "insert" "ped" '(2 -5) 1 1 0 )
(command "insert" "ped" '(1 -11) 1 1 0 )
(command "insert" "ped" '(7 -2) 1 1 0 )
(command "insert" "ped" '(1 -2) 1 1 0 )
(command "insert" "ped" '(2 -19) 1 1 0 )
(command "insert" "ped" '(2 -9) 1 1 0 )
(command "insert" "ped" '(8 -1) 1 1 0 )
(command "insert" "ped" '(1 -16) 1 1 0 )
(command "insert" "ped" '(1 -14) 1 1 0 )
(command "insert" "ped" '(1 -5) 1 1 0 )
(command "insert" "ped" '(2 -13) 1 1 0 )
(command "insert" "ped" '(1 -20) 1 1 0 )
(command "insert" "ped" '(2 -2) 1 1 0 )
(command "insert" "ped" '(1 -10) 1 1 0 )
(command "insert" "ped" '(4 -1) 1 1 0 )
(command "insert" "ped" '(1 -1) 1 1 0 )
(command "insert" "ped" '(2 -16) 1 1 0 )
(command "insert" "ped" '(3 -2) 1 1 0 )
(command "insert" "ped" '(2 -6) 1 1 0 )
(command "insert" "ped" '(8 -2) 1 1 0 )
(command "insert" "ped" '(7 -1) 1 1 0 )
(command "insert" "ped" '(1 -13) 1 1 0 )
(command "insert" "ped" '(2 -20) 1 1 0 )
(command "insert" "ped" '(1 -4) 1 1 0 )
(command "insert" "ped" '(2 -10) 1 1 0 )
(command "insert" "ped" '(1 -19) 1 1 0 )
(command "insert" "ped" '(2 -3) 1 1 0 )
(command "insert" "ped" '(1 -9) 1 1 0 )
(command "insert" "ped" '(4 -2) 1 1 0 )
(command "insert" "ped" '(2 -14) 1 1 0 )
(command "insert" "ped" '(2 -17) 1 1 0 )
(command "insert" "ped" '(2 -7) 1 1 0 )
(command "insert" "ped" '(1 -12) 1 1 0 )
(command "insert" "ped" '(6 -1) 1 1 0 )
(command "insert" "ped" '(3 -1) 1 1 0 )
(command "insert" "ped" '(2 -11) 1 1 0 )
(command "insert" "ped" '(1 -18) 1 1 0 )
(command "insert" "ped" '(1 -8) 1 1 0 )
(command "insert" "ped" '(1 -7) 1 1 0 )
(command "insert" "ped" '(2 -15) 1 1 0 )
(command "insert" "ped" '(5 -2) 1 1 0 )
(command "insert" "ped" '(2 -4) 1 1 0 )
(command "layer" "m" "Center" "" )
(command "insert" "Center" '(268 -53) 1 1 0 )
(command "insert" "Center" '(268 -52) 1 1 0 )
(command "insert" "Center" '(269 -51) 1 1 0 )
(command "insert" "Center" '(268 -51) 1 1 0 )
(command "insert" "Center" '(269 -53) 1 1 0 )
(command "insert" "Center" '(267 -52) 1 1 0 )
(command "insert" "Center" '(267 -53) 1 1 0 )
(command "insert" "Center" '(269 -52) 1 1 0 )
(command "insert" "Center" '(267 -51) 1 1 0 )
(command "layer" "m" "alley" "" )
(command "insert" "alley" '(131 -44) 1 1 0 )
(command "insert" "alley" '(129 -44) 1 1 0 )
(command "insert" "alley" '(136 -44) 1 1 0 )
(command "insert" "alley" '(133 -44) 1 1 0 )
(command "insert" "alley" '(134 -42) 1 1 0 )
(command "insert" "alley" '(130 -43) 1 1 0 )
(command "insert" "alley" '(136 -42) 1 1 0 )
(command "insert" "alley" '(137 -43) 1 1 0 )
(command "insert" "alley" '(135 -42) 1 1 0 )
(command "insert" "alley" '(134 -44) 1 1 0 )
(command "insert" "alley" '(129 -42) 1 1 0 )
(command "insert" "alley" '(133 -42) 1 1 0 )
(command "insert" "alley" '(137 -44) 1 1 0 )
(command "insert" "alley" '(132 -42) 1 1 0 )
(command "insert" "alley" '(133 -43) 1 1 0 )
(command "insert" "alley" '(134 -43) 1 1 0 )
(command "insert" "alley" '(136 -43) 1 1 0 )
(command "insert" "alley" '(131 -43) 1 1 0 )
(command "insert" "alley" '(130 -42) 1 1 0 )
(command "insert" "alley" '(137 -42) 1 1 0 )
(command "insert" "alley" '(135 -44) 1 1 0 )
(command "insert" "alley" '(132 -44) 1 1 0 )
(command "insert" "alley" '(130 -44) 1 1 0 )
(command "insert" "alley" '(135 -43) 1 1 0 )
(command "insert" "alley" '(129 -43) 1 1 0 )
(command "insert" "alley" '(131 -42) 1 1 0 )
(command "insert" "alley" '(132 -43) 1 1 0 )
(command "layer" "m" "Res" "" )
(command "insert" "Res" '(188 -75) 1 1 0 )
(command "insert" "Res" '(187 -76) 1 1 0 )
(command "insert" "Res" '(187 -77) 1 1 0 )
(command "insert" "Res" '(186 -75) 1 1 0 )
(command "insert" "Res" '(187 -75) 1 1 0 )
(command "insert" "Res" '(188 -77) 1 1 0 )
(command "insert" "Res" '(186 -77) 1 1 0 )
(command "insert" "Res" '(188 -76) 1 1 0 )
(command "insert" "Res" '(186 -76) 1 1 0 )
(command "layer" "m" "Commmer" "" )
(command "insert" "Commmer" '(283 -52) 1 1 0 )
(command "insert" "Commmer" '(282 -52) 1 1 0 )
(command "insert" "Commmer" '(284 -55) 1 1 0 )
(command "insert" "Commmer" '(283 -57) 1 1 0 )
(command "insert" "Commmer" '(286 -55) 1 1 0 )
(command "insert" "Commmer" '(285 -54) 1 1 0 )
(command "insert" "Commmer" '(287 -54) 1 1 0 )
(command "insert" "Commmer" '(284 -59) 1 1 0 )
(command "insert" "Commmer" '(286 -56) 1 1 0 )
(command "insert" "Commmer" '(283 -55) 1 1 0 )
(command "insert" "Commmer" '(282 -53) 1 1 0 )
(command "insert" "Commmer" '(282 -58) 1 1 0 )
(command "insert" "Commmer" '(283 -56) 1 1 0 )
(command "insert" "Commmer" '(284 -57) 1 1 0 )
(command "insert" "Commmer" '(283 -51) 1 1 0 )
(command "insert" "Commmer" '(284 -52) 1 1 0 )
(command "insert" "Commmer" '(287 -56) 1 1 0 )
(command "insert" "Commmer" '(283 -54) 1 1 0 )
(command "insert" "Commmer" '(284 -56) 1 1 0 )
(command "insert" "Commmer" '(282 -59) 1 1 0 )
(command "insert" "Commmer" '(283 -59) 1 1 0 )
(command "insert" "Commmer" '(282 -54) 1 1 0 )
(command "insert" "Commmer" '(282 -57) 1 1 0 )
(command "insert" "Commmer" '(284 -53) 1 1 0 )
(command "insert" "Commmer" '(285 -56) 1 1 0 )
(command "insert" "Commmer" '(282 -51) 1 1 0 )
(command "insert" "Commmer" '(282 -56) 1 1 0 )
(command "insert" "Commmer" '(283 -58) 1 1 0 )
(command "insert" "Commmer" '(283 -53) 1 1 0 )
(command "insert" "Commmer" '(282 -55) 1 1 0 )
(command "insert" "Commmer" '(284 -54) 1 1 0 )
(command "insert" "Commmer" '(286 -54) 1 1 0 )
(command "insert" "Commmer" '(285 -55) 1 1 0 )
(command "insert" "Commmer" '(287 -55) 1 1 0 )
(command "insert" "Commmer" '(284 -58) 1 1 0 )
(command "insert" "Commmer" '(284 -51) 1 1 0 )
(command "layer" "m" "edge" "" )
(command "insert" "edge" '(2 -39) 1 1 0 )
(command "insert" "edge" '(1 -44) 1 1 0 )
(command "insert" "edge" '(2 -43) 1 1 0 )
(command "insert" "edge" '(1 -46) 1 1 0 )
(command "insert" "edge" '(2 -47) 1 1 0 )
(command "insert" "edge" '(2 -45) 1 1 0 )
(command "insert" "edge" '(1 -39) 1 1 0 )
(command "insert" "edge" '(1 -42) 1 1 0 )
(command "insert" "edge" '(1 -47) 1 1 0 )
(command "insert" "edge" '(2 -46) 1 1 0 )
(command "insert" "edge" '(2 -41) 1 1 0 )
(command "insert" "edge" '(2 -40) 1 1 0 )
(command "insert" "edge" '(1 -40) 1 1 0 )
(command "insert" "edge" '(2 -42) 1 1 0 )
(command "insert" "edge" '(1 -41) 1 1 0 )
(command "insert" "edge" '(1 -45) 1 1 0 )
(command "insert" "edge" '(1 -43) 1 1 0 )
(command "insert" "edge" '(2 -44) 1 1 0 )
(command "layer" "m" "Res" "" )
(command "insert" "Res" '(178 -45) 1 1 0 )
(command "insert" "Res" '(175 -45) 1 1 0 )
(command "insert" "Res" '(178 -47) 1 1 0 )
(command "insert" "Res" '(179 -49) 1 1 0 )
(command "insert" "Res" '(174 -45) 1 1 0 )
(command "insert" "Res" '(179 -47) 1 1 0 )
(command "insert" "Res" '(174 -47) 1 1 0 )
(command "insert" "Res" '(178 -49) 1 1 0 )
(command "insert" "Res" '(179 -45) 1 1 0 )
(command "insert" "Res" '(177 -45) 1 1 0 )
(command "insert" "Res" '(175 -46) 1 1 0 )
(command "insert" "Res" '(177 -48) 1 1 0 )
(command "insert" "Res" '(177 -47) 1 1 0 )
(command "insert" "Res" '(177 -50) 1 1 0 )
(command "insert" "Res" '(179 -50) 1 1 0 )
(command "insert" "Res" '(179 -48) 1 1 0 )
(command "insert" "Res" '(176 -46) 1 1 0 )
(command "insert" "Res" '(178 -46) 1 1 0 )
(command "insert" "Res" '(179 -46) 1 1 0 )
(command "insert" "Res" '(177 -49) 1 1 0 )
(command "insert" "Res" '(178 -48) 1 1 0 )
(command "insert" "Res" '(178 -50) 1 1 0 )
(command "insert" "Res" '(176 -47) 1 1 0 )
(command "insert" "Res" '(174 -46) 1 1 0 )
(command "insert" "Res" '(176 -45) 1 1 0 )
(command "insert" "Res" '(177 -46) 1 1 0 )
(command "insert" "Res" '(175 -47) 1 1 0 )
(command "layer" "m" "Center" "" )
(command "insert" "Center" '(228 -42) 1 1 0 )
(command "insert" "Center" '(229 -43) 1 1 0 )
(command "insert" "Center" '(231 -44) 1 1 0 )
(command "insert" "Center" '(232 -43) 1 1 0 )
(command "insert" "Center" '(233 -42) 1 1 0 )
(command "insert" "Center" '(228 -44) 1 1 0 )
(command "insert" "Center" '(231 -43) 1 1 0 )
(command "insert" "Center" '(230 -44) 1 1 0 )
(command "insert" "Center" '(228 -43) 1 1 0 )
(command "insert" "Center" '(229 -42) 1 1 0 )
(command "insert" "Center" '(232 -44) 1 1 0 )
(command "insert" "Center" '(229 -44) 1 1 0 )
(command "insert" "Center" '(230 -42) 1 1 0 )
(command "insert" "Center" '(232 -42) 1 1 0 )
(command "insert" "Center" '(230 -43) 1 1 0 )
(command "insert" "Center" '(233 -43) 1 1 0 )
(command "insert" "Center" '(231 -42) 1 1 0 )
(command "insert" "Center" '(233 -44) 1 1 0 )
(command "layer" "m" "edge" "" )
(command "insert" "edge" '(39 -46) 1 1 0 )
(command "insert" "edge" '(40 -45) 1 1 0 )
(command "insert" "edge" '(43 -43) 1 1 0 )
(command "insert" "edge" '(44 -44) 1 1 0 )
(command "insert" "edge" '(36 -46) 1 1 0 )
(command "insert" "edge" '(40 -42) 1 1 0 )
(command "insert" "edge" '(37 -47) 1 1 0 )
(command "insert" "edge" '(42 -43) 1 1 0 )
(command "insert" "edge" '(40 -46) 1 1 0 )
(command "insert" "edge" '(43 -42) 1 1 0 )
(command "insert" "edge" '(41 -47) 1 1 0 )
(command "insert" "edge" '(36 -47) 1 1 0 )
(command "insert" "edge" '(39 -45) 1 1 0 )
(command "insert" "edge" '(42 -44) 1 1 0 )
(command "insert" "edge" '(37 -46) 1 1 0 )
(command "insert" "edge" '(41 -43) 1 1 0 )
(command "insert" "edge" '(38 -45) 1 1 0 )
(command "insert" "edge" '(44 -42) 1 1 0 )
(command "insert" "edge" '(40 -47) 1 1 0 )
(command "insert" "edge" '(41 -46) 1 1 0 )
(command "insert" "edge" '(39 -44) 1 1 0 )
(command "insert" "edge" '(40 -43) 1 1 0 )
(command "insert" "edge" '(37 -45) 1 1 0 )
(command "insert" "edge" '(41 -42) 1 1 0 )
(command "insert" "edge" '(44 -43) 1 1 0 )
(command "insert" "edge" '(39 -43) 1 1 0 )
(command "insert" "edge" '(43 -44) 1 1 0 )
(command "insert" "edge" '(38 -46) 1 1 0 )
(command "insert" "edge" '(41 -45) 1 1 0 )
(command "insert" "edge" '(39 -47) 1 1 0 )
(command "insert" "edge" '(40 -44) 1 1 0 )
(command "insert" "edge" '(42 -42) 1 1 0 )
(command "insert" "edge" '(36 -45) 1 1 0 )
(command "insert" "edge" '(39 -42) 1 1 0 )
(command "insert" "edge" '(38 -47) 1 1 0 )
(command "insert" "edge" '(41 -44) 1 1 0 )
(command "layer" "m" "Res" "" )
(command "insert" "Res" '(49 -34) 1 1 0 )
(command "insert" "Res" '(50 -35) 1 1 0 )
(command "insert" "Res" '(50 -34) 1 1 0 )
(command "insert" "Res" '(48 -35) 1 1 0 )
(command "insert" "Res" '(49 -33) 1 1 0 )
(command "insert" "Res" '(48 -34) 1 1 0 )
(command "insert" "Res" '(48 -33) 1 1 0 )
(command "insert" "Res" '(49 -35) 1 1 0 )
(command "insert" "Res" '(50 -33) 1 1 0 )
(command "layer" "m" "ped" "" )
(command "insert" "ped" '(229 -41) 1 1 0 )
(command "insert" "ped" '(228 -39) 1 1 0 )
(command "insert" "ped" '(228 -40) 1 1 0 )
(command "insert" "ped" '(226 -40) 1 1 0 )
(command "insert" "ped" '(230 -41) 1 1 0 )
(command "insert" "ped" '(227 -41) 1 1 0 )
(command "insert" "ped" '(225 -41) 1 1 0 )
(command "insert" "ped" '(227 -39) 1 1 0 )
(command "insert" "ped" '(229 -40) 1 1 0 )
(command "insert" "ped" '(226 -39) 1 1 0 )
(command "insert" "ped" '(230 -39) 1 1 0 )
(command "insert" "ped" '(230 -40) 1 1 0 )
(command "insert" "ped" '(226 -41) 1 1 0 )
(command "insert" "ped" '(229 -39) 1 1 0 )
(command "insert" "ped" '(228 -41) 1 1 0 )
(command "insert" "ped" '(227 -40) 1 1 0 )
(command "insert" "ped" '(225 -40) 1 1 0 )
(command "insert" "ped" '(225 -39) 1 1 0 )
(command "layer" "m" "Commmer" "" )
(command "insert" "Commmer" '(32 -1) 1 1 0 )
(command "insert" "Commmer" '(23 -1) 1 1 0 )
(command "insert" "Commmer" '(21 -2) 1 1 0 )
(command "insert" "Commmer" '(16 -2) 1 1 0 )
(command "insert" "Commmer" '(15 -1) 1 1 0 )
(command "insert" "Commmer" '(28 -1) 1 1 0 )
(command "insert" "Commmer" '(25 -1) 1 1 0 )
(command "insert" "Commmer" '(27 -2) 1 1 0 )
(command "insert" "Commmer" '(32 -2) 1 1 0 )
(command "insert" "Commmer" '(18 -1) 1 1 0 )
(command "insert" "Commmer" '(31 -1) 1 1 0 )
(command "insert" "Commmer" '(22 -2) 1 1 0 )
(command "insert" "Commmer" '(21 -1) 1 1 0 )
(command "insert" "Commmer" '(23 -2) 1 1 0 )
(command "insert" "Commmer" '(17 -2) 1 1 0 )
(command "insert" "Commmer" '(28 -2) 1 1 0 )
(command "insert" "Commmer" '(34 -1) 1 1 0 )
(command "insert" "Commmer" '(24 -1) 1 1 0 )
(command "insert" "Commmer" '(33 -2) 1 1 0 )
(command "insert" "Commmer" '(30 -1) 1 1 0 )
(command "insert" "Commmer" '(27 -1) 1 1 0 )
(command "insert" "Commmer" '(18 -2) 1 1 0 )
(command "insert" "Commmer" '(20 -1) 1 1 0 )
(command "insert" "Commmer" '(17 -1) 1 1 0 )
(command "insert" "Commmer" '(19 -2) 1 1 0 )
(command "insert" "Commmer" '(29 -2) 1 1 0 )
(command "insert" "Commmer" '(24 -2) 1 1 0 )
(command "insert" "Commmer" '(34 -2) 1 1 0 )
(command "insert" "Commmer" '(35 -1) 1 1 0 )
(command "insert" "Commmer" '(26 -2) 1 1 0 )
(command "insert" "Commmer" '(33 -1) 1 1 0 )
(command "insert" "Commmer" '(35 -2) 1 1 0 )
(command "insert" "Commmer" '(26 -1) 1 1 0 )
(command "insert" "Commmer" '(15 -2) 1 1 0 )
(command "insert" "Commmer" '(20 -2) 1 1 0 )
(command "insert" "Commmer" '(30 -2) 1 1 0 )
(command "insert" "Commmer" '(16 -1) 1 1 0 )
(command "insert" "Commmer" '(29 -1) 1 1 0 )
(command "insert" "Commmer" '(31 -2) 1 1 0 )
(command "insert" "Commmer" '(25 -2) 1 1 0 )
(command "insert" "Commmer" '(22 -1) 1 1 0 )
(command "insert" "Commmer" '(19 -1) 1 1 0 )
(command "layer" "m" "Res" "" )
(command "insert" "Res" '(277 -89) 1 1 0 )
(command "insert" "Res" '(278 -89) 1 1 0 )
(command "insert" "Res" '(278 -87) 1 1 0 )
(command "insert" "Res" '(278 -88) 1 1 0 )
(command "insert" "Res" '(276 -88) 1 1 0 )
(command "insert" "Res" '(277 -87) 1 1 0 )
(command "insert" "Res" '(276 -87) 1 1 0 )
(command "insert" "Res" '(276 -89) 1 1 0 )
(command "insert" "Res" '(277 -88) 1 1 0 )
(command "layer" "m" "Commmer" "" )
(command "insert" "Commmer" '(76 -27) 1 1 0 )
(command "insert" "Commmer" '(74 -29) 1 1 0 )
(command "insert" "Commmer" '(70 -28) 1 1 0 )
(command "insert" "Commmer" '(75 -28) 1 1 0 )
(command "insert" "Commmer" '(73 -29) 1 1 0 )
(command "insert" "Commmer" '(77 -28) 1 1 0 )
(command "insert" "Commmer" '(70 -27) 1 1 0 )
(command "insert" "Commmer" '(72 -28) 1 1 0 )
(command "insert" "Commmer" '(76 -29) 1 1 0 )
(command "insert" "Commmer" '(77 -27) 1 1 0 )
(command "insert" "Commmer" '(69 -28) 1 1 0 )
(command "insert" "Commmer" '(71 -29) 1 1 0 )
(command "insert" "Commmer" '(74 -28) 1 1 0 )
(command "insert" "Commmer" '(73 -27) 1 1 0 )
(command "insert" "Commmer" '(70 -29) 1 1 0 )
(command "insert" "Commmer" '(73 -28) 1 1 0 )
(command "insert" "Commmer" '(75 -29) 1 1 0 )
(command "insert" "Commmer" '(71 -27) 1 1 0 )
(command "insert" "Commmer" '(72 -29) 1 1 0 )
(command "insert" "Commmer" '(75 -27) 1 1 0 )
(command "insert" "Commmer" '(69 -27) 1 1 0 )
(command "insert" "Commmer" '(71 -28) 1 1 0 )
(command "insert" "Commmer" '(74 -27) 1 1 0 )
(command "insert" "Commmer" '(72 -27) 1 1 0 )
(command "insert" "Commmer" '(76 -28) 1 1 0 )
(command "insert" "Commmer" '(69 -29) 1 1 0 )
(command "insert" "Commmer" '(77 -29) 1 1 0 )
(command "layer" "m" "Commmer" "" )
(command "insert" "Commmer" '(47 -24) 1 1 0 )
(command "insert" "Commmer" '(45 -25) 1 1 0 )
(command "insert" "Commmer" '(46 -25) 1 1 0 )
(command "insert" "Commmer" '(42 -25) 1 1 0 )
(command "insert" "Commmer" '(44 -24) 1 1 0 )
(command "insert" "Commmer" '(43 -24) 1 1 0 )
(command "insert" "Commmer" '(42 -27) 1 1 0 )
(command "insert" "Commmer" '(43 -27) 1 1 0 )
(command "insert" "Commmer" '(42 -29) 1 1 0 )
(command "insert" "Commmer" '(43 -25) 1 1 0 )
(command "insert" "Commmer" '(43 -29) 1 1 0 )
(command "insert" "Commmer" '(44 -28) 1 1 0 )
(command "insert" "Commmer" '(44 -27) 1 1 0 )
(command "insert" "Commmer" '(45 -24) 1 1 0 )
(command "insert" "Commmer" '(47 -25) 1 1 0 )
(command "insert" "Commmer" '(43 -28) 1 1 0 )
(command "insert" "Commmer" '(46 -24) 1 1 0 )
(command "insert" "Commmer" '(44 -25) 1 1 0 )
(command "insert" "Commmer" '(43 -26) 1 1 0 )
(command "insert" "Commmer" '(46 -26) 1 1 0 )
(command "insert" "Commmer" '(42 -26) 1 1 0 )
(command "insert" "Commmer" '(44 -29) 1 1 0 )
(command "insert" "Commmer" '(45 -26) 1 1 0 )
(command "insert" "Commmer" '(44 -26) 1 1 0 )
(command "insert" "Commmer" '(42 -28) 1 1 0 )
(command "insert" "Commmer" '(47 -26) 1 1 0 )
(command "insert" "Commmer" '(42 -24) 1 1 0 )
(command "layer" "m" "Res" "" )
(command "insert" "Res" '(295 -84) 1 1 0 )
(command "insert" "Res" '(295 -85) 1 1 0 )
(command "insert" "Res" '(296 -86) 1 1 0 )
(command "insert" "Res" '(296 -85) 1 1 0 )
(command "insert" "Res" '(294 -85) 1 1 0 )
(command "insert" "Res" '(296 -84) 1 1 0 )
(command "insert" "Res" '(294 -84) 1 1 0 )
(command "insert" "Res" '(294 -86) 1 1 0 )
(command "insert" "Res" '(295 -86) 1 1 0 )
(command "layer" "m" "Res" "" )
(command "insert" "Res" '(172 -53) 1 1 0 )
(command "insert" "Res" '(172 -52) 1 1 0 )
(command "insert" "Res" '(173 -51) 1 1 0 )
(command "insert" "Res" '(172 -51) 1 1 0 )
(command "insert" "Res" '(171 -51) 1 1 0 )
(command "insert" "Res" '(171 -52) 1 1 0 )
(command "insert" "Res" '(171 -53) 1 1 0 )
(command "insert" "Res" '(173 -52) 1 1 0 )
(command "insert" "Res" '(173 -53) 1 1 0 )
(command "layer" "m" "Commmer" "" )
(command "insert" "Commmer" '(25 -29) 1 1 0 )
(command "insert" "Commmer" '(21 -26) 1 1 0 )
(command "insert" "Commmer" '(22 -24) 1 1 0 )
(command "insert" "Commmer" '(24 -28) 1 1 0 )
(command "insert" "Commmer" '(22 -26) 1 1 0 )
(command "insert" "Commmer" '(26 -28) 1 1 0 )
(command "insert" "Commmer" '(25 -27) 1 1 0 )
(command "insert" "Commmer" '(23 -26) 1 1 0 )
(command "insert" "Commmer" '(24 -29) 1 1 0 )
(command "insert" "Commmer" '(23 -24) 1 1 0 )
(command "insert" "Commmer" '(25 -28) 1 1 0 )
(command "insert" "Commmer" '(21 -25) 1 1 0 )
(command "insert" "Commmer" '(22 -25) 1 1 0 )
(command "insert" "Commmer" '(26 -27) 1 1 0 )
(command "insert" "Commmer" '(26 -29) 1 1 0 )
(command "insert" "Commmer" '(24 -27) 1 1 0 )
(command "insert" "Commmer" '(21 -24) 1 1 0 )
(command "insert" "Commmer" '(23 -25) 1 1 0 )
(command "layer" "m" "edge" "" )
(command "insert" "edge" '(45 -1) 1 1 0 )
(command "insert" "edge" '(47 -2) 1 1 0 )
(command "insert" "edge" '(44 -2) 1 1 0 )
(command "insert" "edge" '(41 -2) 1 1 0 )
(command "insert" "edge" '(38 -1) 1 1 0 )
(command "insert" "edge" '(46 -1) 1 1 0 )
(command "insert" "edge" '(43 -1) 1 1 0 )
(command "insert" "edge" '(36 -2) 1 1 0 )
(command "insert" "edge" '(45 -2) 1 1 0 )
(command "insert" "edge" '(37 -2) 1 1 0 )
(command "insert" "edge" '(42 -2) 1 1 0 )
(command "insert" "edge" '(41 -1) 1 1 0 )
(command "insert" "edge" '(44 -1) 1 1 0 )
(command "insert" "edge" '(40 -2) 1 1 0 )
(command "insert" "edge" '(39 -1) 1 1 0 )
(command "insert" "edge" '(36 -1) 1 1 0 )
(command "insert" "edge" '(43 -2) 1 1 0 )
(command "insert" "edge" '(47 -1) 1 1 0 )
(command "insert" "edge" '(40 -1) 1 1 0 )
(command "insert" "edge" '(38 -2) 1 1 0 )
(command "insert" "edge" '(42 -1) 1 1 0 )
(command "insert" "edge" '(37 -1) 1 1 0 )
(command "insert" "edge" '(46 -2) 1 1 0 )
(command "insert" "edge" '(39 -2) 1 1 0 )
(command "layer" "m" "Idust" "" )
(command "insert" "Idust" '(12 -20) 1 1 0 )
(command "insert" "Idust" '(14 -19) 1 1 0 )
(command "insert" "Idust" '(14 -18) 1 1 0 )
(command "insert" "Idust" '(12 -19) 1 1 0 )
(command "insert" "Idust" '(12 -18) 1 1 0 )
(command "insert" "Idust" '(13 -18) 1 1 0 )
(command "insert" "Idust" '(13 -19) 1 1 0 )
(command "insert" "Idust" '(14 -20) 1 1 0 )
(command "insert" "Idust" '(13 -20) 1 1 0 )
(command "layer" "m" "edge" "" )
(command "insert" "edge" '(184 -105) 1 1 0 )
(command "insert" "edge" '(185 -107) 1 1 0 )
(command "insert" "edge" '(183 -106) 1 1 0 )
(command "insert" "edge" '(188 -106) 1 1 0 )
(command "insert" "edge" '(186 -106) 1 1 0 )
(command "insert" "edge" '(183 -104) 1 1 0 )
(command "insert" "edge" '(186 -105) 1 1 0 )
(command "insert" "edge" '(185 -103) 1 1 0 )
(command "insert" "edge" '(184 -104) 1 1 0 )
(command "insert" "edge" '(186 -107) 1 1 0 )
(command "insert" "edge" '(187 -107) 1 1 0 )
(command "insert" "edge" '(184 -107) 1 1 0 )
(command "insert" "edge" '(187 -105) 1 1 0 )
(command "insert" "edge" '(185 -104) 1 1 0 )
(command "insert" "edge" '(185 -106) 1 1 0 )
(command "insert" "edge" '(188 -107) 1 1 0 )
(command "insert" "edge" '(184 -103) 1 1 0 )
(command "insert" "edge" '(183 -107) 1 1 0 )
(command "insert" "edge" '(185 -102) 1 1 0 )
(command "insert" "edge" '(183 -105) 1 1 0 )
(command "insert" "edge" '(183 -103) 1 1 0 )
(command "insert" "edge" '(187 -106) 1 1 0 )
(command "insert" "edge" '(188 -105) 1 1 0 )
(command "insert" "edge" '(184 -102) 1 1 0 )
(command "insert" "edge" '(183 -102) 1 1 0 )
(command "insert" "edge" '(184 -106) 1 1 0 )
(command "insert" "edge" '(185 -105) 1 1 0 )
(command "layer" "m" "Res" "" )
(command "insert" "Res" '(92 -37) 1 1 0 )
(command "insert" "Res" '(96 -33) 1 1 0 )
(command "insert" "Res" '(97 -35) 1 1 0 )
(command "insert" "Res" '(94 -34) 1 1 0 )
(command "insert" "Res" '(98 -33) 1 1 0 )
(command "insert" "Res" '(93 -33) 1 1 0 )
(command "insert" "Res" '(90 -37) 1 1 0 )
(command "insert" "Res" '(98 -35) 1 1 0 )
(command "insert" "Res" '(95 -34) 1 1 0 )
(command "insert" "Res" '(91 -37) 1 1 0 )
(command "insert" "Res" '(96 -35) 1 1 0 )
(command "insert" "Res" '(92 -38) 1 1 0 )
(command "insert" "Res" '(97 -34) 1 1 0 )
(command "insert" "Res" '(93 -34) 1 1 0 )
(command "insert" "Res" '(94 -33) 1 1 0 )
(command "insert" "Res" '(92 -36) 1 1 0 )
(command "insert" "Res" '(93 -35) 1 1 0 )
(command "insert" "Res" '(94 -35) 1 1 0 )
(command "insert" "Res" '(91 -38) 1 1 0 )
(command "insert" "Res" '(97 -33) 1 1 0 )
(command "insert" "Res" '(91 -36) 1 1 0 )
(command "insert" "Res" '(90 -36) 1 1 0 )
(command "insert" "Res" '(98 -34) 1 1 0 )
(command "insert" "Res" '(95 -35) 1 1 0 )
(command "insert" "Res" '(90 -38) 1 1 0 )
(command "insert" "Res" '(96 -34) 1 1 0 )
(command "insert" "Res" '(95 -33) 1 1 0 )
(command "layer" "m" "mroads" "" )
(command "insert" "mroads" '(5 -31) 1 1 0 )
(command "insert" "mroads" '(66 -31) 1 1 0 )
(command "insert" "mroads" '(6 -28) 1 1 0 )
(command "insert" "mroads" '(67 -30) 1 1 0 )
(command "insert" "mroads" '(7 -25) 1 1 0 )
(command "insert" "mroads" '(22 -19) 1 1 0 )
(command "insert" "mroads" '(18 -19) 1 1 0 )
(command "insert" "mroads" '(38 -21) 1 1 0 )
(command "insert" "mroads" '(114 -31) 1 1 0 )
(command "insert" "mroads" '(13 -32) 1 1 0 )
(command "insert" "mroads" '(35 -15) 1 1 0 )
(command "insert" "mroads" '(14 -31) 1 1 0 )
(command "insert" "mroads" '(15 -30) 1 1 0 )
(command "insert" "mroads" '(35 -21) 1 1 0 )
(command "insert" "mroads" '(12 -17) 1 1 0 )
(command "insert" "mroads" '(36 -22) 1 1 0 )
(command "insert" "mroads" '(1 -28) 1 1 0 )
(command "insert" "mroads" '(40 -22) 1 1 0 )
(command "insert" "mroads" '(39 -16) 1 1 0 )
(command "insert" "mroads" '(63 -30) 1 1 0 )
(command "insert" "mroads" '(37 -23) 1 1 0 )
(command "insert" "mroads" '(2 -27) 1 1 0 )
(command "insert" "mroads" '(109 -32) 1 1 0 )
(command "insert" "mroads" '(29 -17) 1 1 0 )
(command "insert" "mroads" '(31 -15) 1 1 0 )
(command "insert" "mroads" '(5 -24) 1 1 0 )
(command "insert" "mroads" '(20 -32) 1 1 0 )
(command "insert" "mroads" '(6 -23) 1 1 0 )
(command "insert" "mroads" '(30 -16) 1 1 0 )
(command "insert" "mroads" '(28 -32) 1 1 0 )
(command "insert" "mroads" '(7 -22) 1 1 0 )
(command "insert" "mroads" '(41 -23) 1 1 0 )
(command "insert" "mroads" '(42 -31) 1 1 0 )
(command "insert" "mroads" '(23 -19) 1 1 0 )
(command "insert" "mroads" '(21 -15) 1 1 0 )
(command "insert" "mroads" '(43 -30) 1 1 0 )
(command "insert" "mroads" '(116 -32) 1 1 0 )
(command "insert" "mroads" '(8 -18) 1 1 0 )
(command "insert" "mroads" '(11 -15) 1 1 0 )
(command "insert" "mroads" '(35 -26) 1 1 0 )
(command "insert" "mroads" '(9 -19) 1 1 0 )
(command "insert" "mroads" '(36 -29) 1 1 0 )
(command "insert" "mroads" '(1 -21) 1 1 0 )
(command "insert" "mroads" '(25 -16) 1 1 0 )
(command "insert" "mroads" '(29 -20) 1 1 0 )
(command "insert" "mroads" '(37 -16) 1 1 0 )
(command "insert" "mroads" '(98 -30) 1 1 0 )
(command "insert" "mroads" '(38 -31) 1 1 0 )
(command "insert" "mroads" '(99 -31) 1 1 0 )
(command "insert" "mroads" '(39 -30) 1 1 0 )
(command "insert" "mroads" '(3 -17) 1 1 0 )
(command "insert" "mroads" '(19 -18) 1 1 0 )
(command "insert" "mroads" '(7 -15) 1 1 0 )
(command "insert" "mroads" '(31 -18) 1 1 0 )
(command "insert" "mroads" '(46 -30) 1 1 0 )
(command "insert" "mroads" '(6 -32) 1 1 0 )
(command "insert" "mroads" '(34 -32) 1 1 0 )
(command "insert" "mroads" '(32 -16) 1 1 0 )
(command "insert" "mroads" '(94 -30) 1 1 0 )
(command "insert" "mroads" '(18 -31) 1 1 0 )
(command "insert" "mroads" '(42 -32) 1 1 0 )
(command "insert" "mroads" '(86 -32) 1 1 0 )
(command "insert" "mroads" '(34 -26) 1 1 0 )
(command "insert" "mroads" '(8 -25) 1 1 0 )
(command "insert" "mroads" '(94 -32) 1 1 0 )
(command "insert" "mroads" '(9 -20) 1 1 0 )
(command "insert" "mroads" '(10 -19) 1 1 0 )
(command "insert" "mroads" '(37 -25) 1 1 0 )
(command "insert" "mroads" '(26 -30) 1 1 0 )
(command "insert" "mroads" '(7 -18) 1 1 0 )
(command "insert" "mroads" '(38 -22) 1 1 0 )
(command "insert" "mroads" '(27 -31) 1 1 0 )
(command "insert" "mroads" '(6 -30) 1 1 0 )
(command "insert" "mroads" '(39 -23) 1 1 0 )
(command "insert" "mroads" '(88 -31) 1 1 0 )
(command "insert" "mroads" '(74 -30) 1 1 0 )
(command "insert" "mroads" '(89 -30) 1 1 0 )
(command "insert" "mroads" '(3 -22) 1 1 0 )
(command "insert" "mroads" '(75 -31) 1 1 0 )
(command "insert" "mroads" '(4 -17) 1 1 0 )
(command "insert" "mroads" '(5 -20) 1 1 0 )
(command "insert" "mroads" '(6 -27) 1 1 0 )
(command "insert" "mroads" '(21 -17) 1 1 0 )
(command "insert" "mroads" '(17 -17) 1 1 0 )
(command "insert" "mroads" '(22 -30) 1 1 0 )
(command "insert" "mroads" '(33 -22) 1 1 0 )
(command "insert" "mroads" '(23 -31) 1 1 0 )
(command "insert" "mroads" '(12 -32) 1 1 0 )
(command "insert" "mroads" '(34 -21) 1 1 0 )
(command "insert" "mroads" '(70 -30) 1 1 0 )
(command "insert" "mroads" '(85 -30) 1 1 0 )
(command "insert" "mroads" '(48 -32) 1 1 0 )
(command "insert" "mroads" '(71 -31) 1 1 0 )
(command "insert" "mroads" '(34 -15) 1 1 0 )
(command "insert" "mroads" '(11 -19) 1 1 0 )
(command "insert" "mroads" '(100 -32) 1 1 0 )
(command "insert" "mroads" '(27 -20) 1 1 0 )
(command "insert" "mroads" '(1 -25) 1 1 0 )
(command "insert" "mroads" '(108 -32) 1 1 0 )
(command "insert" "mroads" '(2 -30) 1 1 0 )
(command "insert" "mroads" '(3 -31) 1 1 0 )
(command "insert" "mroads" '(64 -31) 1 1 0 )
(command "insert" "mroads" '(4 -24) 1 1 0 )
(command "insert" "mroads" '(19 -32) 1 1 0 )
(command "insert" "mroads" '(62 -31) 1 1 0 )
(command "insert" "mroads" '(50 -30) 1 1 0 )
(command "insert" "mroads" '(65 -30) 1 1 0 )
(command "insert" "mroads" '(5 -29) 1 1 0 )
(command "insert" "mroads" '(27 -32) 1 1 0 )
(command "insert" "mroads" '(6 -18) 1 1 0 )
(command "insert" "mroads" '(101 -32) 1 1 0 )
(command "insert" "mroads" '(112 -31) 1 1 0 )
(command "insert" "mroads" '(41 -21) 1 1 0 )
(command "insert" "mroads" '(22 -17) 1 1 0 )
(command "insert" "mroads" '(25 -15) 1 1 0 )
(command "insert" "mroads" '(79 -32) 1 1 0 )
(command "insert" "mroads" '(18 -17) 1 1 0 )
(command "insert" "mroads" '(23 -20) 1 1 0 )
(command "insert" "mroads" '(6 -21) 1 1 0 )
(command "insert" "mroads" '(115 -32) 1 1 0 )
(command "insert" "mroads" '(60 -31) 1 1 0 )
(command "insert" "mroads" '(61 -30) 1 1 0 )
(command "insert" "mroads" '(35 -23) 1 1 0 )
(command "insert" "mroads" '(24 -16) 1 1 0 )
(command "insert" "mroads" '(36 -16) 1 1 0 )
(command "insert" "mroads" '(108 -31) 1 1 0 )
(command "insert" "mroads" '(37 -21) 1 1 0 )
(command "insert" "mroads" '(2 -25) 1 1 0 )
(command "insert" "mroads" '(109 -30) 1 1 0 )
(command "insert" "mroads" '(7 -16) 1 1 0 )
(command "insert" "mroads" '(38 -26) 1 1 0 )
(command "insert" "mroads" '(6 -24) 1 1 0 )
(command "insert" "mroads" '(114 -32) 1 1 0 )
(command "insert" "mroads" '(116 -30) 1 1 0 )
(command "insert" "mroads" '(40 -31) 1 1 0 )
(command "insert" "mroads" '(111 -31) 1 1 0 )
(command "insert" "mroads" '(19 -15) 1 1 0 )
(command "insert" "mroads" '(41 -30) 1 1 0 )
(command "insert" "mroads" '(5 -32) 1 1 0 )
(command "insert" "mroads" '(33 -32) 1 1 0 )
(command "insert" "mroads" '(41 -32) 1 1 0 )
(command "insert" "mroads" '(7 -29) 1 1 0 )
(command "insert" "mroads" '(43 -32) 1 1 0 )
(command "insert" "mroads" '(85 -32) 1 1 0 )
(command "insert" "mroads" '(9 -15) 1 1 0 )
(command "insert" "mroads" '(33 -26) 1 1 0 )
(command "insert" "mroads" '(22 -31) 1 1 0 )
(command "insert" "mroads" '(93 -32) 1 1 0 )
(command "insert" "mroads" '(8 -20) 1 1 0 )
(command "insert" "mroads" '(7 -31) 1 1 0 )
(command "insert" "mroads" '(80 -32) 1 1 0 )
(command "insert" "mroads" '(35 -28) 1 1 0 )
(command "insert" "mroads" '(9 -17) 1 1 0 )
(command "insert" "mroads" '(96 -30) 1 1 0 )
(command "insert" "mroads" '(36 -31) 1 1 0 )
(command "insert" "mroads" '(15 -15) 1 1 0 )
(command "insert" "mroads" '(97 -31) 1 1 0 )
(command "insert" "mroads" '(37 -30) 1 1 0 )
(command "insert" "mroads" '(38 -29) 1 1 0 )
(command "insert" "mroads" '(83 -31) 1 1 0 )
(command "insert" "mroads" '(39 -24) 1 1 0 )
(command "insert" "mroads" '(5 -15) 1 1 0 )
(command "insert" "mroads" '(3 -19) 1 1 0 )
(command "insert" "mroads" '(4 -20) 1 1 0 )
(command "insert" "mroads" '(19 -20) 1 1 0 )
(command "insert" "mroads" '(92 -30) 1 1 0 )
(command "insert" "mroads" '(16 -31) 1 1 0 )
(command "insert" "mroads" '(93 -31) 1 1 0 )
(command "insert" "mroads" '(17 -30) 1 1 0 )
(command "insert" "mroads" '(32 -18) 1 1 0 )
(command "insert" "mroads" '(11 -32) 1 1 0 )
(command "insert" "mroads" '(33 -19) 1 1 0 )
(command "insert" "mroads" '(40 -29) 1 1 0 )
(command "insert" "mroads" '(8 -27) 1 1 0 )
(command "insert" "mroads" '(63 -32) 1 1 0 )
(command "insert" "mroads" '(5 -21) 1 1 0 )
(command "insert" "mroads" '(24 -30) 1 1 0 )
(command "insert" "mroads" '(14 -17) 1 1 0 )
(command "insert" "mroads" '(71 -32) 1 1 0 )
(command "insert" "mroads" '(10 -17) 1 1 0 )
(command "insert" "mroads" '(25 -31) 1 1 0 )
(command "insert" "mroads" '(99 -32) 1 1 0 )
(command "insert" "mroads" '(70 -31) 1 1 0 )
(command "insert" "mroads" '(107 -32) 1 1 0 )
(command "insert" "mroads" '(38 -20) 1 1 0 )
(command "insert" "mroads" '(12 -31) 1 1 0 )
(command "insert" "mroads" '(27 -17) 1 1 0 )
(command "insert" "mroads" '(39 -17) 1 1 0 )
(command "insert" "mroads" '(13 -30) 1 1 0 )
(command "insert" "mroads" '(41 -24) 1 1 0 )
(command "insert" "mroads" '(3 -24) 1 1 0 )
(command "insert" "mroads" '(56 -32) 1 1 0 )
(command "insert" "mroads" '(4 -19) 1 1 0 )
(command "insert" "mroads" '(26 -32) 1 1 0 )
(command "insert" "mroads" '(5 -18) 1 1 0 )
(command "insert" "mroads" '(20 -30) 1 1 0 )
(command "insert" "mroads" '(6 -25) 1 1 0 )
(command "insert" "mroads" '(21 -31) 1 1 0 )
(command "insert" "mroads" '(78 -32) 1 1 0 )
(command "insert" "mroads" '(41 -18) 1 1 0 )
(command "insert" "mroads" '(18 -20) 1 1 0 )
(command "insert" "mroads" '(33 -20) 1 1 0 )
(command "insert" "mroads" '(69 -31) 1 1 0 )
(command "insert" "mroads" '(34 -19) 1 1 0 )
(command "insert" "mroads" '(32 -15) 1 1 0 )
(command "insert" "mroads" '(15 -32) 1 1 0 )
(command "insert" "mroads" '(64 -32) 1 1 0 )
(command "insert" "mroads" '(35 -16) 1 1 0 )
(command "insert" "mroads" '(38 -15) 1 1 0 )
(command "insert" "mroads" '(77 -32) 1 1 0 )
(command "insert" "mroads" '(1 -31) 1 1 0 )
(command "insert" "mroads" '(28 -17) 1 1 0 )
(command "insert" "mroads" '(2 -28) 1 1 0 )
(command "insert" "mroads" '(48 -30) 1 1 0 )
(command "insert" "mroads" '(113 -32) 1 1 0 )
(command "insert" "mroads" '(49 -31) 1 1 0 )
(command "insert" "mroads" '(4 -26) 1 1 0 )
(command "insert" "mroads" '(28 -15) 1 1 0 )
(command "insert" "mroads" '(5 -27) 1 1 0 )
(command "insert" "mroads" '(40 -26) 1 1 0 )
(command "insert" "mroads" '(4 -32) 1 1 0 )
(command "insert" "mroads" '(7 -21) 1 1 0 )
(command "insert" "mroads" '(18 -15) 1 1 0 )
(command "insert" "mroads" '(40 -32) 1 1 0 )
(command "insert" "mroads" '(34 -20) 1 1 0 )
(command "insert" "mroads" '(58 -31) 1 1 0 )
(command "insert" "mroads" '(44 -30) 1 1 0 )
(command "insert" "mroads" '(59 -30) 1 1 0 )
(command "insert" "mroads" '(92 -32) 1 1 0 )
(command "insert" "mroads" '(45 -31) 1 1 0 )
(command "insert" "mroads" '(6 -17) 1 1 0 )
(command "insert" "mroads" '(106 -31) 1 1 0 )
(command "insert" "mroads" '(35 -25) 1 1 0 )
(command "insert" "mroads" '(24 -18) 1 1 0 )
(command "insert" "mroads" '(107 -30) 1 1 0 )
(command "insert" "mroads" '(36 -18) 1 1 0 )
(command "insert" "mroads" '(25 -19) 1 1 0 )
(command "insert" "mroads" '(13 -16) 1 1 0 )
(command "insert" "mroads" '(37 -19) 1 1 0 )
(command "insert" "mroads" '(2 -23) 1 1 0 )
(command "insert" "mroads" '(38 -24) 1 1 0 )
(command "insert" "mroads" '(39 -29) 1 1 0 )
(command "insert" "mroads" '(54 -31) 1 1 0 )
(command "insert" "mroads" '(115 -31) 1 1 0 )
(command "insert" "mroads" '(55 -30) 1 1 0 )
(command "insert" "mroads" '(56 -30) 1 1 0 )
(command "insert" "mroads" '(30 -20) 1 1 0 )
(command "insert" "mroads" '(19 -17) 1 1 0 )
(command "insert" "mroads" '(102 -31) 1 1 0 )
(command "insert" "mroads" '(41 -28) 1 1 0 )
(command "insert" "mroads" '(31 -17) 1 1 0 )
(command "insert" "mroads" '(103 -30) 1 1 0 )
(command "insert" "mroads" '(10 -32) 1 1 0 )
(command "insert" "mroads" '(18 -32) 1 1 0 )
(command "insert" "mroads" '(33 -24) 1 1 0 )
(command "insert" "mroads" '(62 -32) 1 1 0 )
(command "insert" "mroads" '(110 -30) 1 1 0 )
(command "insert" "mroads" '(34 -31) 1 1 0 )
(command "insert" "mroads" '(8 -22) 1 1 0 )
(command "insert" "mroads" '(23 -17) 1 1 0 )
(command "insert" "mroads" '(70 -32) 1 1 0 )
(command "insert" "mroads" '(35 -30) 1 1 0 )
(command "insert" "mroads" '(98 -32) 1 1 0 )
(command "insert" "mroads" '(36 -25) 1 1 0 )
(command "insert" "mroads" '(10 -20) 1 1 0 )
(command "insert" "mroads" '(25 -20) 1 1 0 )
(command "insert" "mroads" '(82 -31) 1 1 0 )
(command "insert" "mroads" '(106 -32) 1 1 0 )
(command "insert" "mroads" '(37 -28) 1 1 0 )
(command "insert" "mroads" '(26 -19) 1 1 0 )
(command "insert" "mroads" '(38 -19) 1 1 0 )
(command "insert" "mroads" '(3 -15) 1 1 0 )
(command "insert" "mroads" '(39 -26) 1 1 0 )
(command "insert" "mroads" '(51 -31) 1 1 0 )
(command "insert" "mroads" '(79 -30) 1 1 0 )
(command "insert" "mroads" '(3 -21) 1 1 0 )
(command "insert" "mroads" '(25 -32) 1 1 0 )
(command "insert" "mroads" '(90 -30) 1 1 0 )
(command "insert" "mroads" '(30 -31) 1 1 0 )
(command "insert" "mroads" '(4 -22) 1 1 0 )
(command "insert" "mroads" '(91 -31) 1 1 0 )
(command "insert" "mroads" '(31 -30) 1 1 0 )
(command "insert" "mroads" '(5 -23) 1 1 0 )
(command "insert" "mroads" '(20 -17) 1 1 0 )
(command "insert" "mroads" '(16 -17) 1 1 0 )
(command "insert" "mroads" '(21 -20) 1 1 0 )
(command "insert" "mroads" '(32 -20) 1 1 0 )
(command "insert" "mroads" '(33 -17) 1 1 0 )
(command "insert" "mroads" '(34 -22) 1 1 0 )
(command "insert" "mroads" '(8 -29) 1 1 0 )
(command "insert" "mroads" '(86 -30) 1 1 0 )
(command "insert" "mroads" '(10 -31) 1 1 0 )
(command "insert" "mroads" '(6 -19) 1 1 0 )
(command "insert" "mroads" '(87 -31) 1 1 0 )
(command "insert" "mroads" '(11 -30) 1 1 0 )
(command "insert" "mroads" '(76 -32) 1 1 0 )
(command "insert" "mroads" '(27 -19) 1 1 0 )
(command "insert" "mroads" '(39 -19) 1 1 0 )
(command "insert" "mroads" '(28 -20) 1 1 0 )
(command "insert" "mroads" '(3 -26) 1 1 0 )
(command "insert" "mroads" '(40 -15) 1 1 0 )
(command "insert" "mroads" '(4 -29) 1 1 0 )
(command "insert" "mroads" '(19 -31) 1 1 0 )
(command "insert" "mroads" '(41 -20) 1 1 0 )
(command "insert" "mroads" '(5 -16) 1 1 0 )
(command "insert" "mroads" '(3 -32) 1 1 0 )
(command "insert" "mroads" '(66 -30) 1 1 0 )
(command "insert" "mroads" '(40 -21) 1 1 0 )
(command "insert" "mroads" '(67 -31) 1 1 0 )
(command "insert" "mroads" '(7 -30) 1 1 0 )
(command "insert" "mroads" '(22 -18) 1 1 0 )
(command "insert" "mroads" '(55 -32) 1 1 0 )
(command "insert" "mroads" '(18 -18) 1 1 0 )
(command "insert" "mroads" '(83 -32) 1 1 0 )
(command "insert" "mroads" '(114 -30) 1 1 0 )
(command "insert" "mroads" '(34 -17) 1 1 0 )
(command "insert" "mroads" '(6 -16) 1 1 0 )
(command "insert" "mroads" '(91 -32) 1 1 0 )
(command "insert" "mroads" '(14 -30) 1 1 0 )
(command "insert" "mroads" '(36 -15) 1 1 0 )
(command "insert" "mroads" '(15 -31) 1 1 0 )
(command "insert" "mroads" '(35 -18) 1 1 0 )
(command "insert" "mroads" '(12 -16) 1 1 0 )
(command "insert" "mroads" '(36 -21) 1 1 0 )
(command "insert" "mroads" '(1 -29) 1 1 0 )
(command "insert" "mroads" '(63 -31) 1 1 0 )
(command "insert" "mroads" '(28 -19) 1 1 0 )
(command "insert" "mroads" '(2 -26) 1 1 0 )
(command "insert" "mroads" '(26 -15) 1 1 0 )
(command "insert" "mroads" '(12 -15) 1 1 0 )
(command "insert" "mroads" '(29 -18) 1 1 0 )
(command "insert" "mroads" '(5 -25) 1 1 0 )
(command "insert" "mroads" '(16 -15) 1 1 0 )
(command "insert" "mroads" '(6 -22) 1 1 0 )
(command "insert" "mroads" '(30 -19) 1 1 0 )
(command "insert" "mroads" '(41 -25) 1 1 0 )
(command "insert" "mroads" '(56 -31) 1 1 0 )
(command "insert" "mroads" '(9 -32) 1 1 0 )
(command "insert" "mroads" '(42 -30) 1 1 0 )
(command "insert" "mroads" '(23 -16) 1 1 0 )
(command "insert" "mroads" '(43 -31) 1 1 0 )
(command "insert" "mroads" '(17 -32) 1 1 0 )
(command "insert" "mroads" '(22 -15) 1 1 0 )
(command "insert" "mroads" '(61 -32) 1 1 0 )
(command "insert" "mroads" '(52 -30) 1 1 0 )
(command "insert" "mroads" '(105 -30) 1 1 0 )
(command "insert" "mroads" '(69 -32) 1 1 0 )
(command "insert" "mroads" '(34 -24) 1 1 0 )
(command "insert" "mroads" '(8 -17) 1 1 0 )
(command "insert" "mroads" '(97 -32) 1 1 0 )
(command "insert" "mroads" '(35 -27) 1 1 0 )
(command "insert" "mroads" '(24 -20) 1 1 0 )
(command "insert" "mroads" '(105 -32) 1 1 0 )
(command "insert" "mroads" '(36 -28) 1 1 0 )
(command "insert" "mroads" '(1 -22) 1 1 0 )
(command "insert" "mroads" '(6 -29) 1 1 0 )
(command "insert" "mroads" '(37 -17) 1 1 0 )
(command "insert" "mroads" '(2 -21) 1 1 0 )
(command "insert" "mroads" '(38 -30) 1 1 0 )
(command "insert" "mroads" '(53 -30) 1 1 0 )
(command "insert" "mroads" '(112 -32) 1 1 0 )
(command "insert" "mroads" '(39 -31) 1 1 0 )
(command "insert" "mroads" '(100 -31) 1 1 0 )
(command "insert" "mroads" '(24 -32) 1 1 0 )
(command "insert" "mroads" '(101 -30) 1 1 0 )
(command "insert" "mroads" '(19 -19) 1 1 0 )
(command "insert" "mroads" '(31 -19) 1 1 0 )
(command "insert" "mroads" '(20 -20) 1 1 0 )
(command "insert" "mroads" '(47 -31) 1 1 0 )
(command "insert" "mroads" '(32 -31) 1 1 0 )
(command "insert" "mroads" '(18 -30) 1 1 0 )
(command "insert" "mroads" '(33 -30) 1 1 0 )
(command "insert" "mroads" '(34 -29) 1 1 0 )
(command "insert" "mroads" '(8 -24) 1 1 0 )
(command "insert" "mroads" '(39 -32) 1 1 0 )
(command "insert" "mroads" '(80 -31) 1 1 0 )
(command "insert" "mroads" '(81 -30) 1 1 0 )
(command "insert" "mroads" '(36 -27) 1 1 0 )
(command "insert" "mroads" '(10 -18) 1 1 0 )
(command "insert" "mroads" '(75 -32) 1 1 0 )
(command "insert" "mroads" '(37 -26) 1 1 0 )
(command "insert" "mroads" '(26 -17) 1 1 0 )
(command "insert" "mroads" '(38 -17) 1 1 0 )
(command "insert" "mroads" '(39 -20) 1 1 0 )
(command "insert" "mroads" '(88 -30) 1 1 0 )
(command "insert" "mroads" '(28 -31) 1 1 0 )
(command "insert" "mroads" '(89 -31) 1 1 0 )
(command "insert" "mroads" '(29 -30) 1 1 0 )
(command "insert" "mroads" '(3 -23) 1 1 0 )
(command "insert" "mroads" '(4 -16) 1 1 0 )
(command "insert" "mroads" '(2 -32) 1 1 0 )
(command "insert" "mroads" '(76 -31) 1 1 0 )
(command "insert" "mroads" '(46 -32) 1 1 0 )
(command "insert" "mroads" '(20 -19) 1 1 0 )
(command "insert" "mroads" '(33 -29) 1 1 0 )
(command "insert" "mroads" '(77 -30) 1 1 0 )
(command "insert" "mroads" '(40 -16) 1 1 0 )
(command "insert" "mroads" '(21 -18) 1 1 0 )
(command "insert" "mroads" '(54 -32) 1 1 0 )
(command "insert" "mroads" '(33 -23) 1 1 0 )
(command "insert" "mroads" '(90 -32) 1 1 0 )
(command "insert" "mroads" '(84 -30) 1 1 0 )
(command "insert" "mroads" '(8 -31) 1 1 0 )
(command "insert" "mroads" '(95 -31) 1 1 0 )
(command "insert" "mroads" '(85 -31) 1 1 0 )
(command "insert" "mroads" '(9 -30) 1 1 0 )
(command "insert" "mroads" '(104 -32) 1 1 0 )
(command "insert" "mroads" '(15 -16) 1 1 0 )
(command "insert" "mroads" '(11 -16) 1 1 0 )
(command "insert" "mroads" '(1 -26) 1 1 0 )
(command "insert" "mroads" '(6 -31) 1 1 0 )
(command "insert" "mroads" '(73 -31) 1 1 0 )
(command "insert" "mroads" '(3 -28) 1 1 0 )
(command "insert" "mroads" '(64 -30) 1 1 0 )
(command "insert" "mroads" '(4 -31) 1 1 0 )
(command "insert" "mroads" '(65 -31) 1 1 0 )
(command "insert" "mroads" '(5 -30) 1 1 0 )
(command "insert" "mroads" '(40 -23) 1 1 0 )
(command "insert" "mroads" '(112 -30) 1 1 0 )
(command "insert" "mroads" '(8 -32) 1 1 0 )
(command "insert" "mroads" '(41 -22) 1 1 0 )
(command "insert" "mroads" '(22 -16) 1 1 0 )
(command "insert" "mroads" '(113 -31) 1 1 0 )
(command "insert" "mroads" '(18 -16) 1 1 0 )
(command "insert" "mroads" '(16 -32) 1 1 0 )
(command "insert" "mroads" '(60 -32) 1 1 0 )
(command "insert" "mroads" '(68 -32) 1 1 0 )
(command "insert" "mroads" '(96 -32) 1 1 0 )
(command "insert" "mroads" '(60 -30) 1 1 0 )
(command "insert" "mroads" '(61 -31) 1 1 0 )
(command "insert" "mroads" '(35 -20) 1 1 0 )
(command "insert" "mroads" '(24 -15) 1 1 0 )
(command "insert" "mroads" '(36 -23) 1 1 0 )
(command "insert" "mroads" '(108 -30) 1 1 0 )
(command "insert" "mroads" '(37 -22) 1 1 0 )
(command "insert" "mroads" '(2 -24) 1 1 0 )
(command "insert" "mroads" '(109 -31) 1 1 0 )
(command "insert" "mroads" '(29 -16) 1 1 0 )
(command "insert" "mroads" '(30 -15) 1 1 0 )
(command "insert" "mroads" '(6 -26) 1 1 0 )
(command "insert" "mroads" '(40 -30) 1 1 0 )
(command "insert" "mroads" '(30 -17) 1 1 0 )
(command "insert" "mroads" '(7 -17) 1 1 0 )
(command "insert" "mroads" '(31 -20) 1 1 0 )
(command "insert" "mroads" '(20 -15) 1 1 0 )
(command "insert" "mroads" '(33 -31) 1 1 0 )
(command "insert" "mroads" '(23 -18) 1 1 0 )
(command "insert" "mroads" '(47 -32) 1 1 0 )
(command "insert" "mroads" '(33 -27) 1 1 0 )
(command "insert" "mroads" '(38 -32) 1 1 0 )
(command "insert" "mroads" '(10 -15) 1 1 0 )
(command "insert" "mroads" '(8 -19) 1 1 0 )
(command "insert" "mroads" '(35 -29) 1 1 0 )
(command "insert" "mroads" '(9 -18) 1 1 0 )
(command "insert" "mroads" '(74 -32) 1 1 0 )
(command "insert" "mroads" '(102 -30) 1 1 0 )
(command "insert" "mroads" '(36 -30) 1 1 0 )
(command "insert" "mroads" '(51 -30) 1 1 0 )
(command "insert" "mroads" '(41 -27) 1 1 0 )
(command "insert" "mroads" '(82 -32) 1 1 0 )
(command "insert" "mroads" '(37 -31) 1 1 0 )
(command "insert" "mroads" '(26 -20) 1 1 0 )
(command "insert" "mroads" '(7 -19) 1 1 0 )
(command "insert" "mroads" '(98 -31) 1 1 0 )
(command "insert" "mroads" '(38 -28) 1 1 0 )
(command "insert" "mroads" '(40 -19) 1 1 0 )
(command "insert" "mroads" '(99 -30) 1 1 0 )
(command "insert" "mroads" '(39 -25) 1 1 0 )
(command "insert" "mroads" '(3 -16) 1 1 0 )
(command "insert" "mroads" '(1 -32) 1 1 0 )
(command "insert" "mroads" '(6 -15) 1 1 0 )
(command "insert" "mroads" '(46 -31) 1 1 0 )
(command "insert" "mroads" '(53 -32) 1 1 0 )
(command "insert" "mroads" '(16 -30) 1 1 0 )
(command "insert" "mroads" '(47 -30) 1 1 0 )
(command "insert" "mroads" '(17 -31) 1 1 0 )
(command "insert" "mroads" '(32 -17) 1 1 0 )
(command "insert" "mroads" '(7 -28) 1 1 0 )
(command "insert" "mroads" '(89 -32) 1 1 0 )
(command "insert" "mroads" '(7 -24) 1 1 0 )
(command "insert" "mroads" '(94 -31) 1 1 0 )
(command "insert" "mroads" '(33 -28) 1 1 0 )
(command "insert" "mroads" '(95 -30) 1 1 0 )
(command "insert" "mroads" '(34 -27) 1 1 0 )
(command "insert" "mroads" '(8 -26) 1 1 0 )
(command "insert" "mroads" '(14 -16) 1 1 0 )
(command "insert" "mroads" '(10 -16) 1 1 0 )
(command "insert" "mroads" '(37 -24) 1 1 0 )
(command "insert" "mroads" '(68 -30) 1 1 0 )
(command "insert" "mroads" '(26 -31) 1 1 0 )
(command "insert" "mroads" '(38 -23) 1 1 0 )
(command "insert" "mroads" '(83 -30) 1 1 0 )
(command "insert" "mroads" '(27 -30) 1 1 0 )
(command "insert" "mroads" '(39 -22) 1 1 0 )
(command "insert" "mroads" '(13 -31) 1 1 0 )
(command "insert" "mroads" '(74 -31) 1 1 0 )
(command "insert" "mroads" '(3 -25) 1 1 0 )
(command "insert" "mroads" '(75 -30) 1 1 0 )
(command "insert" "mroads" '(4 -18) 1 1 0 )
(command "insert" "mroads" '(62 -30) 1 1 0 )
(command "insert" "mroads" '(5 -19) 1 1 0 )
(command "insert" "mroads" '(23 -32) 1 1 0 )
(command "insert" "mroads" '(40 -18) 1 1 0 )
(command "insert" "mroads" '(21 -16) 1 1 0 )
(command "insert" "mroads" '(17 -16) 1 1 0 )
(command "insert" "mroads" '(41 -19) 1 1 0 )
(command "insert" "mroads" '(31 -32) 1 1 0 )
(command "insert" "mroads" '(59 -32) 1 1 0 )
(command "insert" "mroads" '(33 -21) 1 1 0 )
(command "insert" "mroads" '(23 -30) 1 1 0 )
(command "insert" "mroads" '(34 -18) 1 1 0 )
(command "insert" "mroads" '(67 -32) 1 1 0 )
(command "insert" "mroads" '(6 -20) 1 1 0 )
(command "insert" "mroads" '(111 -32) 1 1 0 )
(command "insert" "mroads" '(33 -15) 1 1 0 )
(command "insert" "mroads" '(71 -30) 1 1 0 )
(command "insert" "mroads" '(11 -18) 1 1 0 )
(command "insert" "mroads" '(35 -17) 1 1 0 )
(command "insert" "mroads" '(1 -24) 1 1 0 )
(command "insert" "mroads" '(39 -15) 1 1 0 )
(command "insert" "mroads" '(28 -16) 1 1 0 )
(command "insert" "mroads" '(2 -31) 1 1 0 )
(command "insert" "mroads" '(12 -30) 1 1 0 )
(command "insert" "mroads" '(41 -31) 1 1 0 )
(command "insert" "mroads" '(79 -31) 1 1 0 )
(command "insert" "mroads" '(3 -30) 1 1 0 )
(command "insert" "mroads" '(40 -17) 1 1 0 )
(command "insert" "mroads" '(4 -25) 1 1 0 )
(command "insert" "mroads" '(50 -31) 1 1 0 )
(command "insert" "mroads" '(5 -28) 1 1 0 )
(command "insert" "mroads" '(29 -15) 1 1 0 )
(command "insert" "mroads" '(40 -25) 1 1 0 )
(command "insert" "mroads" '(7 -26) 1 1 0 )
(command "insert" "mroads" '(58 -30) 1 1 0 )
(command "insert" "mroads" '(37 -32) 1 1 0 )
(command "insert" "mroads" '(59 -31) 1 1 0 )
(command "insert" "mroads" '(41 -16) 1 1 0 )
(command "insert" "mroads" '(45 -32) 1 1 0 )
(command "insert" "mroads" '(73 -32) 1 1 0 )
(command "insert" "mroads" '(106 -30) 1 1 0 )
(command "insert" "mroads" '(35 -22) 1 1 0 )
(command "insert" "mroads" '(24 -17) 1 1 0 )
(command "insert" "mroads" '(107 -31) 1 1 0 )
(command "insert" "mroads" '(81 -32) 1 1 0 )
(command "insert" "mroads" '(36 -17) 1 1 0 )
(command "insert" "mroads" '(13 -17) 1 1 0 )
(command "insert" "mroads" '(37 -20) 1 1 0 )
(command "insert" "mroads" '(2 -22) 1 1 0 )
(command "insert" "mroads" '(72 -30) 1 1 0 )
(command "insert" "mroads" '(38 -27) 1 1 0 )
(command "insert" "mroads" '(54 -30) 1 1 0 )
(command "insert" "mroads" '(55 -31) 1 1 0 )
(command "insert" "mroads" '(116 -31) 1 1 0 )
(command "insert" "mroads" '(52 -32) 1 1 0 )
(command "insert" "mroads" '(41 -29) 1 1 0 )
(command "insert" "mroads" '(103 -31) 1 1 0 )
(command "insert" "mroads" '(88 -32) 1 1 0 )
(command "insert" "mroads" '(84 -31) 1 1 0 )
(command "insert" "mroads" '(8 -15) 1 1 0 )
(command "insert" "mroads" '(33 -25) 1 1 0 )
(command "insert" "mroads" '(34 -30) 1 1 0 )
(command "insert" "mroads" '(8 -21) 1 1 0 )
(command "insert" "mroads" '(35 -31) 1 1 0 )
(command "insert" "mroads" '(9 -16) 1 1 0 )
(command "insert" "mroads" '(14 -15) 1 1 0 )
(command "insert" "mroads" '(40 -28) 1 1 0 )
(command "insert" "mroads" '(96 -31) 1 1 0 )
(command "insert" "mroads" '(36 -24) 1 1 0 )
(command "insert" "mroads" '(78 -31) 1 1 0 )
(command "insert" "mroads" '(82 -30) 1 1 0 )
(command "insert" "mroads" '(97 -30) 1 1 0 )
(command "insert" "mroads" '(37 -29) 1 1 0 )
(command "insert" "mroads" '(26 -18) 1 1 0 )
(command "insert" "mroads" '(38 -18) 1 1 0 )
(command "insert" "mroads" '(103 -32) 1 1 0 )
(command "insert" "mroads" '(39 -27) 1 1 0 )
(command "insert" "mroads" '(4 -15) 1 1 0 )
(command "insert" "mroads" '(7 -23) 1 1 0 )
(command "insert" "mroads" '(3 -18) 1 1 0 )
(command "insert" "mroads" '(30 -30) 1 1 0 )
(command "insert" "mroads" '(4 -21) 1 1 0 )
(command "insert" "mroads" '(22 -32) 1 1 0 )
(command "insert" "mroads" '(20 -16) 1 1 0 )
(command "insert" "mroads" '(92 -31) 1 1 0 )
(command "insert" "mroads" '(16 -16) 1 1 0 )
(command "insert" "mroads" '(30 -32) 1 1 0 )
(command "insert" "mroads" '(93 -30) 1 1 0 )
(command "insert" "mroads" '(58 -32) 1 1 0 )
(command "insert" "mroads" '(32 -19) 1 1 0 )
(command "insert" "mroads" '(33 -18) 1 1 0 )
(command "insert" "mroads" '(66 -32) 1 1 0 )
(command "insert" "mroads" '(110 -32) 1 1 0 )
(command "insert" "mroads" '(34 -25) 1 1 0 )
(command "insert" "mroads" '(8 -28) 1 1 0 )
(command "insert" "mroads" '(57 -30) 1 1 0 )
(command "insert" "mroads" '(24 -31) 1 1 0 )
(command "insert" "mroads" '(10 -30) 1 1 0 )
(command "insert" "mroads" '(25 -30) 1 1 0 )
(command "insert" "mroads" '(11 -31) 1 1 0 )
(command "insert" "mroads" '(72 -31) 1 1 0 )
(command "insert" "mroads" '(27 -16) 1 1 0 )
(command "insert" "mroads" '(49 -32) 1 1 0 )
(command "insert" "mroads" '(73 -30) 1 1 0 )
(command "insert" "mroads" '(3 -27) 1 1 0 )
(command "insert" "mroads" '(4 -28) 1 1 0 )
(command "insert" "mroads" '(41 -15) 1 1 0 )
(command "insert" "mroads" '(5 -17) 1 1 0 )
(command "insert" "mroads" '(20 -31) 1 1 0 )
(command "insert" "mroads" '(40 -20) 1 1 0 )
(command "insert" "mroads" '(21 -30) 1 1 0 )
(command "insert" "mroads" '(104 -31) 1 1 0 )
(command "insert" "mroads" '(68 -31) 1 1 0 )
(command "insert" "mroads" '(36 -32) 1 1 0 )
(command "insert" "mroads" '(69 -30) 1 1 0 )
(command "insert" "mroads" '(34 -16) 1 1 0 )
(command "insert" "mroads" '(44 -32) 1 1 0 )
(command "insert" "mroads" '(72 -32) 1 1 0 )
(command "insert" "mroads" '(31 -31) 1 1 0 )
(command "insert" "mroads" '(37 -15) 1 1 0 )
(command "insert" "mroads" '(11 -20) 1 1 0 )
(command "insert" "mroads" '(35 -19) 1 1 0 )
(command "insert" "mroads" '(36 -20) 1 1 0 )
(command "insert" "mroads" '(1 -30) 1 1 0 )
(command "insert" "mroads" '(28 -18) 1 1 0 )
(command "insert" "mroads" '(2 -29) 1 1 0 )
(command "insert" "mroads" '(48 -31) 1 1 0 )
(command "insert" "mroads" '(29 -19) 1 1 0 )
(command "insert" "mroads" '(27 -15) 1 1 0 )
(command "insert" "mroads" '(49 -30) 1 1 0 )
(command "insert" "mroads" '(4 -27) 1 1 0 )
(command "insert" "mroads" '(32 -32) 1 1 0 )
(command "insert" "mroads" '(5 -26) 1 1 0 )
(command "insert" "mroads" '(51 -32) 1 1 0 )
(command "insert" "mroads" '(40 -27) 1 1 0 )
(command "insert" "mroads" '(30 -18) 1 1 0 )
(command "insert" "mroads" '(17 -15) 1 1 0 )
(command "insert" "mroads" '(41 -26) 1 1 0 )
(command "insert" "mroads" '(22 -20) 1 1 0 )
(command "insert" "mroads" '(57 -31) 1 1 0 )
(command "insert" "mroads" '(86 -31) 1 1 0 )
(command "insert" "mroads" '(104 -30) 1 1 0 )
(command "insert" "mroads" '(44 -31) 1 1 0 )
(command "insert" "mroads" '(23 -15) 1 1 0 )
(command "insert" "mroads" '(105 -31) 1 1 0 )
(command "insert" "mroads" '(45 -30) 1 1 0 )
(command "insert" "mroads" '(8 -16) 1 1 0 )
(command "insert" "mroads" '(35 -24) 1 1 0 )
(command "insert" "mroads" '(50 -32) 1 1 0 )
(command "insert" "mroads" '(24 -19) 1 1 0 )
(command "insert" "mroads" '(36 -19) 1 1 0 )
(command "insert" "mroads" '(1 -23) 1 1 0 )
(command "insert" "mroads" '(25 -18) 1 1 0 )
(command "insert" "mroads" '(13 -15) 1 1 0 )
(command "insert" "mroads" '(37 -18) 1 1 0 )
(command "insert" "mroads" '(102 -32) 1 1 0 )
(command "insert" "mroads" '(38 -25) 1 1 0 )
(command "insert" "mroads" '(53 -31) 1 1 0 )
(command "insert" "mroads" '(78 -30) 1 1 0 )
(command "insert" "mroads" '(39 -28) 1 1 0 )
(command "insert" "mroads" '(84 -32) 1 1 0 )
(command "insert" "mroads" '(100 -30) 1 1 0 )
(command "insert" "mroads" '(115 -30) 1 1 0 )
(command "insert" "mroads" '(25 -17) 1 1 0 )
(command "insert" "mroads" '(101 -31) 1 1 0 )
(command "insert" "mroads" '(21 -32) 1 1 0 )
(command "insert" "mroads" '(19 -16) 1 1 0 )
(command "insert" "mroads" '(31 -16) 1 1 0 )
(command "insert" "mroads" '(29 -32) 1 1 0 )
(command "insert" "mroads" '(41 -17) 1 1 0 )
(command "insert" "mroads" '(32 -30) 1 1 0 )
(command "insert" "mroads" '(65 -32) 1 1 0 )
(command "insert" "mroads" '(52 -31) 1 1 0 )
(command "insert" "mroads" '(7 -20) 1 1 0 )
(command "insert" "mroads" '(110 -31) 1 1 0 )
(command "insert" "mroads" '(34 -28) 1 1 0 )
(command "insert" "mroads" '(8 -23) 1 1 0 )
(command "insert" "mroads" '(80 -30) 1 1 0 )
(command "insert" "mroads" '(111 -30) 1 1 0 )
(command "insert" "mroads" '(57 -32) 1 1 0 )
(command "insert" "mroads" '(81 -31) 1 1 0 )
(command "insert" "mroads" '(36 -26) 1 1 0 )
(command "insert" "mroads" '(40 -24) 1 1 0 )
(command "insert" "mroads" '(37 -27) 1 1 0 )
(command "insert" "mroads" '(26 -16) 1 1 0 )
(command "insert" "mroads" '(38 -16) 1 1 0 )
(command "insert" "mroads" '(39 -21) 1 1 0 )
(command "insert" "mroads" '(28 -30) 1 1 0 )
(command "insert" "mroads" '(29 -31) 1 1 0 )
(command "insert" "mroads" '(3 -20) 1 1 0 )
(command "insert" "mroads" '(90 -31) 1 1 0 )
(command "insert" "mroads" '(4 -23) 1 1 0 )
(command "insert" "mroads" '(76 -30) 1 1 0 )
(command "insert" "mroads" '(91 -30) 1 1 0 )
(command "insert" "mroads" '(7 -27) 1 1 0 )
(command "insert" "mroads" '(5 -22) 1 1 0 )
(command "insert" "mroads" '(20 -18) 1 1 0 )
(command "insert" "mroads" '(77 -31) 1 1 0 )
(command "insert" "mroads" '(21 -19) 1 1 0 )
(command "insert" "mroads" '(7 -32) 1 1 0 )
(command "insert" "mroads" '(35 -32) 1 1 0 )
(command "insert" "mroads" '(113 -30) 1 1 0 )
(command "insert" "mroads" '(33 -16) 1 1 0 )
(command "insert" "mroads" '(34 -23) 1 1 0 )
(command "insert" "mroads" '(8 -30) 1 1 0 )
(command "insert" "mroads" '(87 -32) 1 1 0 )
(command "insert" "mroads" '(9 -31) 1 1 0 )
(command "insert" "mroads" '(95 -32) 1 1 0 )
(command "insert" "mroads" '(15 -17) 1 1 0 )
(command "insert" "mroads" '(87 -30) 1 1 0 )
(command "insert" "mroads" '(11 -17) 1 1 0 )
(command "insert" "mroads" '(27 -18) 1 1 0 )
(command "insert" "mroads" '(1 -27) 1 1 0 )
(command "insert" "mroads" '(39 -18) 1 1 0 )
(command "insert" "mroads" '(14 -32) 1 1 0 )
(command "insert" "mroads" '(3 -29) 1 1 0 )
(command "insert" "mroads" '(4 -30) 1 1 0 )
(command "insert" "mroads" '(19 -30) 1 1 0 )
(command "layer" "m" "Commmer" "" )
(command "insert" "Commmer" '(63 -28) 1 1 0 )
(command "insert" "Commmer" '(64 -27) 1 1 0 )
(command "insert" "Commmer" '(65 -27) 1 1 0 )
(command "insert" "Commmer" '(64 -25) 1 1 0 )
(command "insert" "Commmer" '(65 -24) 1 1 0 )
(command "insert" "Commmer" '(63 -27) 1 1 0 )
(command "insert" "Commmer" '(63 -25) 1 1 0 )
(command "insert" "Commmer" '(65 -29) 1 1 0 )
(command "insert" "Commmer" '(64 -28) 1 1 0 )
(command "insert" "Commmer" '(63 -29) 1 1 0 )
(command "insert" "Commmer" '(65 -25) 1 1 0 )
(command "insert" "Commmer" '(64 -24) 1 1 0 )
(command "insert" "Commmer" '(64 -26) 1 1 0 )
(command "insert" "Commmer" '(63 -26) 1 1 0 )
(command "insert" "Commmer" '(65 -26) 1 1 0 )
(command "insert" "Commmer" '(63 -24) 1 1 0 )
(command "insert" "Commmer" '(65 -28) 1 1 0 )
(command "insert" "Commmer" '(64 -29) 1 1 0 )
(command "layer" "m" "Res" "" )
(command "insert" "Res" '(247 -94) 1 1 0 )
(command "insert" "Res" '(249 -94) 1 1 0 )
(command "insert" "Res" '(252 -94) 1 1 0 )
(command "insert" "Res" '(248 -94) 1 1 0 )
(command "insert" "Res" '(250 -93) 1 1 0 )
(command "insert" "Res" '(253 -95) 1 1 0 )
(command "insert" "Res" '(250 -95) 1 1 0 )
(command "insert" "Res" '(251 -94) 1 1 0 )
(command "insert" "Res" '(254 -94) 1 1 0 )
(command "insert" "Res" '(248 -93) 1 1 0 )
(command "insert" "Res" '(253 -93) 1 1 0 )
(command "insert" "Res" '(249 -93) 1 1 0 )
(command "insert" "Res" '(252 -95) 1 1 0 )
(command "insert" "Res" '(247 -95) 1 1 0 )
(command "insert" "Res" '(249 -95) 1 1 0 )
(command "insert" "Res" '(252 -93) 1 1 0 )
(command "insert" "Res" '(247 -93) 1 1 0 )
(command "insert" "Res" '(254 -93) 1 1 0 )
(command "insert" "Res" '(253 -94) 1 1 0 )
(command "insert" "Res" '(250 -94) 1 1 0 )
(command "insert" "Res" '(254 -95) 1 1 0 )
(command "insert" "Res" '(246 -93) 1 1 0 )
(command "insert" "Res" '(251 -95) 1 1 0 )
(command "insert" "Res" '(246 -94) 1 1 0 )
(command "insert" "Res" '(246 -95) 1 1 0 )
(command "insert" "Res" '(248 -95) 1 1 0 )
(command "insert" "Res" '(251 -93) 1 1 0 )
(command "layer" "m" "Res" "" )
(command "insert" "Res" '(192 -47) 1 1 0 )
(command "insert" "Res" '(192 -46) 1 1 0 )
(command "insert" "Res" '(193 -46) 1 1 0 )
(command "insert" "Res" '(193 -47) 1 1 0 )
(command "insert" "Res" '(194 -45) 1 1 0 )
(command "insert" "Res" '(193 -45) 1 1 0 )
(command "insert" "Res" '(194 -47) 1 1 0 )
(command "insert" "Res" '(194 -46) 1 1 0 )
(command "insert" "Res" '(192 -45) 1 1 0 )
(command "layer" "m" "Res" "" )
(command "insert" "Res" '(1 -34) 1 1 0 )
(command "insert" "Res" '(1 -35) 1 1 0 )
(command "insert" "Res" '(2 -35) 1 1 0 )
(command "insert" "Res" '(2 -34) 1 1 0 )
(command "insert" "Res" '(1 -33) 1 1 0 )
(command "insert" "Res" '(2 -33) 1 1 0 )
(command "layer" "m" "Commmer" "" )
(command "insert" "Commmer" '(161 -24) 1 1 0 )
(command "insert" "Commmer" '(160 -26) 1 1 0 )
(command "insert" "Commmer" '(160 -25) 1 1 0 )
(command "insert" "Commmer" '(160 -24) 1 1 0 )
(command "insert" "Commmer" '(159 -26) 1 1 0 )
(command "insert" "Commmer" '(161 -26) 1 1 0 )
(command "insert" "Commmer" '(159 -24) 1 1 0 )
(command "insert" "Commmer" '(159 -25) 1 1 0 )
(command "insert" "Commmer" '(161 -25) 1 1 0 )
(command "layer" "m" "Res" "" )
(command "insert" "Res" '(271 -86) 1 1 0 )
(command "insert" "Res" '(271 -89) 1 1 0 )
(command "insert" "Res" '(271 -84) 1 1 0 )
(command "insert" "Res" '(270 -88) 1 1 0 )
(command "insert" "Res" '(272 -87) 1 1 0 )
(command "insert" "Res" '(268 -82) 1 1 0 )
(command "insert" "Res" '(272 -85) 1 1 0 )
(command "insert" "Res" '(269 -83) 1 1 0 )
(command "insert" "Res" '(270 -84) 1 1 0 )
(command "insert" "Res" '(272 -88) 1 1 0 )
(command "insert" "Res" '(267 -83) 1 1 0 )
(command "insert" "Res" '(270 -86) 1 1 0 )
(command "insert" "Res" '(267 -81) 1 1 0 )
(command "insert" "Res" '(271 -88) 1 1 0 )
(command "insert" "Res" '(271 -87) 1 1 0 )
(command "insert" "Res" '(269 -81) 1 1 0 )
(command "insert" "Res" '(270 -89) 1 1 0 )
(command "insert" "Res" '(271 -85) 1 1 0 )
(command "insert" "Res" '(268 -83) 1 1 0 )
(command "insert" "Res" '(272 -86) 1 1 0 )
(command "insert" "Res" '(269 -82) 1 1 0 )
(command "insert" "Res" '(270 -85) 1 1 0 )
(command "insert" "Res" '(272 -84) 1 1 0 )
(command "insert" "Res" '(272 -89) 1 1 0 )
(command "insert" "Res" '(268 -81) 1 1 0 )
(command "insert" "Res" '(267 -82) 1 1 0 )
(command "insert" "Res" '(270 -87) 1 1 0 )
(command "layer" "m" "Res" "" )
(command "insert" "Res" '(12 -2) 1 1 0 )
(command "insert" "Res" '(12 -1) 1 1 0 )
(command "insert" "Res" '(9 -1) 1 1 0 )
(command "insert" "Res" '(13 -1) 1 1 0 )
(command "insert" "Res" '(9 -2) 1 1 0 )
(command "insert" "Res" '(11 -2) 1 1 0 )
(command "insert" "Res" '(14 -1) 1 1 0 )
(command "insert" "Res" '(11 -1) 1 1 0 )
(command "insert" "Res" '(10 -1) 1 1 0 )
(command "insert" "Res" '(13 -2) 1 1 0 )
(command "insert" "Res" '(14 -2) 1 1 0 )
(command "insert" "Res" '(10 -2) 1 1 0 )
(command "layer" "m" "Res" "" )
(command "insert" "Res" '(1 -34) 1 1 0 )
(command "insert" "Res" '(1 -35) 1 1 0 )
(command "insert" "Res" '(2 -35) 1 1 0 )
(command "insert" "Res" '(2 -34) 1 1 0 )
(command "insert" "Res" '(1 -33) 1 1 0 )
(command "insert" "Res" '(2 -33) 1 1 0 )
(command "layer" "m" "Res" "" )
(command "insert" "Res" '(244 -77) 1 1 0 )
(command "insert" "Res" '(244 -76) 1 1 0 )
(command "insert" "Res" '(243 -77) 1 1 0 )
(command "insert" "Res" '(244 -75) 1 1 0 )
(command "insert" "Res" '(243 -73) 1 1 0 )
(command "insert" "Res" '(244 -73) 1 1 0 )
(command "insert" "Res" '(245 -72) 1 1 0 )
(command "insert" "Res" '(243 -74) 1 1 0 )
(command "insert" "Res" '(245 -76) 1 1 0 )
(command "insert" "Res" '(243 -72) 1 1 0 )
(command "insert" "Res" '(243 -76) 1 1 0 )
(command "insert" "Res" '(244 -74) 1 1 0 )
(command "insert" "Res" '(245 -77) 1 1 0 )
(command "insert" "Res" '(245 -73) 1 1 0 )
(command "insert" "Res" '(245 -75) 1 1 0 )
(command "insert" "Res" '(245 -74) 1 1 0 )
(command "insert" "Res" '(244 -72) 1 1 0 )
(command "insert" "Res" '(243 -75) 1 1 0 )
(command "layer" "m" "Res" "" )
(command "insert" "Res" '(13 -1) 1 1 0 )
(command "insert" "Res" '(12 -1) 1 1 0 )
(command "insert" "Res" '(9 -1) 1 1 0 )
(command "insert" "Res" '(12 -2) 1 1 0 )
(command "insert" "Res" '(9 -2) 1 1 0 )
(command "insert" "Res" '(11 -2) 1 1 0 )
(command "insert" "Res" '(14 -1) 1 1 0 )
(command "insert" "Res" '(11 -1) 1 1 0 )
(command "insert" "Res" '(10 -1) 1 1 0 )
(command "insert" "Res" '(13 -2) 1 1 0 )
(command "insert" "Res" '(14 -2) 1 1 0 )
(command "insert" "Res" '(10 -2) 1 1 0 )
(command "layer" "m" "ped" "" )
(command "insert" "ped" '(1 -3) 1 1 0 )
(command "insert" "ped" '(2 -18) 1 1 0 )
(command "insert" "ped" '(2 -8) 1 1 0 )
(command "insert" "ped" '(1 -17) 1 1 0 )
(command "insert" "ped" '(2 -1) 1 1 0 )
(command "insert" "ped" '(1 -15) 1 1 0 )
(command "insert" "ped" '(6 -2) 1 1 0 )
(command "insert" "ped" '(1 -6) 1 1 0 )
(command "insert" "ped" '(2 -12) 1 1 0 )
(command "insert" "ped" '(5 -1) 1 1 0 )
(command "insert" "ped" '(2 -5) 1 1 0 )
(command "insert" "ped" '(1 -11) 1 1 0 )
(command "insert" "ped" '(7 -2) 1 1 0 )
(command "insert" "ped" '(1 -2) 1 1 0 )
(command "insert" "ped" '(2 -19) 1 1 0 )
(command "insert" "ped" '(2 -9) 1 1 0 )
(command "insert" "ped" '(8 -1) 1 1 0 )
(command "insert" "ped" '(1 -16) 1 1 0 )
(command "insert" "ped" '(1 -14) 1 1 0 )
(command "insert" "ped" '(1 -5) 1 1 0 )
(command "insert" "ped" '(2 -13) 1 1 0 )
(command "insert" "ped" '(1 -20) 1 1 0 )
(command "insert" "ped" '(2 -2) 1 1 0 )
(command "insert" "ped" '(1 -10) 1 1 0 )
(command "insert" "ped" '(4 -1) 1 1 0 )
(command "insert" "ped" '(1 -1) 1 1 0 )
(command "insert" "ped" '(2 -16) 1 1 0 )
(command "insert" "ped" '(3 -2) 1 1 0 )
(command "insert" "ped" '(2 -6) 1 1 0 )
(command "insert" "ped" '(8 -2) 1 1 0 )
(command "insert" "ped" '(7 -1) 1 1 0 )
(command "insert" "ped" '(1 -13) 1 1 0 )
(command "insert" "ped" '(2 -20) 1 1 0 )
(command "insert" "ped" '(1 -4) 1 1 0 )
(command "insert" "ped" '(2 -10) 1 1 0 )
(command "insert" "ped" '(1 -19) 1 1 0 )
(command "insert" "ped" '(2 -3) 1 1 0 )
(command "insert" "ped" '(1 -9) 1 1 0 )
(command "insert" "ped" '(4 -2) 1 1 0 )
(command "insert" "ped" '(2 -14) 1 1 0 )
(command "insert" "ped" '(2 -17) 1 1 0 )
(command "insert" "ped" '(2 -7) 1 1 0 )
(command "insert" "ped" '(1 -12) 1 1 0 )
(command "insert" "ped" '(6 -1) 1 1 0 )
(command "insert" "ped" '(3 -1) 1 1 0 )
(command "insert" "ped" '(2 -11) 1 1 0 )
(command "insert" "ped" '(1 -18) 1 1 0 )
(command "insert" "ped" '(1 -8) 1 1 0 )
(command "insert" "ped" '(1 -7) 1 1 0 )
(command "insert" "ped" '(2 -15) 1 1 0 )
(command "insert" "ped" '(5 -2) 1 1 0 )
(command "insert" "ped" '(2 -4) 1 1 0 )
(command "layer" "m" "edge" "" )
(command "insert" "edge" '(12 -37) 1 1 0 )
(command "insert" "edge" '(14 -37) 1 1 0 )
(command "insert" "edge" '(14 -36) 1 1 0 )
(command "insert" "edge" '(13 -36) 1 1 0 )
(command "insert" "edge" '(13 -37) 1 1 0 )
(command "insert" "edge" '(12 -38) 1 1 0 )
(command "insert" "edge" '(13 -38) 1 1 0 )
(command "insert" "edge" '(12 -36) 1 1 0 )
(command "insert" "edge" '(14 -38) 1 1 0 )
(command "layer" "m" "Commmer" "" )
(command "insert" "Commmer" '(32 -1) 1 1 0 )
(command "insert" "Commmer" '(34 -2) 1 1 0 )
(command "insert" "Commmer" '(21 -2) 1 1 0 )
(command "insert" "Commmer" '(16 -2) 1 1 0 )
(command "insert" "Commmer" '(26 -2) 1 1 0 )
(command "insert" "Commmer" '(28 -1) 1 1 0 )
(command "insert" "Commmer" '(25 -1) 1 1 0 )
(command "insert" "Commmer" '(27 -2) 1 1 0 )
(command "insert" "Commmer" '(32 -2) 1 1 0 )
(command "insert" "Commmer" '(18 -1) 1 1 0 )
(command "insert" "Commmer" '(31 -1) 1 1 0 )
(command "insert" "Commmer" '(22 -2) 1 1 0 )
(command "insert" "Commmer" '(21 -1) 1 1 0 )
(command "insert" "Commmer" '(23 -2) 1 1 0 )
(command "insert" "Commmer" '(17 -2) 1 1 0 )
(command "insert" "Commmer" '(28 -2) 1 1 0 )
(command "insert" "Commmer" '(34 -1) 1 1 0 )
(command "insert" "Commmer" '(24 -1) 1 1 0 )
(command "insert" "Commmer" '(33 -2) 1 1 0 )
(command "insert" "Commmer" '(30 -1) 1 1 0 )
(command "insert" "Commmer" '(27 -1) 1 1 0 )
(command "insert" "Commmer" '(18 -2) 1 1 0 )
(command "insert" "Commmer" '(20 -1) 1 1 0 )
(command "insert" "Commmer" '(17 -1) 1 1 0 )
(command "insert" "Commmer" '(19 -2) 1 1 0 )
(command "insert" "Commmer" '(29 -2) 1 1 0 )
(command "insert" "Commmer" '(24 -2) 1 1 0 )
(command "insert" "Commmer" '(23 -1) 1 1 0 )
(command "insert" "Commmer" '(35 -1) 1 1 0 )
(command "insert" "Commmer" '(15 -1) 1 1 0 )
(command "insert" "Commmer" '(33 -1) 1 1 0 )
(command "insert" "Commmer" '(35 -2) 1 1 0 )
(command "insert" "Commmer" '(26 -1) 1 1 0 )
(command "insert" "Commmer" '(15 -2) 1 1 0 )
(command "insert" "Commmer" '(20 -2) 1 1 0 )
(command "insert" "Commmer" '(30 -2) 1 1 0 )
(command "insert" "Commmer" '(16 -1) 1 1 0 )
(command "insert" "Commmer" '(29 -1) 1 1 0 )
(command "insert" "Commmer" '(31 -2) 1 1 0 )
(command "insert" "Commmer" '(25 -2) 1 1 0 )
(command "insert" "Commmer" '(22 -1) 1 1 0 )
(command "insert" "Commmer" '(19 -1) 1 1 0 )
(command "layer" "m" "Res" "" )
(command "insert" "Res" '(81 -38) 1 1 0 )
(command "insert" "Res" '(82 -37) 1 1 0 )
(command "insert" "Res" '(86 -37) 1 1 0 )
(command "insert" "Res" '(83 -37) 1 1 0 )
(command "insert" "Res" '(85 -38) 1 1 0 )
(command "insert" "Res" '(85 -37) 1 1 0 )
(command "insert" "Res" '(84 -36) 1 1 0 )
(command "insert" "Res" '(81 -37) 1 1 0 )
(command "insert" "Res" '(83 -38) 1 1 0 )
(command "insert" "Res" '(83 -36) 1 1 0 )
(command "insert" "Res" '(82 -36) 1 1 0 )
(command "insert" "Res" '(86 -36) 1 1 0 )
(command "insert" "Res" '(85 -36) 1 1 0 )
(command "insert" "Res" '(82 -38) 1 1 0 )
(command "insert" "Res" '(86 -38) 1 1 0 )
(command "insert" "Res" '(84 -37) 1 1 0 )
(command "insert" "Res" '(81 -36) 1 1 0 )
(command "insert" "Res" '(84 -38) 1 1 0 )
(command "layer" "m" "mroads" "" )
(command "insert" "mroads" '(5 -31) 1 1 0 )
(command "insert" "mroads" '(66 -31) 1 1 0 )
(command "insert" "mroads" '(6 -28) 1 1 0 )
(command "insert" "mroads" '(67 -30) 1 1 0 )
(command "insert" "mroads" '(7 -25) 1 1 0 )
(command "insert" "mroads" '(22 -19) 1 1 0 )
(command "insert" "mroads" '(18 -19) 1 1 0 )
(command "insert" "mroads" '(38 -21) 1 1 0 )
(command "insert" "mroads" '(114 -31) 1 1 0 )
(command "insert" "mroads" '(13 -32) 1 1 0 )
(command "insert" "mroads" '(35 -15) 1 1 0 )
(command "insert" "mroads" '(14 -31) 1 1 0 )
(command "insert" "mroads" '(15 -30) 1 1 0 )
(command "insert" "mroads" '(35 -21) 1 1 0 )
(command "insert" "mroads" '(12 -17) 1 1 0 )
(command "insert" "mroads" '(36 -22) 1 1 0 )
(command "insert" "mroads" '(1 -28) 1 1 0 )
(command "insert" "mroads" '(25 -15) 1 1 0 )
(command "insert" "mroads" '(39 -16) 1 1 0 )
(command "insert" "mroads" '(63 -30) 1 1 0 )
(command "insert" "mroads" '(37 -23) 1 1 0 )
(command "insert" "mroads" '(2 -27) 1 1 0 )
(command "insert" "mroads" '(109 -32) 1 1 0 )
(command "insert" "mroads" '(29 -17) 1 1 0 )
(command "insert" "mroads" '(31 -15) 1 1 0 )
(command "insert" "mroads" '(5 -24) 1 1 0 )
(command "insert" "mroads" '(20 -32) 1 1 0 )
(command "insert" "mroads" '(6 -23) 1 1 0 )
(command "insert" "mroads" '(30 -16) 1 1 0 )
(command "insert" "mroads" '(28 -32) 1 1 0 )
(command "insert" "mroads" '(7 -22) 1 1 0 )
(command "insert" "mroads" '(41 -23) 1 1 0 )
(command "insert" "mroads" '(42 -31) 1 1 0 )
(command "insert" "mroads" '(23 -19) 1 1 0 )
(command "insert" "mroads" '(21 -15) 1 1 0 )
(command "insert" "mroads" '(43 -30) 1 1 0 )
(command "insert" "mroads" '(116 -32) 1 1 0 )
(command "insert" "mroads" '(8 -18) 1 1 0 )
(command "insert" "mroads" '(11 -15) 1 1 0 )
(command "insert" "mroads" '(35 -26) 1 1 0 )
(command "insert" "mroads" '(9 -19) 1 1 0 )
(command "insert" "mroads" '(36 -29) 1 1 0 )
(command "insert" "mroads" '(1 -21) 1 1 0 )
(command "insert" "mroads" '(25 -16) 1 1 0 )
(command "insert" "mroads" '(29 -20) 1 1 0 )
(command "insert" "mroads" '(37 -16) 1 1 0 )
(command "insert" "mroads" '(98 -30) 1 1 0 )
(command "insert" "mroads" '(38 -31) 1 1 0 )
(command "insert" "mroads" '(99 -31) 1 1 0 )
(command "insert" "mroads" '(39 -30) 1 1 0 )
(command "insert" "mroads" '(3 -17) 1 1 0 )
(command "insert" "mroads" '(19 -18) 1 1 0 )
(command "insert" "mroads" '(7 -15) 1 1 0 )
(command "insert" "mroads" '(31 -18) 1 1 0 )
(command "insert" "mroads" '(46 -30) 1 1 0 )
(command "insert" "mroads" '(6 -32) 1 1 0 )
(command "insert" "mroads" '(34 -32) 1 1 0 )
(command "insert" "mroads" '(32 -16) 1 1 0 )
(command "insert" "mroads" '(94 -30) 1 1 0 )
(command "insert" "mroads" '(18 -31) 1 1 0 )
(command "insert" "mroads" '(42 -32) 1 1 0 )
(command "insert" "mroads" '(86 -32) 1 1 0 )
(command "insert" "mroads" '(34 -26) 1 1 0 )
(command "insert" "mroads" '(8 -25) 1 1 0 )
(command "insert" "mroads" '(94 -32) 1 1 0 )
(command "insert" "mroads" '(9 -20) 1 1 0 )
(command "insert" "mroads" '(10 -19) 1 1 0 )
(command "insert" "mroads" '(37 -25) 1 1 0 )
(command "insert" "mroads" '(26 -30) 1 1 0 )
(command "insert" "mroads" '(41 -28) 1 1 0 )
(command "insert" "mroads" '(38 -22) 1 1 0 )
(command "insert" "mroads" '(27 -31) 1 1 0 )
(command "insert" "mroads" '(40 -20) 1 1 0 )
(command "insert" "mroads" '(39 -23) 1 1 0 )
(command "insert" "mroads" '(88 -31) 1 1 0 )
(command "insert" "mroads" '(74 -30) 1 1 0 )
(command "insert" "mroads" '(89 -30) 1 1 0 )
(command "insert" "mroads" '(3 -22) 1 1 0 )
(command "insert" "mroads" '(75 -31) 1 1 0 )
(command "insert" "mroads" '(4 -17) 1 1 0 )
(command "insert" "mroads" '(5 -20) 1 1 0 )
(command "insert" "mroads" '(6 -27) 1 1 0 )
(command "insert" "mroads" '(21 -17) 1 1 0 )
(command "insert" "mroads" '(17 -17) 1 1 0 )
(command "insert" "mroads" '(22 -30) 1 1 0 )
(command "insert" "mroads" '(33 -22) 1 1 0 )
(command "insert" "mroads" '(23 -31) 1 1 0 )
(command "insert" "mroads" '(12 -32) 1 1 0 )
(command "insert" "mroads" '(34 -21) 1 1 0 )
(command "insert" "mroads" '(70 -30) 1 1 0 )
(command "insert" "mroads" '(85 -30) 1 1 0 )
(command "insert" "mroads" '(48 -32) 1 1 0 )
(command "insert" "mroads" '(71 -31) 1 1 0 )
(command "insert" "mroads" '(34 -15) 1 1 0 )
(command "insert" "mroads" '(11 -19) 1 1 0 )
(command "insert" "mroads" '(100 -32) 1 1 0 )
(command "insert" "mroads" '(27 -20) 1 1 0 )
(command "insert" "mroads" '(1 -25) 1 1 0 )
(command "insert" "mroads" '(108 -32) 1 1 0 )
(command "insert" "mroads" '(2 -30) 1 1 0 )
(command "insert" "mroads" '(3 -31) 1 1 0 )
(command "insert" "mroads" '(64 -31) 1 1 0 )
(command "insert" "mroads" '(4 -24) 1 1 0 )
(command "insert" "mroads" '(19 -32) 1 1 0 )
(command "insert" "mroads" '(62 -31) 1 1 0 )
(command "insert" "mroads" '(50 -30) 1 1 0 )
(command "insert" "mroads" '(65 -30) 1 1 0 )
(command "insert" "mroads" '(5 -29) 1 1 0 )
(command "insert" "mroads" '(27 -32) 1 1 0 )
(command "insert" "mroads" '(6 -18) 1 1 0 )
(command "insert" "mroads" '(101 -32) 1 1 0 )
(command "insert" "mroads" '(112 -31) 1 1 0 )
(command "insert" "mroads" '(41 -21) 1 1 0 )
(command "insert" "mroads" '(22 -17) 1 1 0 )
(command "insert" "mroads" '(79 -32) 1 1 0 )
(command "insert" "mroads" '(18 -17) 1 1 0 )
(command "insert" "mroads" '(23 -20) 1 1 0 )
(command "insert" "mroads" '(6 -21) 1 1 0 )
(command "insert" "mroads" '(115 -32) 1 1 0 )
(command "insert" "mroads" '(60 -31) 1 1 0 )
(command "insert" "mroads" '(61 -30) 1 1 0 )
(command "insert" "mroads" '(35 -23) 1 1 0 )
(command "insert" "mroads" '(24 -16) 1 1 0 )
(command "insert" "mroads" '(36 -16) 1 1 0 )
(command "insert" "mroads" '(108 -31) 1 1 0 )
(command "insert" "mroads" '(37 -21) 1 1 0 )
(command "insert" "mroads" '(2 -25) 1 1 0 )
(command "insert" "mroads" '(109 -30) 1 1 0 )
(command "insert" "mroads" '(7 -16) 1 1 0 )
(command "insert" "mroads" '(38 -26) 1 1 0 )
(command "insert" "mroads" '(40 -18) 1 1 0 )
(command "insert" "mroads" '(114 -32) 1 1 0 )
(command "insert" "mroads" '(116 -30) 1 1 0 )
(command "insert" "mroads" '(40 -31) 1 1 0 )
(command "insert" "mroads" '(111 -31) 1 1 0 )
(command "insert" "mroads" '(19 -15) 1 1 0 )
(command "insert" "mroads" '(41 -30) 1 1 0 )
(command "insert" "mroads" '(5 -32) 1 1 0 )
(command "insert" "mroads" '(33 -32) 1 1 0 )
(command "insert" "mroads" '(41 -32) 1 1 0 )
(command "insert" "mroads" '(7 -29) 1 1 0 )
(command "insert" "mroads" '(43 -32) 1 1 0 )
(command "insert" "mroads" '(85 -32) 1 1 0 )
(command "insert" "mroads" '(9 -15) 1 1 0 )
(command "insert" "mroads" '(33 -26) 1 1 0 )
(command "insert" "mroads" '(22 -31) 1 1 0 )
(command "insert" "mroads" '(93 -32) 1 1 0 )
(command "insert" "mroads" '(8 -20) 1 1 0 )
(command "insert" "mroads" '(7 -31) 1 1 0 )
(command "insert" "mroads" '(37 -15) 1 1 0 )
(command "insert" "mroads" '(35 -28) 1 1 0 )
(command "insert" "mroads" '(9 -17) 1 1 0 )
(command "insert" "mroads" '(96 -30) 1 1 0 )
(command "insert" "mroads" '(36 -31) 1 1 0 )
(command "insert" "mroads" '(15 -15) 1 1 0 )
(command "insert" "mroads" '(97 -31) 1 1 0 )
(command "insert" "mroads" '(37 -30) 1 1 0 )
(command "insert" "mroads" '(38 -29) 1 1 0 )
(command "insert" "mroads" '(33 -21) 1 1 0 )
(command "insert" "mroads" '(39 -24) 1 1 0 )
(command "insert" "mroads" '(5 -15) 1 1 0 )
(command "insert" "mroads" '(3 -19) 1 1 0 )
(command "insert" "mroads" '(4 -20) 1 1 0 )
(command "insert" "mroads" '(19 -20) 1 1 0 )
(command "insert" "mroads" '(92 -30) 1 1 0 )
(command "insert" "mroads" '(16 -31) 1 1 0 )
(command "insert" "mroads" '(93 -31) 1 1 0 )
(command "insert" "mroads" '(17 -30) 1 1 0 )
(command "insert" "mroads" '(32 -18) 1 1 0 )
(command "insert" "mroads" '(11 -32) 1 1 0 )
(command "insert" "mroads" '(33 -19) 1 1 0 )
(command "insert" "mroads" '(34 -24) 1 1 0 )
(command "insert" "mroads" '(8 -27) 1 1 0 )
(command "insert" "mroads" '(63 -32) 1 1 0 )
(command "insert" "mroads" '(5 -21) 1 1 0 )
(command "insert" "mroads" '(24 -30) 1 1 0 )
(command "insert" "mroads" '(14 -17) 1 1 0 )
(command "insert" "mroads" '(71 -32) 1 1 0 )
(command "insert" "mroads" '(10 -17) 1 1 0 )
(command "insert" "mroads" '(25 -31) 1 1 0 )
(command "insert" "mroads" '(99 -32) 1 1 0 )
(command "insert" "mroads" '(111 -32) 1 1 0 )
(command "insert" "mroads" '(107 -32) 1 1 0 )
(command "insert" "mroads" '(38 -20) 1 1 0 )
(command "insert" "mroads" '(12 -31) 1 1 0 )
(command "insert" "mroads" '(27 -17) 1 1 0 )
(command "insert" "mroads" '(39 -17) 1 1 0 )
(command "insert" "mroads" '(13 -30) 1 1 0 )
(command "insert" "mroads" '(41 -24) 1 1 0 )
(command "insert" "mroads" '(3 -24) 1 1 0 )
(command "insert" "mroads" '(56 -32) 1 1 0 )
(command "insert" "mroads" '(4 -19) 1 1 0 )
(command "insert" "mroads" '(26 -32) 1 1 0 )
(command "insert" "mroads" '(5 -18) 1 1 0 )
(command "insert" "mroads" '(20 -30) 1 1 0 )
(command "insert" "mroads" '(40 -19) 1 1 0 )
(command "insert" "mroads" '(21 -31) 1 1 0 )
(command "insert" "mroads" '(40 -22) 1 1 0 )
(command "insert" "mroads" '(78 -32) 1 1 0 )
(command "insert" "mroads" '(41 -18) 1 1 0 )
(command "insert" "mroads" '(18 -20) 1 1 0 )
(command "insert" "mroads" '(33 -20) 1 1 0 )
(command "insert" "mroads" '(69 -31) 1 1 0 )
(command "insert" "mroads" '(34 -19) 1 1 0 )
(command "insert" "mroads" '(32 -15) 1 1 0 )
(command "insert" "mroads" '(49 -30) 1 1 0 )
(command "insert" "mroads" '(64 -32) 1 1 0 )
(command "insert" "mroads" '(35 -16) 1 1 0 )
(command "insert" "mroads" '(38 -15) 1 1 0 )
(command "insert" "mroads" '(77 -32) 1 1 0 )
(command "insert" "mroads" '(1 -31) 1 1 0 )
(command "insert" "mroads" '(28 -17) 1 1 0 )
(command "insert" "mroads" '(2 -28) 1 1 0 )
(command "insert" "mroads" '(48 -30) 1 1 0 )
(command "insert" "mroads" '(113 -32) 1 1 0 )
(command "insert" "mroads" '(49 -31) 1 1 0 )
(command "insert" "mroads" '(4 -26) 1 1 0 )
(command "insert" "mroads" '(28 -15) 1 1 0 )
(command "insert" "mroads" '(5 -27) 1 1 0 )
(command "insert" "mroads" '(40 -26) 1 1 0 )
(command "insert" "mroads" '(4 -32) 1 1 0 )
(command "insert" "mroads" '(7 -21) 1 1 0 )
(command "insert" "mroads" '(18 -15) 1 1 0 )
(command "insert" "mroads" '(40 -32) 1 1 0 )
(command "insert" "mroads" '(84 -32) 1 1 0 )
(command "insert" "mroads" '(58 -31) 1 1 0 )
(command "insert" "mroads" '(44 -30) 1 1 0 )
(command "insert" "mroads" '(59 -30) 1 1 0 )
(command "insert" "mroads" '(92 -32) 1 1 0 )
(command "insert" "mroads" '(45 -31) 1 1 0 )
(command "insert" "mroads" '(6 -17) 1 1 0 )
(command "insert" "mroads" '(106 -31) 1 1 0 )
(command "insert" "mroads" '(105 -32) 1 1 0 )
(command "insert" "mroads" '(35 -25) 1 1 0 )
(command "insert" "mroads" '(24 -18) 1 1 0 )
(command "insert" "mroads" '(107 -30) 1 1 0 )
(command "insert" "mroads" '(36 -18) 1 1 0 )
(command "insert" "mroads" '(25 -19) 1 1 0 )
(command "insert" "mroads" '(13 -16) 1 1 0 )
(command "insert" "mroads" '(37 -19) 1 1 0 )
(command "insert" "mroads" '(2 -23) 1 1 0 )
(command "insert" "mroads" '(38 -24) 1 1 0 )
(command "insert" "mroads" '(39 -29) 1 1 0 )
(command "insert" "mroads" '(54 -31) 1 1 0 )
(command "insert" "mroads" '(115 -31) 1 1 0 )
(command "insert" "mroads" '(55 -30) 1 1 0 )
(command "insert" "mroads" '(56 -30) 1 1 0 )
(command "insert" "mroads" '(30 -20) 1 1 0 )
(command "insert" "mroads" '(19 -17) 1 1 0 )
(command "insert" "mroads" '(102 -31) 1 1 0 )
(command "insert" "mroads" '(7 -18) 1 1 0 )
(command "insert" "mroads" '(31 -17) 1 1 0 )
(command "insert" "mroads" '(103 -30) 1 1 0 )
(command "insert" "mroads" '(10 -32) 1 1 0 )
(command "insert" "mroads" '(22 -32) 1 1 0 )
(command "insert" "mroads" '(18 -32) 1 1 0 )
(command "insert" "mroads" '(33 -24) 1 1 0 )
(command "insert" "mroads" '(62 -32) 1 1 0 )
(command "insert" "mroads" '(110 -30) 1 1 0 )
(command "insert" "mroads" '(34 -31) 1 1 0 )
(command "insert" "mroads" '(8 -22) 1 1 0 )
(command "insert" "mroads" '(57 -31) 1 1 0 )
(command "insert" "mroads" '(70 -32) 1 1 0 )
(command "insert" "mroads" '(35 -30) 1 1 0 )
(command "insert" "mroads" '(98 -32) 1 1 0 )
(command "insert" "mroads" '(36 -25) 1 1 0 )
(command "insert" "mroads" '(10 -20) 1 1 0 )
(command "insert" "mroads" '(25 -20) 1 1 0 )
(command "insert" "mroads" '(82 -31) 1 1 0 )
(command "insert" "mroads" '(106 -32) 1 1 0 )
(command "insert" "mroads" '(37 -28) 1 1 0 )
(command "insert" "mroads" '(26 -19) 1 1 0 )
(command "insert" "mroads" '(38 -19) 1 1 0 )
(command "insert" "mroads" '(3 -15) 1 1 0 )
(command "insert" "mroads" '(39 -26) 1 1 0 )
(command "insert" "mroads" '(51 -31) 1 1 0 )
(command "insert" "mroads" '(3 -21) 1 1 0 )
(command "insert" "mroads" '(25 -32) 1 1 0 )
(command "insert" "mroads" '(90 -30) 1 1 0 )
(command "insert" "mroads" '(30 -31) 1 1 0 )
(command "insert" "mroads" '(4 -22) 1 1 0 )
(command "insert" "mroads" '(91 -31) 1 1 0 )
(command "insert" "mroads" '(31 -30) 1 1 0 )
(command "insert" "mroads" '(5 -23) 1 1 0 )
(command "insert" "mroads" '(20 -17) 1 1 0 )
(command "insert" "mroads" '(16 -17) 1 1 0 )
(command "insert" "mroads" '(21 -20) 1 1 0 )
(command "insert" "mroads" '(32 -20) 1 1 0 )
(command "insert" "mroads" '(33 -17) 1 1 0 )
(command "insert" "mroads" '(34 -22) 1 1 0 )
(command "insert" "mroads" '(8 -29) 1 1 0 )
(command "insert" "mroads" '(61 -31) 1 1 0 )
(command "insert" "mroads" '(86 -30) 1 1 0 )
(command "insert" "mroads" '(10 -31) 1 1 0 )
(command "insert" "mroads" '(6 -19) 1 1 0 )
(command "insert" "mroads" '(87 -31) 1 1 0 )
(command "insert" "mroads" '(11 -30) 1 1 0 )
(command "insert" "mroads" '(76 -32) 1 1 0 )
(command "insert" "mroads" '(27 -19) 1 1 0 )
(command "insert" "mroads" '(39 -19) 1 1 0 )
(command "insert" "mroads" '(28 -20) 1 1 0 )
(command "insert" "mroads" '(3 -26) 1 1 0 )
(command "insert" "mroads" '(40 -15) 1 1 0 )
(command "insert" "mroads" '(4 -29) 1 1 0 )
(command "insert" "mroads" '(19 -31) 1 1 0 )
(command "insert" "mroads" '(41 -20) 1 1 0 )
(command "insert" "mroads" '(5 -16) 1 1 0 )
(command "insert" "mroads" '(3 -32) 1 1 0 )
(command "insert" "mroads" '(66 -30) 1 1 0 )
(command "insert" "mroads" '(6 -31) 1 1 0 )
(command "insert" "mroads" '(67 -31) 1 1 0 )
(command "insert" "mroads" '(7 -30) 1 1 0 )
(command "insert" "mroads" '(22 -18) 1 1 0 )
(command "insert" "mroads" '(55 -32) 1 1 0 )
(command "insert" "mroads" '(18 -18) 1 1 0 )
(command "insert" "mroads" '(83 -32) 1 1 0 )
(command "insert" "mroads" '(114 -30) 1 1 0 )
(command "insert" "mroads" '(34 -17) 1 1 0 )
(command "insert" "mroads" '(91 -32) 1 1 0 )
(command "insert" "mroads" '(14 -30) 1 1 0 )
(command "insert" "mroads" '(36 -15) 1 1 0 )
(command "insert" "mroads" '(15 -31) 1 1 0 )
(command "insert" "mroads" '(35 -18) 1 1 0 )
(command "insert" "mroads" '(12 -16) 1 1 0 )
(command "insert" "mroads" '(36 -21) 1 1 0 )
(command "insert" "mroads" '(1 -29) 1 1 0 )
(command "insert" "mroads" '(63 -31) 1 1 0 )
(command "insert" "mroads" '(28 -19) 1 1 0 )
(command "insert" "mroads" '(2 -26) 1 1 0 )
(command "insert" "mroads" '(26 -15) 1 1 0 )
(command "insert" "mroads" '(29 -18) 1 1 0 )
(command "insert" "mroads" '(5 -25) 1 1 0 )
(command "insert" "mroads" '(16 -15) 1 1 0 )
(command "insert" "mroads" '(6 -22) 1 1 0 )
(command "insert" "mroads" '(30 -19) 1 1 0 )
(command "insert" "mroads" '(41 -25) 1 1 0 )
(command "insert" "mroads" '(56 -31) 1 1 0 )
(command "insert" "mroads" '(9 -32) 1 1 0 )
(command "insert" "mroads" '(42 -30) 1 1 0 )
(command "insert" "mroads" '(23 -16) 1 1 0 )
(command "insert" "mroads" '(43 -31) 1 1 0 )
(command "insert" "mroads" '(17 -32) 1 1 0 )
(command "insert" "mroads" '(22 -15) 1 1 0 )
(command "insert" "mroads" '(61 -32) 1 1 0 )
(command "insert" "mroads" '(52 -30) 1 1 0 )
(command "insert" "mroads" '(105 -30) 1 1 0 )
(command "insert" "mroads" '(69 -32) 1 1 0 )
(command "insert" "mroads" '(8 -17) 1 1 0 )
(command "insert" "mroads" '(97 -32) 1 1 0 )
(command "insert" "mroads" '(35 -27) 1 1 0 )
(command "insert" "mroads" '(24 -20) 1 1 0 )
(command "insert" "mroads" '(12 -15) 1 1 0 )
(command "insert" "mroads" '(36 -28) 1 1 0 )
(command "insert" "mroads" '(1 -22) 1 1 0 )
(command "insert" "mroads" '(6 -29) 1 1 0 )
(command "insert" "mroads" '(37 -17) 1 1 0 )
(command "insert" "mroads" '(2 -21) 1 1 0 )
(command "insert" "mroads" '(38 -30) 1 1 0 )
(command "insert" "mroads" '(53 -30) 1 1 0 )
(command "insert" "mroads" '(112 -32) 1 1 0 )
(command "insert" "mroads" '(39 -31) 1 1 0 )
(command "insert" "mroads" '(100 -31) 1 1 0 )
(command "insert" "mroads" '(24 -32) 1 1 0 )
(command "insert" "mroads" '(101 -30) 1 1 0 )
(command "insert" "mroads" '(19 -19) 1 1 0 )
(command "insert" "mroads" '(31 -19) 1 1 0 )
(command "insert" "mroads" '(20 -20) 1 1 0 )
(command "insert" "mroads" '(47 -31) 1 1 0 )
(command "insert" "mroads" '(32 -31) 1 1 0 )
(command "insert" "mroads" '(18 -30) 1 1 0 )
(command "insert" "mroads" '(33 -30) 1 1 0 )
(command "insert" "mroads" '(34 -29) 1 1 0 )
(command "insert" "mroads" '(8 -24) 1 1 0 )
(command "insert" "mroads" '(39 -32) 1 1 0 )
(command "insert" "mroads" '(80 -31) 1 1 0 )
(command "insert" "mroads" '(81 -30) 1 1 0 )
(command "insert" "mroads" '(113 -31) 1 1 0 )
(command "insert" "mroads" '(36 -27) 1 1 0 )
(command "insert" "mroads" '(10 -18) 1 1 0 )
(command "insert" "mroads" '(75 -32) 1 1 0 )
(command "insert" "mroads" '(37 -26) 1 1 0 )
(command "insert" "mroads" '(26 -17) 1 1 0 )
(command "insert" "mroads" '(38 -17) 1 1 0 )
(command "insert" "mroads" '(39 -20) 1 1 0 )
(command "insert" "mroads" '(88 -30) 1 1 0 )
(command "insert" "mroads" '(28 -31) 1 1 0 )
(command "insert" "mroads" '(89 -31) 1 1 0 )
(command "insert" "mroads" '(29 -30) 1 1 0 )
(command "insert" "mroads" '(3 -23) 1 1 0 )
(command "insert" "mroads" '(4 -16) 1 1 0 )
(command "insert" "mroads" '(2 -32) 1 1 0 )
(command "insert" "mroads" '(76 -31) 1 1 0 )
(command "insert" "mroads" '(46 -32) 1 1 0 )
(command "insert" "mroads" '(20 -19) 1 1 0 )
(command "insert" "mroads" '(33 -29) 1 1 0 )
(command "insert" "mroads" '(77 -30) 1 1 0 )
(command "insert" "mroads" '(40 -16) 1 1 0 )
(command "insert" "mroads" '(21 -18) 1 1 0 )
(command "insert" "mroads" '(54 -32) 1 1 0 )
(command "insert" "mroads" '(33 -23) 1 1 0 )
(command "insert" "mroads" '(90 -32) 1 1 0 )
(command "insert" "mroads" '(84 -30) 1 1 0 )
(command "insert" "mroads" '(8 -31) 1 1 0 )
(command "insert" "mroads" '(95 -31) 1 1 0 )
(command "insert" "mroads" '(85 -31) 1 1 0 )
(command "insert" "mroads" '(9 -30) 1 1 0 )
(command "insert" "mroads" '(15 -16) 1 1 0 )
(command "insert" "mroads" '(11 -16) 1 1 0 )
(command "insert" "mroads" '(1 -26) 1 1 0 )
(command "insert" "mroads" '(40 -21) 1 1 0 )
(command "insert" "mroads" '(73 -31) 1 1 0 )
(command "insert" "mroads" '(3 -28) 1 1 0 )
(command "insert" "mroads" '(64 -30) 1 1 0 )
(command "insert" "mroads" '(4 -31) 1 1 0 )
(command "insert" "mroads" '(65 -31) 1 1 0 )
(command "insert" "mroads" '(5 -30) 1 1 0 )
(command "insert" "mroads" '(40 -23) 1 1 0 )
(command "insert" "mroads" '(112 -30) 1 1 0 )
(command "insert" "mroads" '(8 -32) 1 1 0 )
(command "insert" "mroads" '(41 -22) 1 1 0 )
(command "insert" "mroads" '(22 -16) 1 1 0 )
(command "insert" "mroads" '(34 -20) 1 1 0 )
(command "insert" "mroads" '(18 -16) 1 1 0 )
(command "insert" "mroads" '(16 -32) 1 1 0 )
(command "insert" "mroads" '(60 -32) 1 1 0 )
(command "insert" "mroads" '(68 -32) 1 1 0 )
(command "insert" "mroads" '(96 -32) 1 1 0 )
(command "insert" "mroads" '(60 -30) 1 1 0 )
(command "insert" "mroads" '(104 -32) 1 1 0 )
(command "insert" "mroads" '(35 -20) 1 1 0 )
(command "insert" "mroads" '(24 -15) 1 1 0 )
(command "insert" "mroads" '(36 -23) 1 1 0 )
(command "insert" "mroads" '(108 -30) 1 1 0 )
(command "insert" "mroads" '(37 -22) 1 1 0 )
(command "insert" "mroads" '(2 -24) 1 1 0 )
(command "insert" "mroads" '(109 -31) 1 1 0 )
(command "insert" "mroads" '(29 -16) 1 1 0 )
(command "insert" "mroads" '(40 -29) 1 1 0 )
(command "insert" "mroads" '(30 -15) 1 1 0 )
(command "insert" "mroads" '(6 -26) 1 1 0 )
(command "insert" "mroads" '(40 -30) 1 1 0 )
(command "insert" "mroads" '(30 -17) 1 1 0 )
(command "insert" "mroads" '(7 -17) 1 1 0 )
(command "insert" "mroads" '(31 -20) 1 1 0 )
(command "insert" "mroads" '(20 -15) 1 1 0 )
(command "insert" "mroads" '(33 -31) 1 1 0 )
(command "insert" "mroads" '(23 -18) 1 1 0 )
(command "insert" "mroads" '(47 -32) 1 1 0 )
(command "insert" "mroads" '(33 -27) 1 1 0 )
(command "insert" "mroads" '(38 -32) 1 1 0 )
(command "insert" "mroads" '(10 -15) 1 1 0 )
(command "insert" "mroads" '(8 -19) 1 1 0 )
(command "insert" "mroads" '(35 -29) 1 1 0 )
(command "insert" "mroads" '(9 -18) 1 1 0 )
(command "insert" "mroads" '(74 -32) 1 1 0 )
(command "insert" "mroads" '(102 -30) 1 1 0 )
(command "insert" "mroads" '(36 -30) 1 1 0 )
(command "insert" "mroads" '(51 -30) 1 1 0 )
(command "insert" "mroads" '(41 -27) 1 1 0 )
(command "insert" "mroads" '(82 -32) 1 1 0 )
(command "insert" "mroads" '(37 -31) 1 1 0 )
(command "insert" "mroads" '(26 -20) 1 1 0 )
(command "insert" "mroads" '(41 -29) 1 1 0 )
(command "insert" "mroads" '(98 -31) 1 1 0 )
(command "insert" "mroads" '(38 -28) 1 1 0 )
(command "insert" "mroads" '(6 -25) 1 1 0 )
(command "insert" "mroads" '(99 -30) 1 1 0 )
(command "insert" "mroads" '(39 -25) 1 1 0 )
(command "insert" "mroads" '(3 -16) 1 1 0 )
(command "insert" "mroads" '(1 -32) 1 1 0 )
(command "insert" "mroads" '(6 -15) 1 1 0 )
(command "insert" "mroads" '(46 -31) 1 1 0 )
(command "insert" "mroads" '(53 -32) 1 1 0 )
(command "insert" "mroads" '(16 -30) 1 1 0 )
(command "insert" "mroads" '(47 -30) 1 1 0 )
(command "insert" "mroads" '(17 -31) 1 1 0 )
(command "insert" "mroads" '(32 -17) 1 1 0 )
(command "insert" "mroads" '(7 -28) 1 1 0 )
(command "insert" "mroads" '(89 -32) 1 1 0 )
(command "insert" "mroads" '(7 -24) 1 1 0 )
(command "insert" "mroads" '(94 -31) 1 1 0 )
(command "insert" "mroads" '(33 -28) 1 1 0 )
(command "insert" "mroads" '(95 -30) 1 1 0 )
(command "insert" "mroads" '(34 -27) 1 1 0 )
(command "insert" "mroads" '(8 -26) 1 1 0 )
(command "insert" "mroads" '(14 -16) 1 1 0 )
(command "insert" "mroads" '(10 -16) 1 1 0 )
(command "insert" "mroads" '(37 -24) 1 1 0 )
(command "insert" "mroads" '(68 -30) 1 1 0 )
(command "insert" "mroads" '(26 -31) 1 1 0 )
(command "insert" "mroads" '(38 -23) 1 1 0 )
(command "insert" "mroads" '(83 -30) 1 1 0 )
(command "insert" "mroads" '(27 -30) 1 1 0 )
(command "insert" "mroads" '(31 -31) 1 1 0 )
(command "insert" "mroads" '(39 -22) 1 1 0 )
(command "insert" "mroads" '(13 -31) 1 1 0 )
(command "insert" "mroads" '(74 -31) 1 1 0 )
(command "insert" "mroads" '(3 -25) 1 1 0 )
(command "insert" "mroads" '(75 -30) 1 1 0 )
(command "insert" "mroads" '(4 -18) 1 1 0 )
(command "insert" "mroads" '(62 -30) 1 1 0 )
(command "insert" "mroads" '(5 -19) 1 1 0 )
(command "insert" "mroads" '(23 -32) 1 1 0 )
(command "insert" "mroads" '(6 -24) 1 1 0 )
(command "insert" "mroads" '(21 -16) 1 1 0 )
(command "insert" "mroads" '(17 -16) 1 1 0 )
(command "insert" "mroads" '(41 -19) 1 1 0 )
(command "insert" "mroads" '(31 -32) 1 1 0 )
(command "insert" "mroads" '(59 -32) 1 1 0 )
(command "insert" "mroads" '(83 -31) 1 1 0 )
(command "insert" "mroads" '(23 -30) 1 1 0 )
(command "insert" "mroads" '(34 -18) 1 1 0 )
(command "insert" "mroads" '(67 -32) 1 1 0 )
(command "insert" "mroads" '(6 -20) 1 1 0 )
(command "insert" "mroads" '(70 -31) 1 1 0 )
(command "insert" "mroads" '(33 -15) 1 1 0 )
(command "insert" "mroads" '(71 -30) 1 1 0 )
(command "insert" "mroads" '(11 -18) 1 1 0 )
(command "insert" "mroads" '(35 -17) 1 1 0 )
(command "insert" "mroads" '(1 -24) 1 1 0 )
(command "insert" "mroads" '(39 -15) 1 1 0 )
(command "insert" "mroads" '(28 -16) 1 1 0 )
(command "insert" "mroads" '(2 -31) 1 1 0 )
(command "insert" "mroads" '(12 -30) 1 1 0 )
(command "insert" "mroads" '(41 -31) 1 1 0 )
(command "insert" "mroads" '(79 -31) 1 1 0 )
(command "insert" "mroads" '(3 -30) 1 1 0 )
(command "insert" "mroads" '(40 -17) 1 1 0 )
(command "insert" "mroads" '(4 -25) 1 1 0 )
(command "insert" "mroads" '(50 -31) 1 1 0 )
(command "insert" "mroads" '(5 -28) 1 1 0 )
(command "insert" "mroads" '(29 -15) 1 1 0 )
(command "insert" "mroads" '(40 -25) 1 1 0 )
(command "insert" "mroads" '(7 -26) 1 1 0 )
(command "insert" "mroads" '(58 -30) 1 1 0 )
(command "insert" "mroads" '(37 -32) 1 1 0 )
(command "insert" "mroads" '(59 -31) 1 1 0 )
(command "insert" "mroads" '(41 -16) 1 1 0 )
(command "insert" "mroads" '(45 -32) 1 1 0 )
(command "insert" "mroads" '(73 -32) 1 1 0 )
(command "insert" "mroads" '(106 -30) 1 1 0 )
(command "insert" "mroads" '(35 -22) 1 1 0 )
(command "insert" "mroads" '(24 -17) 1 1 0 )
(command "insert" "mroads" '(107 -31) 1 1 0 )
(command "insert" "mroads" '(81 -32) 1 1 0 )
(command "insert" "mroads" '(36 -17) 1 1 0 )
(command "insert" "mroads" '(13 -17) 1 1 0 )
(command "insert" "mroads" '(37 -20) 1 1 0 )
(command "insert" "mroads" '(2 -22) 1 1 0 )
(command "insert" "mroads" '(72 -30) 1 1 0 )
(command "insert" "mroads" '(38 -27) 1 1 0 )
(command "insert" "mroads" '(54 -30) 1 1 0 )
(command "insert" "mroads" '(55 -31) 1 1 0 )
(command "insert" "mroads" '(116 -31) 1 1 0 )
(command "insert" "mroads" '(52 -32) 1 1 0 )
(command "insert" "mroads" '(7 -19) 1 1 0 )
(command "insert" "mroads" '(103 -31) 1 1 0 )
(command "insert" "mroads" '(88 -32) 1 1 0 )
(command "insert" "mroads" '(84 -31) 1 1 0 )
(command "insert" "mroads" '(8 -15) 1 1 0 )
(command "insert" "mroads" '(33 -25) 1 1 0 )
(command "insert" "mroads" '(34 -30) 1 1 0 )
(command "insert" "mroads" '(8 -21) 1 1 0 )
(command "insert" "mroads" '(35 -31) 1 1 0 )
(command "insert" "mroads" '(9 -16) 1 1 0 )
(command "insert" "mroads" '(14 -15) 1 1 0 )
(command "insert" "mroads" '(40 -28) 1 1 0 )
(command "insert" "mroads" '(96 -31) 1 1 0 )
(command "insert" "mroads" '(36 -24) 1 1 0 )
(command "insert" "mroads" '(78 -31) 1 1 0 )
(command "insert" "mroads" '(82 -30) 1 1 0 )
(command "insert" "mroads" '(97 -30) 1 1 0 )
(command "insert" "mroads" '(37 -29) 1 1 0 )
(command "insert" "mroads" '(26 -18) 1 1 0 )
(command "insert" "mroads" '(38 -18) 1 1 0 )
(command "insert" "mroads" '(103 -32) 1 1 0 )
(command "insert" "mroads" '(39 -27) 1 1 0 )
(command "insert" "mroads" '(4 -15) 1 1 0 )
(command "insert" "mroads" '(7 -23) 1 1 0 )
(command "insert" "mroads" '(3 -18) 1 1 0 )
(command "insert" "mroads" '(30 -30) 1 1 0 )
(command "insert" "mroads" '(4 -21) 1 1 0 )
(command "insert" "mroads" '(79 -30) 1 1 0 )
(command "insert" "mroads" '(20 -16) 1 1 0 )
(command "insert" "mroads" '(92 -31) 1 1 0 )
(command "insert" "mroads" '(16 -16) 1 1 0 )
(command "insert" "mroads" '(30 -32) 1 1 0 )
(command "insert" "mroads" '(93 -30) 1 1 0 )
(command "insert" "mroads" '(58 -32) 1 1 0 )
(command "insert" "mroads" '(32 -19) 1 1 0 )
(command "insert" "mroads" '(33 -18) 1 1 0 )
(command "insert" "mroads" '(66 -32) 1 1 0 )
(command "insert" "mroads" '(110 -32) 1 1 0 )
(command "insert" "mroads" '(34 -25) 1 1 0 )
(command "insert" "mroads" '(8 -28) 1 1 0 )
(command "insert" "mroads" '(57 -30) 1 1 0 )
(command "insert" "mroads" '(24 -31) 1 1 0 )
(command "insert" "mroads" '(10 -30) 1 1 0 )
(command "insert" "mroads" '(25 -30) 1 1 0 )
(command "insert" "mroads" '(11 -31) 1 1 0 )
(command "insert" "mroads" '(72 -31) 1 1 0 )
(command "insert" "mroads" '(27 -16) 1 1 0 )
(command "insert" "mroads" '(49 -32) 1 1 0 )
(command "insert" "mroads" '(73 -30) 1 1 0 )
(command "insert" "mroads" '(3 -27) 1 1 0 )
(command "insert" "mroads" '(4 -28) 1 1 0 )
(command "insert" "mroads" '(41 -15) 1 1 0 )
(command "insert" "mroads" '(5 -17) 1 1 0 )
(command "insert" "mroads" '(20 -31) 1 1 0 )
(command "insert" "mroads" '(6 -30) 1 1 0 )
(command "insert" "mroads" '(21 -30) 1 1 0 )
(command "insert" "mroads" '(104 -31) 1 1 0 )
(command "insert" "mroads" '(68 -31) 1 1 0 )
(command "insert" "mroads" '(36 -32) 1 1 0 )
(command "insert" "mroads" '(69 -30) 1 1 0 )
(command "insert" "mroads" '(34 -16) 1 1 0 )
(command "insert" "mroads" '(44 -32) 1 1 0 )
(command "insert" "mroads" '(72 -32) 1 1 0 )
(command "insert" "mroads" '(6 -16) 1 1 0 )
(command "insert" "mroads" '(80 -32) 1 1 0 )
(command "insert" "mroads" '(11 -20) 1 1 0 )
(command "insert" "mroads" '(35 -19) 1 1 0 )
(command "insert" "mroads" '(36 -20) 1 1 0 )
(command "insert" "mroads" '(1 -30) 1 1 0 )
(command "insert" "mroads" '(28 -18) 1 1 0 )
(command "insert" "mroads" '(2 -29) 1 1 0 )
(command "insert" "mroads" '(48 -31) 1 1 0 )
(command "insert" "mroads" '(29 -19) 1 1 0 )
(command "insert" "mroads" '(27 -15) 1 1 0 )
(command "insert" "mroads" '(15 -32) 1 1 0 )
(command "insert" "mroads" '(4 -27) 1 1 0 )
(command "insert" "mroads" '(32 -32) 1 1 0 )
(command "insert" "mroads" '(5 -26) 1 1 0 )
(command "insert" "mroads" '(51 -32) 1 1 0 )
(command "insert" "mroads" '(40 -27) 1 1 0 )
(command "insert" "mroads" '(30 -18) 1 1 0 )
(command "insert" "mroads" '(17 -15) 1 1 0 )
(command "insert" "mroads" '(41 -26) 1 1 0 )
(command "insert" "mroads" '(22 -20) 1 1 0 )
(command "insert" "mroads" '(23 -17) 1 1 0 )
(command "insert" "mroads" '(86 -31) 1 1 0 )
(command "insert" "mroads" '(104 -30) 1 1 0 )
(command "insert" "mroads" '(44 -31) 1 1 0 )
(command "insert" "mroads" '(23 -15) 1 1 0 )
(command "insert" "mroads" '(105 -31) 1 1 0 )
(command "insert" "mroads" '(45 -30) 1 1 0 )
(command "insert" "mroads" '(8 -16) 1 1 0 )
(command "insert" "mroads" '(35 -24) 1 1 0 )
(command "insert" "mroads" '(50 -32) 1 1 0 )
(command "insert" "mroads" '(24 -19) 1 1 0 )
(command "insert" "mroads" '(36 -19) 1 1 0 )
(command "insert" "mroads" '(1 -23) 1 1 0 )
(command "insert" "mroads" '(25 -18) 1 1 0 )
(command "insert" "mroads" '(13 -15) 1 1 0 )
(command "insert" "mroads" '(37 -18) 1 1 0 )
(command "insert" "mroads" '(102 -32) 1 1 0 )
(command "insert" "mroads" '(38 -25) 1 1 0 )
(command "insert" "mroads" '(53 -31) 1 1 0 )
(command "insert" "mroads" '(78 -30) 1 1 0 )
(command "insert" "mroads" '(39 -28) 1 1 0 )
(command "insert" "mroads" '(100 -30) 1 1 0 )
(command "insert" "mroads" '(115 -30) 1 1 0 )
(command "insert" "mroads" '(25 -17) 1 1 0 )
(command "insert" "mroads" '(101 -31) 1 1 0 )
(command "insert" "mroads" '(21 -32) 1 1 0 )
(command "insert" "mroads" '(19 -16) 1 1 0 )
(command "insert" "mroads" '(31 -16) 1 1 0 )
(command "insert" "mroads" '(29 -32) 1 1 0 )
(command "insert" "mroads" '(41 -17) 1 1 0 )
(command "insert" "mroads" '(32 -30) 1 1 0 )
(command "insert" "mroads" '(65 -32) 1 1 0 )
(command "insert" "mroads" '(52 -31) 1 1 0 )
(command "insert" "mroads" '(7 -20) 1 1 0 )
(command "insert" "mroads" '(110 -31) 1 1 0 )
(command "insert" "mroads" '(34 -28) 1 1 0 )
(command "insert" "mroads" '(8 -23) 1 1 0 )
(command "insert" "mroads" '(80 -30) 1 1 0 )
(command "insert" "mroads" '(111 -30) 1 1 0 )
(command "insert" "mroads" '(57 -32) 1 1 0 )
(command "insert" "mroads" '(81 -31) 1 1 0 )
(command "insert" "mroads" '(36 -26) 1 1 0 )
(command "insert" "mroads" '(40 -24) 1 1 0 )
(command "insert" "mroads" '(37 -27) 1 1 0 )
(command "insert" "mroads" '(26 -16) 1 1 0 )
(command "insert" "mroads" '(38 -16) 1 1 0 )
(command "insert" "mroads" '(39 -21) 1 1 0 )
(command "insert" "mroads" '(28 -30) 1 1 0 )
(command "insert" "mroads" '(29 -31) 1 1 0 )
(command "insert" "mroads" '(3 -20) 1 1 0 )
(command "insert" "mroads" '(90 -31) 1 1 0 )
(command "insert" "mroads" '(4 -23) 1 1 0 )
(command "insert" "mroads" '(76 -30) 1 1 0 )
(command "insert" "mroads" '(91 -30) 1 1 0 )
(command "insert" "mroads" '(7 -27) 1 1 0 )
(command "insert" "mroads" '(5 -22) 1 1 0 )
(command "insert" "mroads" '(20 -18) 1 1 0 )
(command "insert" "mroads" '(77 -31) 1 1 0 )
(command "insert" "mroads" '(21 -19) 1 1 0 )
(command "insert" "mroads" '(7 -32) 1 1 0 )
(command "insert" "mroads" '(35 -32) 1 1 0 )
(command "insert" "mroads" '(113 -30) 1 1 0 )
(command "insert" "mroads" '(33 -16) 1 1 0 )
(command "insert" "mroads" '(34 -23) 1 1 0 )
(command "insert" "mroads" '(8 -30) 1 1 0 )
(command "insert" "mroads" '(87 -32) 1 1 0 )
(command "insert" "mroads" '(9 -31) 1 1 0 )
(command "insert" "mroads" '(95 -32) 1 1 0 )
(command "insert" "mroads" '(15 -17) 1 1 0 )
(command "insert" "mroads" '(87 -30) 1 1 0 )
(command "insert" "mroads" '(11 -17) 1 1 0 )
(command "insert" "mroads" '(27 -18) 1 1 0 )
(command "insert" "mroads" '(1 -27) 1 1 0 )
(command "insert" "mroads" '(39 -18) 1 1 0 )
(command "insert" "mroads" '(14 -32) 1 1 0 )
(command "insert" "mroads" '(3 -29) 1 1 0 )
(command "insert" "mroads" '(4 -30) 1 1 0 )
(command "insert" "mroads" '(19 -30) 1 1 0 )
(command "layer" "m" "Commmer" "" )
(command "insert" "Commmer" '(102 -38) 1 1 0 )
(command "insert" "Commmer" '(110 -36) 1 1 0 )
(command "insert" "Commmer" '(107 -41) 1 1 0 )
(command "insert" "Commmer" '(109 -37) 1 1 0 )
(command "insert" "Commmer" '(109 -38) 1 1 0 )
(command "insert" "Commmer" '(106 -33) 1 1 0 )
(command "insert" "Commmer" '(107 -39) 1 1 0 )
(command "insert" "Commmer" '(110 -37) 1 1 0 )
(command "insert" "Commmer" '(105 -34) 1 1 0 )
(command "insert" "Commmer" '(104 -37) 1 1 0 )
(command "insert" "Commmer" '(103 -38) 1 1 0 )
(command "insert" "Commmer" '(107 -35) 1 1 0 )
(command "insert" "Commmer" '(108 -36) 1 1 0 )
(command "insert" "Commmer" '(109 -36) 1 1 0 )
(command "insert" "Commmer" '(106 -34) 1 1 0 )
(command "insert" "Commmer" '(102 -36) 1 1 0 )
(command "insert" "Commmer" '(105 -35) 1 1 0 )
(command "insert" "Commmer" '(105 -33) 1 1 0 )
(command "insert" "Commmer" '(107 -34) 1 1 0 )
(command "insert" "Commmer" '(110 -38) 1 1 0 )
(command "insert" "Commmer" '(108 -37) 1 1 0 )
(command "insert" "Commmer" '(103 -37) 1 1 0 )
(command "insert" "Commmer" '(106 -35) 1 1 0 )
(command "insert" "Commmer" '(102 -37) 1 1 0 )
(command "insert" "Commmer" '(106 -40) 1 1 0 )
(command "insert" "Commmer" '(106 -39) 1 1 0 )
(command "insert" "Commmer" '(108 -38) 1 1 0 )
(command "insert" "Commmer" '(103 -36) 1 1 0 )
(command "insert" "Commmer" '(107 -40) 1 1 0 )
(command "insert" "Commmer" '(107 -33) 1 1 0 )
(command "insert" "Commmer" '(105 -41) 1 1 0 )
(command "insert" "Commmer" '(105 -40) 1 1 0 )
(command "insert" "Commmer" '(104 -38) 1 1 0 )
(command "insert" "Commmer" '(104 -36) 1 1 0 )
(command "insert" "Commmer" '(106 -41) 1 1 0 )
(command "insert" "Commmer" '(105 -39) 1 1 0 )
(command "layer" "m" "edge" "" )
(command "insert" "edge" '(95 -43) 1 1 0 )
(command "insert" "edge" '(94 -44) 1 1 0 )
(command "insert" "edge" '(93 -42) 1 1 0 )
(command "insert" "edge" '(93 -43) 1 1 0 )
(command "insert" "edge" '(94 -43) 1 1 0 )
(command "insert" "edge" '(93 -44) 1 1 0 )
(command "insert" "edge" '(94 -42) 1 1 0 )
(command "insert" "edge" '(95 -44) 1 1 0 )
(command "insert" "edge" '(95 -42) 1 1 0 )
(command "layer" "m" "edge" "" )
(command "insert" "edge" '(54 -2) 1 1 0 )
(command "insert" "edge" '(55 -2) 1 1 0 )
(command "insert" "edge" '(56 -2) 1 1 0 )
(command "insert" "edge" '(55 -1) 1 1 0 )
(command "insert" "edge" '(56 -1) 1 1 0 )
(command "insert" "edge" '(54 -1) 1 1 0 )
(command "layer" "m" "edge" "" )
(command "insert" "edge" '(2 -39) 1 1 0 )
(command "insert" "edge" '(1 -44) 1 1 0 )
(command "insert" "edge" '(2 -43) 1 1 0 )
(command "insert" "edge" '(1 -46) 1 1 0 )
(command "insert" "edge" '(2 -47) 1 1 0 )
(command "insert" "edge" '(2 -45) 1 1 0 )
(command "insert" "edge" '(1 -39) 1 1 0 )
(command "insert" "edge" '(1 -42) 1 1 0 )
(command "insert" "edge" '(1 -47) 1 1 0 )
(command "insert" "edge" '(2 -46) 1 1 0 )
(command "insert" "edge" '(2 -41) 1 1 0 )
(command "insert" "edge" '(2 -40) 1 1 0 )
(command "insert" "edge" '(1 -40) 1 1 0 )
(command "insert" "edge" '(2 -42) 1 1 0 )
(command "insert" "edge" '(1 -41) 1 1 0 )
(command "insert" "edge" '(1 -45) 1 1 0 )
(command "insert" "edge" '(1 -43) 1 1 0 )
(command "insert" "edge" '(2 -44) 1 1 0 )
(command "layer" "m" "ped" "" )
(command "insert" "ped" '(58 -24) 1 1 0 )
(command "insert" "ped" '(59 -26) 1 1 0 )
(command "insert" "ped" '(58 -26) 1 1 0 )
(command "insert" "ped" '(59 -24) 1 1 0 )
(command "insert" "ped" '(57 -24) 1 1 0 )
(command "insert" "ped" '(59 -25) 1 1 0 )
(command "insert" "ped" '(57 -25) 1 1 0 )
(command "insert" "ped" '(57 -26) 1 1 0 )
(command "insert" "ped" '(58 -25) 1 1 0 )
(command "layer" "m" "ped" "" )
(command "insert" "ped" '(213 -64) 1 1 0 )
(command "insert" "ped" '(211 -61) 1 1 0 )
(command "insert" "ped" '(212 -62) 1 1 0 )
(command "insert" "ped" '(210 -61) 1 1 0 )
(command "insert" "ped" '(213 -63) 1 1 0 )
(command "insert" "ped" '(215 -65) 1 1 0 )
(command "insert" "ped" '(214 -64) 1 1 0 )
(command "insert" "ped" '(211 -62) 1 1 0 )
(command "insert" "ped" '(211 -60) 1 1 0 )
(command "insert" "ped" '(215 -63) 1 1 0 )
(command "insert" "ped" '(213 -65) 1 1 0 )
(command "insert" "ped" '(212 -61) 1 1 0 )
(command "insert" "ped" '(212 -60) 1 1 0 )
(command "insert" "ped" '(215 -64) 1 1 0 )
(command "insert" "ped" '(210 -60) 1 1 0 )
(command "insert" "ped" '(214 -65) 1 1 0 )
(command "insert" "ped" '(210 -62) 1 1 0 )
(command "insert" "ped" '(214 -63) 1 1 0 )
(command "layer" "m" "ped" "" )
(command "insert" "ped" '(1 -3) 1 1 0 )
(command "insert" "ped" '(2 -18) 1 1 0 )
(command "insert" "ped" '(2 -8) 1 1 0 )
(command "insert" "ped" '(1 -17) 1 1 0 )
(command "insert" "ped" '(2 -1) 1 1 0 )
(command "insert" "ped" '(1 -15) 1 1 0 )
(command "insert" "ped" '(6 -2) 1 1 0 )
(command "insert" "ped" '(1 -6) 1 1 0 )
(command "insert" "ped" '(2 -12) 1 1 0 )
(command "insert" "ped" '(5 -1) 1 1 0 )
(command "insert" "ped" '(2 -5) 1 1 0 )
(command "insert" "ped" '(1 -11) 1 1 0 )
(command "insert" "ped" '(7 -2) 1 1 0 )
(command "insert" "ped" '(1 -2) 1 1 0 )
(command "insert" "ped" '(2 -19) 1 1 0 )
(command "insert" "ped" '(2 -9) 1 1 0 )
(command "insert" "ped" '(8 -1) 1 1 0 )
(command "insert" "ped" '(1 -16) 1 1 0 )
(command "insert" "ped" '(1 -14) 1 1 0 )
(command "insert" "ped" '(1 -5) 1 1 0 )
(command "insert" "ped" '(2 -13) 1 1 0 )
(command "insert" "ped" '(1 -20) 1 1 0 )
(command "insert" "ped" '(2 -2) 1 1 0 )
(command "insert" "ped" '(1 -10) 1 1 0 )
(command "insert" "ped" '(4 -1) 1 1 0 )
(command "insert" "ped" '(1 -1) 1 1 0 )
(command "insert" "ped" '(2 -16) 1 1 0 )
(command "insert" "ped" '(3 -2) 1 1 0 )
(command "insert" "ped" '(2 -6) 1 1 0 )
(command "insert" "ped" '(8 -2) 1 1 0 )
(command "insert" "ped" '(7 -1) 1 1 0 )
(command "insert" "ped" '(1 -13) 1 1 0 )
(command "insert" "ped" '(2 -20) 1 1 0 )
(command "insert" "ped" '(1 -4) 1 1 0 )
(command "insert" "ped" '(2 -10) 1 1 0 )
(command "insert" "ped" '(1 -19) 1 1 0 )
(command "insert" "ped" '(2 -3) 1 1 0 )
(command "insert" "ped" '(1 -9) 1 1 0 )
(command "insert" "ped" '(4 -2) 1 1 0 )
(command "insert" "ped" '(2 -14) 1 1 0 )
(command "insert" "ped" '(2 -17) 1 1 0 )
(command "insert" "ped" '(2 -7) 1 1 0 )
(command "insert" "ped" '(1 -12) 1 1 0 )
(command "insert" "ped" '(6 -1) 1 1 0 )
(command "insert" "ped" '(3 -1) 1 1 0 )
(command "insert" "ped" '(2 -11) 1 1 0 )
(command "insert" "ped" '(1 -18) 1 1 0 )
(command "insert" "ped" '(1 -8) 1 1 0 )
(command "insert" "ped" '(1 -7) 1 1 0 )
(command "insert" "ped" '(2 -15) 1 1 0 )
(command "insert" "ped" '(5 -2) 1 1 0 )
(command "insert" "ped" '(2 -4) 1 1 0 )
(command "layer" "m" "ped" "" )
(command "insert" "ped" '(1 -3) 1 1 0 )
(command "insert" "ped" '(2 -18) 1 1 0 )
(command "insert" "ped" '(2 -8) 1 1 0 )
(command "insert" "ped" '(1 -17) 1 1 0 )
(command "insert" "ped" '(2 -1) 1 1 0 )
(command "insert" "ped" '(1 -15) 1 1 0 )
(command "insert" "ped" '(6 -2) 1 1 0 )
(command "insert" "ped" '(1 -6) 1 1 0 )
(command "insert" "ped" '(2 -12) 1 1 0 )
(command "insert" "ped" '(5 -1) 1 1 0 )
(command "insert" "ped" '(2 -5) 1 1 0 )
(command "insert" "ped" '(1 -11) 1 1 0 )
(command "insert" "ped" '(1 -20) 1 1 0 )
(command "insert" "ped" '(1 -2) 1 1 0 )
(command "insert" "ped" '(2 -19) 1 1 0 )
(command "insert" "ped" '(2 -9) 1 1 0 )
(command "insert" "ped" '(8 -1) 1 1 0 )
(command "insert" "ped" '(1 -16) 1 1 0 )
(command "insert" "ped" '(1 -14) 1 1 0 )
(command "insert" "ped" '(1 -5) 1 1 0 )
(command "insert" "ped" '(2 -13) 1 1 0 )
(command "insert" "ped" '(7 -2) 1 1 0 )
(command "insert" "ped" '(2 -2) 1 1 0 )
(command "insert" "ped" '(1 -10) 1 1 0 )
(command "insert" "ped" '(4 -1) 1 1 0 )
(command "insert" "ped" '(1 -1) 1 1 0 )
(command "insert" "ped" '(2 -16) 1 1 0 )
(command "insert" "ped" '(3 -2) 1 1 0 )
(command "insert" "ped" '(2 -6) 1 1 0 )
(command "insert" "ped" '(8 -2) 1 1 0 )
(command "insert" "ped" '(7 -1) 1 1 0 )
(command "insert" "ped" '(1 -13) 1 1 0 )
(command "insert" "ped" '(2 -20) 1 1 0 )
(command "insert" "ped" '(1 -4) 1 1 0 )
(command "insert" "ped" '(2 -10) 1 1 0 )
(command "insert" "ped" '(1 -19) 1 1 0 )
(command "insert" "ped" '(2 -3) 1 1 0 )
(command "insert" "ped" '(1 -9) 1 1 0 )
(command "insert" "ped" '(4 -2) 1 1 0 )
(command "insert" "ped" '(2 -14) 1 1 0 )
(command "insert" "ped" '(2 -17) 1 1 0 )
(command "insert" "ped" '(2 -7) 1 1 0 )
(command "insert" "ped" '(1 -12) 1 1 0 )
(command "insert" "ped" '(6 -1) 1 1 0 )
(command "insert" "ped" '(3 -1) 1 1 0 )
(command "insert" "ped" '(2 -11) 1 1 0 )
(command "insert" "ped" '(1 -18) 1 1 0 )
(command "insert" "ped" '(1 -8) 1 1 0 )
(command "insert" "ped" '(1 -7) 1 1 0 )
(command "insert" "ped" '(2 -15) 1 1 0 )
(command "insert" "ped" '(5 -2) 1 1 0 )
(command "insert" "ped" '(2 -4) 1 1 0 )
(command "layer" "m" "ped" "" )
(command "insert" "ped" '(1 -3) 1 1 0 )
(command "insert" "ped" '(2 -18) 1 1 0 )
(command "insert" "ped" '(2 -8) 1 1 0 )
(command "insert" "ped" '(1 -17) 1 1 0 )
(command "insert" "ped" '(2 -1) 1 1 0 )
(command "insert" "ped" '(1 -15) 1 1 0 )
(command "insert" "ped" '(6 -2) 1 1 0 )
(command "insert" "ped" '(1 -6) 1 1 0 )
(command "insert" "ped" '(2 -12) 1 1 0 )
(command "insert" "ped" '(5 -1) 1 1 0 )
(command "insert" "ped" '(2 -5) 1 1 0 )
(command "insert" "ped" '(1 -11) 1 1 0 )
(command "insert" "ped" '(7 -2) 1 1 0 )
(command "insert" "ped" '(1 -2) 1 1 0 )
(command "insert" "ped" '(2 -19) 1 1 0 )
(command "insert" "ped" '(2 -9) 1 1 0 )
(command "insert" "ped" '(8 -1) 1 1 0 )
(command "insert" "ped" '(1 -16) 1 1 0 )
(command "insert" "ped" '(1 -14) 1 1 0 )
(command "insert" "ped" '(1 -5) 1 1 0 )
(command "insert" "ped" '(2 -13) 1 1 0 )
(command "insert" "ped" '(1 -20) 1 1 0 )
(command "insert" "ped" '(2 -2) 1 1 0 )
(command "insert" "ped" '(1 -10) 1 1 0 )
(command "insert" "ped" '(4 -1) 1 1 0 )
(command "insert" "ped" '(1 -1) 1 1 0 )
(command "insert" "ped" '(2 -16) 1 1 0 )
(command "insert" "ped" '(3 -2) 1 1 0 )
(command "insert" "ped" '(2 -6) 1 1 0 )
(command "insert" "ped" '(8 -2) 1 1 0 )
(command "insert" "ped" '(7 -1) 1 1 0 )
(command "insert" "ped" '(1 -13) 1 1 0 )
(command "insert" "ped" '(2 -20) 1 1 0 )
(command "insert" "ped" '(1 -4) 1 1 0 )
(command "insert" "ped" '(2 -10) 1 1 0 )
(command "insert" "ped" '(1 -19) 1 1 0 )
(command "insert" "ped" '(2 -3) 1 1 0 )
(command "insert" "ped" '(1 -9) 1 1 0 )
(command "insert" "ped" '(4 -2) 1 1 0 )
(command "insert" "ped" '(2 -14) 1 1 0 )
(command "insert" "ped" '(2 -17) 1 1 0 )
(command "insert" "ped" '(2 -7) 1 1 0 )
(command "insert" "ped" '(1 -12) 1 1 0 )
(command "insert" "ped" '(6 -1) 1 1 0 )
(command "insert" "ped" '(3 -1) 1 1 0 )
(command "insert" "ped" '(2 -11) 1 1 0 )
(command "insert" "ped" '(1 -18) 1 1 0 )
(command "insert" "ped" '(1 -8) 1 1 0 )
(command "insert" "ped" '(1 -7) 1 1 0 )
(command "insert" "ped" '(2 -15) 1 1 0 )
(command "insert" "ped" '(5 -2) 1 1 0 )
(command "insert" "ped" '(2 -4) 1 1 0 )
(command "layer" "m" "ped" "" )
(command "insert" "ped" '(1 -3) 1 1 0 )
(command "insert" "ped" '(2 -18) 1 1 0 )
(command "insert" "ped" '(2 -8) 1 1 0 )
(command "insert" "ped" '(1 -17) 1 1 0 )
(command "insert" "ped" '(2 -1) 1 1 0 )
(command "insert" "ped" '(1 -15) 1 1 0 )
(command "insert" "ped" '(6 -2) 1 1 0 )
(command "insert" "ped" '(1 -6) 1 1 0 )
(command "insert" "ped" '(2 -12) 1 1 0 )
(command "insert" "ped" '(5 -1) 1 1 0 )
(command "insert" "ped" '(2 -5) 1 1 0 )
(command "insert" "ped" '(1 -11) 1 1 0 )
(command "insert" "ped" '(1 -20) 1 1 0 )
(command "insert" "ped" '(1 -2) 1 1 0 )
(command "insert" "ped" '(2 -19) 1 1 0 )
(command "insert" "ped" '(2 -9) 1 1 0 )
(command "insert" "ped" '(8 -1) 1 1 0 )
(command "insert" "ped" '(1 -16) 1 1 0 )
(command "insert" "ped" '(1 -14) 1 1 0 )
(command "insert" "ped" '(1 -5) 1 1 0 )
(command "insert" "ped" '(2 -13) 1 1 0 )
(command "insert" "ped" '(7 -2) 1 1 0 )
(command "insert" "ped" '(2 -2) 1 1 0 )
(command "insert" "ped" '(1 -10) 1 1 0 )
(command "insert" "ped" '(4 -1) 1 1 0 )
(command "insert" "ped" '(1 -1) 1 1 0 )
(command "insert" "ped" '(2 -16) 1 1 0 )
(command "insert" "ped" '(3 -2) 1 1 0 )
(command "insert" "ped" '(2 -6) 1 1 0 )
(command "insert" "ped" '(8 -2) 1 1 0 )
(command "insert" "ped" '(7 -1) 1 1 0 )
(command "insert" "ped" '(1 -13) 1 1 0 )
(command "insert" "ped" '(2 -20) 1 1 0 )
(command "insert" "ped" '(1 -4) 1 1 0 )
(command "insert" "ped" '(2 -10) 1 1 0 )
(command "insert" "ped" '(1 -19) 1 1 0 )
(command "insert" "ped" '(2 -3) 1 1 0 )
(command "insert" "ped" '(1 -9) 1 1 0 )
(command "insert" "ped" '(4 -2) 1 1 0 )
(command "insert" "ped" '(2 -14) 1 1 0 )
(command "insert" "ped" '(2 -17) 1 1 0 )
(command "insert" "ped" '(2 -7) 1 1 0 )
(command "insert" "ped" '(1 -12) 1 1 0 )
(command "insert" "ped" '(6 -1) 1 1 0 )
(command "insert" "ped" '(3 -1) 1 1 0 )
(command "insert" "ped" '(2 -11) 1 1 0 )
(command "insert" "ped" '(1 -18) 1 1 0 )
(command "insert" "ped" '(1 -8) 1 1 0 )
(command "insert" "ped" '(1 -7) 1 1 0 )
(command "insert" "ped" '(2 -15) 1 1 0 )
(command "insert" "ped" '(5 -2) 1 1 0 )
(command "insert" "ped" '(2 -4) 1 1 0 )
(command "layer" "m" "Commmer" "" )
(command "insert" "Commmer" '(32 -1) 1 1 0 )
(command "insert" "Commmer" '(23 -1) 1 1 0 )
(command "insert" "Commmer" '(21 -2) 1 1 0 )
(command "insert" "Commmer" '(16 -2) 1 1 0 )
(command "insert" "Commmer" '(15 -1) 1 1 0 )
(command "insert" "Commmer" '(28 -1) 1 1 0 )
(command "insert" "Commmer" '(25 -1) 1 1 0 )
(command "insert" "Commmer" '(27 -2) 1 1 0 )
(command "insert" "Commmer" '(32 -2) 1 1 0 )
(command "insert" "Commmer" '(18 -1) 1 1 0 )
(command "insert" "Commmer" '(31 -1) 1 1 0 )
(command "insert" "Commmer" '(22 -2) 1 1 0 )
(command "insert" "Commmer" '(21 -1) 1 1 0 )
(command "insert" "Commmer" '(23 -2) 1 1 0 )
(command "insert" "Commmer" '(17 -2) 1 1 0 )
(command "insert" "Commmer" '(28 -2) 1 1 0 )
(command "insert" "Commmer" '(34 -1) 1 1 0 )
(command "insert" "Commmer" '(24 -1) 1 1 0 )
(command "insert" "Commmer" '(33 -2) 1 1 0 )
(command "insert" "Commmer" '(30 -1) 1 1 0 )
(command "insert" "Commmer" '(27 -1) 1 1 0 )
(command "insert" "Commmer" '(18 -2) 1 1 0 )
(command "insert" "Commmer" '(20 -1) 1 1 0 )
(command "insert" "Commmer" '(17 -1) 1 1 0 )
(command "insert" "Commmer" '(19 -2) 1 1 0 )
(command "insert" "Commmer" '(29 -2) 1 1 0 )
(command "insert" "Commmer" '(24 -2) 1 1 0 )
(command "insert" "Commmer" '(34 -2) 1 1 0 )
(command "insert" "Commmer" '(35 -1) 1 1 0 )
(command "insert" "Commmer" '(26 -2) 1 1 0 )
(command "insert" "Commmer" '(33 -1) 1 1 0 )
(command "insert" "Commmer" '(35 -2) 1 1 0 )
(command "insert" "Commmer" '(26 -1) 1 1 0 )
(command "insert" "Commmer" '(15 -2) 1 1 0 )
(command "insert" "Commmer" '(20 -2) 1 1 0 )
(command "insert" "Commmer" '(30 -2) 1 1 0 )
(command "insert" "Commmer" '(16 -1) 1 1 0 )
(command "insert" "Commmer" '(29 -1) 1 1 0 )
(command "insert" "Commmer" '(31 -2) 1 1 0 )
(command "insert" "Commmer" '(25 -2) 1 1 0 )
(command "insert" "Commmer" '(22 -1) 1 1 0 )
(command "insert" "Commmer" '(19 -1) 1 1 0 )
(command "layer" "m" "edge" "" )
(command "insert" "edge" '(167 -26) 1 1 0 )
(command "insert" "edge" '(167 -24) 1 1 0 )
(command "insert" "edge" '(165 -24) 1 1 0 )
(command "insert" "edge" '(167 -25) 1 1 0 )
(command "insert" "edge" '(165 -25) 1 1 0 )
(command "insert" "edge" '(166 -25) 1 1 0 )
(command "insert" "edge" '(165 -26) 1 1 0 )
(command "insert" "edge" '(166 -24) 1 1 0 )
(command "insert" "edge" '(166 -26) 1 1 0 )
(command "layer" "m" "Commmer" "" )
(command "insert" "Commmer" '(32 -1) 1 1 0 )
(command "insert" "Commmer" '(35 -1) 1 1 0 )
(command "insert" "Commmer" '(21 -2) 1 1 0 )
(command "insert" "Commmer" '(16 -2) 1 1 0 )
(command "insert" "Commmer" '(26 -2) 1 1 0 )
(command "insert" "Commmer" '(28 -1) 1 1 0 )
(command "insert" "Commmer" '(25 -1) 1 1 0 )
(command "insert" "Commmer" '(34 -2) 1 1 0 )
(command "insert" "Commmer" '(27 -2) 1 1 0 )
(command "insert" "Commmer" '(32 -2) 1 1 0 )
(command "insert" "Commmer" '(18 -1) 1 1 0 )
(command "insert" "Commmer" '(31 -1) 1 1 0 )
(command "insert" "Commmer" '(22 -2) 1 1 0 )
(command "insert" "Commmer" '(21 -1) 1 1 0 )
(command "insert" "Commmer" '(23 -2) 1 1 0 )
(command "insert" "Commmer" '(17 -2) 1 1 0 )
(command "insert" "Commmer" '(28 -2) 1 1 0 )
(command "insert" "Commmer" '(34 -1) 1 1 0 )
(command "insert" "Commmer" '(24 -1) 1 1 0 )
(command "insert" "Commmer" '(33 -2) 1 1 0 )
(command "insert" "Commmer" '(30 -1) 1 1 0 )
(command "insert" "Commmer" '(27 -1) 1 1 0 )
(command "insert" "Commmer" '(18 -2) 1 1 0 )
(command "insert" "Commmer" '(20 -1) 1 1 0 )
(command "insert" "Commmer" '(17 -1) 1 1 0 )
(command "insert" "Commmer" '(19 -2) 1 1 0 )
(command "insert" "Commmer" '(29 -2) 1 1 0 )
(command "insert" "Commmer" '(24 -2) 1 1 0 )
(command "insert" "Commmer" '(23 -1) 1 1 0 )
(command "insert" "Commmer" '(15 -1) 1 1 0 )
(command "insert" "Commmer" '(33 -1) 1 1 0 )
(command "insert" "Commmer" '(35 -2) 1 1 0 )
(command "insert" "Commmer" '(26 -1) 1 1 0 )
(command "insert" "Commmer" '(15 -2) 1 1 0 )
(command "insert" "Commmer" '(20 -2) 1 1 0 )
(command "insert" "Commmer" '(30 -2) 1 1 0 )
(command "insert" "Commmer" '(16 -1) 1 1 0 )
(command "insert" "Commmer" '(29 -1) 1 1 0 )
(command "insert" "Commmer" '(31 -2) 1 1 0 )
(command "insert" "Commmer" '(25 -2) 1 1 0 )
(command "insert" "Commmer" '(22 -1) 1 1 0 )
(command "insert" "Commmer" '(19 -1) 1 1 0 )
(command "layer" "m" "ped" "" )
(command "insert" "ped" '(1 -3) 1 1 0 )
(command "insert" "ped" '(2 -18) 1 1 0 )
(command "insert" "ped" '(2 -8) 1 1 0 )
(command "insert" "ped" '(1 -17) 1 1 0 )
(command "insert" "ped" '(2 -1) 1 1 0 )
(command "insert" "ped" '(1 -15) 1 1 0 )
(command "insert" "ped" '(6 -2) 1 1 0 )
(command "insert" "ped" '(1 -6) 1 1 0 )
(command "insert" "ped" '(2 -12) 1 1 0 )
(command "insert" "ped" '(5 -1) 1 1 0 )
(command "insert" "ped" '(2 -5) 1 1 0 )
(command "insert" "ped" '(1 -11) 1 1 0 )
(command "insert" "ped" '(7 -2) 1 1 0 )
(command "insert" "ped" '(1 -2) 1 1 0 )
(command "insert" "ped" '(2 -19) 1 1 0 )
(command "insert" "ped" '(2 -9) 1 1 0 )
(command "insert" "ped" '(8 -1) 1 1 0 )
(command "insert" "ped" '(1 -16) 1 1 0 )
(command "insert" "ped" '(1 -14) 1 1 0 )
(command "insert" "ped" '(1 -5) 1 1 0 )
(command "insert" "ped" '(2 -13) 1 1 0 )
(command "insert" "ped" '(1 -20) 1 1 0 )
(command "insert" "ped" '(2 -2) 1 1 0 )
(command "insert" "ped" '(1 -10) 1 1 0 )
(command "insert" "ped" '(4 -1) 1 1 0 )
(command "insert" "ped" '(1 -1) 1 1 0 )
(command "insert" "ped" '(2 -16) 1 1 0 )
(command "insert" "ped" '(3 -2) 1 1 0 )
(command "insert" "ped" '(2 -6) 1 1 0 )
(command "insert" "ped" '(8 -2) 1 1 0 )
(command "insert" "ped" '(7 -1) 1 1 0 )
(command "insert" "ped" '(1 -13) 1 1 0 )
(command "insert" "ped" '(2 -20) 1 1 0 )
(command "insert" "ped" '(1 -4) 1 1 0 )
(command "insert" "ped" '(2 -10) 1 1 0 )
(command "insert" "ped" '(1 -19) 1 1 0 )
(command "insert" "ped" '(2 -3) 1 1 0 )
(command "insert" "ped" '(1 -9) 1 1 0 )
(command "insert" "ped" '(4 -2) 1 1 0 )
(command "insert" "ped" '(2 -14) 1 1 0 )
(command "insert" "ped" '(2 -17) 1 1 0 )
(command "insert" "ped" '(2 -7) 1 1 0 )
(command "insert" "ped" '(1 -12) 1 1 0 )
(command "insert" "ped" '(6 -1) 1 1 0 )
(command "insert" "ped" '(3 -1) 1 1 0 )
(command "insert" "ped" '(2 -11) 1 1 0 )
(command "insert" "ped" '(1 -18) 1 1 0 )
(command "insert" "ped" '(1 -8) 1 1 0 )
(command "insert" "ped" '(1 -7) 1 1 0 )
(command "insert" "ped" '(2 -15) 1 1 0 )
(command "insert" "ped" '(5 -2) 1 1 0 )
(command "insert" "ped" '(2 -4) 1 1 0 )
(command "layer" "m" "ped" "" )
(command "insert" "ped" '(1 -3) 1 1 0 )
(command "insert" "ped" '(2 -18) 1 1 0 )
(command "insert" "ped" '(2 -8) 1 1 0 )
(command "insert" "ped" '(1 -17) 1 1 0 )
(command "insert" "ped" '(2 -1) 1 1 0 )
(command "insert" "ped" '(1 -15) 1 1 0 )
(command "insert" "ped" '(6 -2) 1 1 0 )
(command "insert" "ped" '(1 -6) 1 1 0 )
(command "insert" "ped" '(2 -12) 1 1 0 )
(command "insert" "ped" '(5 -1) 1 1 0 )
(command "insert" "ped" '(2 -5) 1 1 0 )
(command "insert" "ped" '(1 -11) 1 1 0 )
(command "insert" "ped" '(1 -20) 1 1 0 )
(command "insert" "ped" '(1 -2) 1 1 0 )
(command "insert" "ped" '(2 -19) 1 1 0 )
(command "insert" "ped" '(2 -9) 1 1 0 )
(command "insert" "ped" '(8 -1) 1 1 0 )
(command "insert" "ped" '(1 -16) 1 1 0 )
(command "insert" "ped" '(1 -14) 1 1 0 )
(command "insert" "ped" '(1 -5) 1 1 0 )
(command "insert" "ped" '(2 -13) 1 1 0 )
(command "insert" "ped" '(7 -2) 1 1 0 )
(command "insert" "ped" '(2 -2) 1 1 0 )
(command "insert" "ped" '(1 -10) 1 1 0 )
(command "insert" "ped" '(4 -1) 1 1 0 )
(command "insert" "ped" '(1 -1) 1 1 0 )
(command "insert" "ped" '(2 -16) 1 1 0 )
(command "insert" "ped" '(3 -2) 1 1 0 )
(command "insert" "ped" '(2 -6) 1 1 0 )
(command "insert" "ped" '(8 -2) 1 1 0 )
(command "insert" "ped" '(7 -1) 1 1 0 )
(command "insert" "ped" '(1 -13) 1 1 0 )
(command "insert" "ped" '(2 -20) 1 1 0 )
(command "insert" "ped" '(1 -4) 1 1 0 )
(command "insert" "ped" '(2 -10) 1 1 0 )
(command "insert" "ped" '(1 -19) 1 1 0 )
(command "insert" "ped" '(2 -3) 1 1 0 )
(command "insert" "ped" '(1 -9) 1 1 0 )
(command "insert" "ped" '(4 -2) 1 1 0 )
(command "insert" "ped" '(2 -14) 1 1 0 )
(command "insert" "ped" '(2 -17) 1 1 0 )
(command "insert" "ped" '(2 -7) 1 1 0 )
(command "insert" "ped" '(1 -12) 1 1 0 )
(command "insert" "ped" '(6 -1) 1 1 0 )
(command "insert" "ped" '(3 -1) 1 1 0 )
(command "insert" "ped" '(2 -11) 1 1 0 )
(command "insert" "ped" '(1 -18) 1 1 0 )
(command "insert" "ped" '(1 -8) 1 1 0 )
(command "insert" "ped" '(1 -7) 1 1 0 )
(command "insert" "ped" '(2 -15) 1 1 0 )
(command "insert" "ped" '(5 -2) 1 1 0 )
(command "insert" "ped" '(2 -4) 1 1 0 )
(command "layer" "m" "alley" "" )
(command "insert" "alley" '(43 -48) 1 1 0 )
(command "insert" "alley" '(43 -49) 1 1 0 )
(command "insert" "alley" '(42 -49) 1 1 0 )
(command "insert" "alley" '(42 -48) 1 1 0 )
(command "insert" "alley" '(42 -50) 1 1 0 )
(command "insert" "alley" '(44 -50) 1 1 0 )
(command "insert" "alley" '(44 -49) 1 1 0 )
(command "insert" "alley" '(44 -48) 1 1 0 )
(command "insert" "alley" '(43 -50) 1 1 0 )
(command "layer" "m" "edge" "" )
(command "insert" "edge" '(45 -1) 1 1 0 )
(command "insert" "edge" '(47 -2) 1 1 0 )
(command "insert" "edge" '(44 -2) 1 1 0 )
(command "insert" "edge" '(41 -2) 1 1 0 )
(command "insert" "edge" '(38 -1) 1 1 0 )
(command "insert" "edge" '(46 -1) 1 1 0 )
(command "insert" "edge" '(43 -1) 1 1 0 )
(command "insert" "edge" '(36 -2) 1 1 0 )
(command "insert" "edge" '(44 -1) 1 1 0 )
(command "insert" "edge" '(37 -2) 1 1 0 )
(command "insert" "edge" '(42 -2) 1 1 0 )
(command "insert" "edge" '(41 -1) 1 1 0 )
(command "insert" "edge" '(45 -2) 1 1 0 )
(command "insert" "edge" '(40 -2) 1 1 0 )
(command "insert" "edge" '(39 -1) 1 1 0 )
(command "insert" "edge" '(36 -1) 1 1 0 )
(command "insert" "edge" '(43 -2) 1 1 0 )
(command "insert" "edge" '(47 -1) 1 1 0 )
(command "insert" "edge" '(40 -1) 1 1 0 )
(command "insert" "edge" '(38 -2) 1 1 0 )
(command "insert" "edge" '(42 -1) 1 1 0 )
(command "insert" "edge" '(37 -1) 1 1 0 )
(command "insert" "edge" '(46 -2) 1 1 0 )
(command "insert" "edge" '(39 -2) 1 1 0 )
(command "layer" "m" "edge" "" )
(command "insert" "edge" '(2 -39) 1 1 0 )
(command "insert" "edge" '(1 -44) 1 1 0 )
(command "insert" "edge" '(1 -46) 1 1 0 )
(command "insert" "edge" '(2 -43) 1 1 0 )
(command "insert" "edge" '(1 -42) 1 1 0 )
(command "insert" "edge" '(1 -40) 1 1 0 )
(command "insert" "edge" '(1 -39) 1 1 0 )
(command "insert" "edge" '(2 -47) 1 1 0 )
(command "insert" "edge" '(2 -42) 1 1 0 )
(command "insert" "edge" '(1 -43) 1 1 0 )
(command "insert" "edge" '(2 -41) 1 1 0 )
(command "insert" "edge" '(2 -40) 1 1 0 )
(command "insert" "edge" '(2 -45) 1 1 0 )
(command "insert" "edge" '(1 -47) 1 1 0 )
(command "insert" "edge" '(1 -41) 1 1 0 )
(command "insert" "edge" '(1 -45) 1 1 0 )
(command "insert" "edge" '(2 -46) 1 1 0 )
(command "insert" "edge" '(2 -44) 1 1 0 )
(command "layer" "m" "Commmer" "" )
(command "insert" "Commmer" '(32 -1) 1 1 0 )
(command "insert" "Commmer" '(23 -1) 1 1 0 )
(command "insert" "Commmer" '(21 -2) 1 1 0 )
(command "insert" "Commmer" '(16 -2) 1 1 0 )
(command "insert" "Commmer" '(15 -1) 1 1 0 )
(command "insert" "Commmer" '(28 -1) 1 1 0 )
(command "insert" "Commmer" '(25 -1) 1 1 0 )
(command "insert" "Commmer" '(27 -2) 1 1 0 )
(command "insert" "Commmer" '(32 -2) 1 1 0 )
(command "insert" "Commmer" '(18 -1) 1 1 0 )
(command "insert" "Commmer" '(31 -1) 1 1 0 )
(command "insert" "Commmer" '(22 -2) 1 1 0 )
(command "insert" "Commmer" '(21 -1) 1 1 0 )
(command "insert" "Commmer" '(23 -2) 1 1 0 )
(command "insert" "Commmer" '(17 -2) 1 1 0 )
(command "insert" "Commmer" '(28 -2) 1 1 0 )
(command "insert" "Commmer" '(34 -1) 1 1 0 )
(command "insert" "Commmer" '(24 -1) 1 1 0 )
(command "insert" "Commmer" '(33 -2) 1 1 0 )
(command "insert" "Commmer" '(30 -1) 1 1 0 )
(command "insert" "Commmer" '(27 -1) 1 1 0 )
(command "insert" "Commmer" '(18 -2) 1 1 0 )
(command "insert" "Commmer" '(20 -1) 1 1 0 )
(command "insert" "Commmer" '(17 -1) 1 1 0 )
(command "insert" "Commmer" '(19 -2) 1 1 0 )
(command "insert" "Commmer" '(29 -2) 1 1 0 )
(command "insert" "Commmer" '(24 -2) 1 1 0 )
(command "insert" "Commmer" '(34 -2) 1 1 0 )
(command "insert" "Commmer" '(35 -1) 1 1 0 )
(command "insert" "Commmer" '(26 -2) 1 1 0 )
(command "insert" "Commmer" '(33 -1) 1 1 0 )
(command "insert" "Commmer" '(35 -2) 1 1 0 )
(command "insert" "Commmer" '(26 -1) 1 1 0 )
(command "insert" "Commmer" '(15 -2) 1 1 0 )
(command "insert" "Commmer" '(20 -2) 1 1 0 )
(command "insert" "Commmer" '(30 -2) 1 1 0 )
(command "insert" "Commmer" '(16 -1) 1 1 0 )
(command "insert" "Commmer" '(29 -1) 1 1 0 )
(command "insert" "Commmer" '(31 -2) 1 1 0 )
(command "insert" "Commmer" '(25 -2) 1 1 0 )
(command "insert" "Commmer" '(22 -1) 1 1 0 )
(command "insert" "Commmer" '(19 -1) 1 1 0 )
(command "layer" "m" "Res" "" )
(command "insert" "Res" '(48 -1) 1 1 0 )
(command "insert" "Res" '(49 -2) 1 1 0 )
(command "insert" "Res" '(50 -2) 1 1 0 )
(command "insert" "Res" '(48 -2) 1 1 0 )
(command "insert" "Res" '(50 -1) 1 1 0 )
(command "insert" "Res" '(49 -1) 1 1 0 )
(command "layer" "m" "mroads" "" )
(command "insert" "mroads" '(5 -31) 1 1 0 )
(command "insert" "mroads" '(66 -31) 1 1 0 )
(command "insert" "mroads" '(6 -28) 1 1 0 )
(command "insert" "mroads" '(67 -30) 1 1 0 )
(command "insert" "mroads" '(7 -25) 1 1 0 )
(command "insert" "mroads" '(22 -19) 1 1 0 )
(command "insert" "mroads" '(18 -19) 1 1 0 )
(command "insert" "mroads" '(38 -21) 1 1 0 )
(command "insert" "mroads" '(114 -31) 1 1 0 )
(command "insert" "mroads" '(13 -32) 1 1 0 )
(command "insert" "mroads" '(35 -15) 1 1 0 )
(command "insert" "mroads" '(14 -31) 1 1 0 )
(command "insert" "mroads" '(15 -30) 1 1 0 )
(command "insert" "mroads" '(35 -21) 1 1 0 )
(command "insert" "mroads" '(12 -17) 1 1 0 )
(command "insert" "mroads" '(36 -22) 1 1 0 )
(command "insert" "mroads" '(1 -28) 1 1 0 )
(command "insert" "mroads" '(25 -15) 1 1 0 )
(command "insert" "mroads" '(39 -16) 1 1 0 )
(command "insert" "mroads" '(63 -30) 1 1 0 )
(command "insert" "mroads" '(37 -23) 1 1 0 )
(command "insert" "mroads" '(2 -27) 1 1 0 )
(command "insert" "mroads" '(109 -32) 1 1 0 )
(command "insert" "mroads" '(29 -17) 1 1 0 )
(command "insert" "mroads" '(31 -15) 1 1 0 )
(command "insert" "mroads" '(5 -24) 1 1 0 )
(command "insert" "mroads" '(20 -32) 1 1 0 )
(command "insert" "mroads" '(6 -23) 1 1 0 )
(command "insert" "mroads" '(30 -16) 1 1 0 )
(command "insert" "mroads" '(28 -32) 1 1 0 )
(command "insert" "mroads" '(7 -22) 1 1 0 )
(command "insert" "mroads" '(41 -23) 1 1 0 )
(command "insert" "mroads" '(42 -31) 1 1 0 )
(command "insert" "mroads" '(23 -19) 1 1 0 )
(command "insert" "mroads" '(21 -15) 1 1 0 )
(command "insert" "mroads" '(43 -30) 1 1 0 )
(command "insert" "mroads" '(116 -32) 1 1 0 )
(command "insert" "mroads" '(8 -18) 1 1 0 )
(command "insert" "mroads" '(11 -15) 1 1 0 )
(command "insert" "mroads" '(35 -26) 1 1 0 )
(command "insert" "mroads" '(9 -19) 1 1 0 )
(command "insert" "mroads" '(36 -29) 1 1 0 )
(command "insert" "mroads" '(1 -21) 1 1 0 )
(command "insert" "mroads" '(25 -16) 1 1 0 )
(command "insert" "mroads" '(29 -20) 1 1 0 )
(command "insert" "mroads" '(37 -16) 1 1 0 )
(command "insert" "mroads" '(98 -30) 1 1 0 )
(command "insert" "mroads" '(38 -31) 1 1 0 )
(command "insert" "mroads" '(99 -31) 1 1 0 )
(command "insert" "mroads" '(39 -30) 1 1 0 )
(command "insert" "mroads" '(3 -17) 1 1 0 )
(command "insert" "mroads" '(19 -18) 1 1 0 )
(command "insert" "mroads" '(7 -15) 1 1 0 )
(command "insert" "mroads" '(31 -18) 1 1 0 )
(command "insert" "mroads" '(46 -30) 1 1 0 )
(command "insert" "mroads" '(6 -32) 1 1 0 )
(command "insert" "mroads" '(34 -32) 1 1 0 )
(command "insert" "mroads" '(32 -16) 1 1 0 )
(command "insert" "mroads" '(94 -30) 1 1 0 )
(command "insert" "mroads" '(18 -31) 1 1 0 )
(command "insert" "mroads" '(42 -32) 1 1 0 )
(command "insert" "mroads" '(86 -32) 1 1 0 )
(command "insert" "mroads" '(34 -26) 1 1 0 )
(command "insert" "mroads" '(8 -25) 1 1 0 )
(command "insert" "mroads" '(94 -32) 1 1 0 )
(command "insert" "mroads" '(9 -20) 1 1 0 )
(command "insert" "mroads" '(10 -19) 1 1 0 )
(command "insert" "mroads" '(37 -25) 1 1 0 )
(command "insert" "mroads" '(26 -30) 1 1 0 )
(command "insert" "mroads" '(7 -18) 1 1 0 )
(command "insert" "mroads" '(38 -22) 1 1 0 )
(command "insert" "mroads" '(27 -31) 1 1 0 )
(command "insert" "mroads" '(40 -20) 1 1 0 )
(command "insert" "mroads" '(39 -23) 1 1 0 )
(command "insert" "mroads" '(88 -31) 1 1 0 )
(command "insert" "mroads" '(74 -30) 1 1 0 )
(command "insert" "mroads" '(89 -30) 1 1 0 )
(command "insert" "mroads" '(3 -22) 1 1 0 )
(command "insert" "mroads" '(75 -31) 1 1 0 )
(command "insert" "mroads" '(4 -17) 1 1 0 )
(command "insert" "mroads" '(5 -20) 1 1 0 )
(command "insert" "mroads" '(6 -27) 1 1 0 )
(command "insert" "mroads" '(21 -17) 1 1 0 )
(command "insert" "mroads" '(17 -17) 1 1 0 )
(command "insert" "mroads" '(22 -30) 1 1 0 )
(command "insert" "mroads" '(33 -22) 1 1 0 )
(command "insert" "mroads" '(23 -31) 1 1 0 )
(command "insert" "mroads" '(12 -32) 1 1 0 )
(command "insert" "mroads" '(34 -21) 1 1 0 )
(command "insert" "mroads" '(70 -30) 1 1 0 )
(command "insert" "mroads" '(85 -30) 1 1 0 )
(command "insert" "mroads" '(48 -32) 1 1 0 )
(command "insert" "mroads" '(71 -31) 1 1 0 )
(command "insert" "mroads" '(34 -15) 1 1 0 )
(command "insert" "mroads" '(11 -19) 1 1 0 )
(command "insert" "mroads" '(100 -32) 1 1 0 )
(command "insert" "mroads" '(27 -20) 1 1 0 )
(command "insert" "mroads" '(1 -25) 1 1 0 )
(command "insert" "mroads" '(108 -32) 1 1 0 )
(command "insert" "mroads" '(2 -30) 1 1 0 )
(command "insert" "mroads" '(3 -31) 1 1 0 )
(command "insert" "mroads" '(64 -31) 1 1 0 )
(command "insert" "mroads" '(4 -24) 1 1 0 )
(command "insert" "mroads" '(19 -32) 1 1 0 )
(command "insert" "mroads" '(62 -31) 1 1 0 )
(command "insert" "mroads" '(50 -30) 1 1 0 )
(command "insert" "mroads" '(65 -30) 1 1 0 )
(command "insert" "mroads" '(5 -29) 1 1 0 )
(command "insert" "mroads" '(27 -32) 1 1 0 )
(command "insert" "mroads" '(6 -18) 1 1 0 )
(command "insert" "mroads" '(101 -32) 1 1 0 )
(command "insert" "mroads" '(112 -31) 1 1 0 )
(command "insert" "mroads" '(41 -21) 1 1 0 )
(command "insert" "mroads" '(22 -17) 1 1 0 )
(command "insert" "mroads" '(79 -32) 1 1 0 )
(command "insert" "mroads" '(18 -17) 1 1 0 )
(command "insert" "mroads" '(23 -20) 1 1 0 )
(command "insert" "mroads" '(40 -31) 1 1 0 )
(command "insert" "mroads" '(115 -32) 1 1 0 )
(command "insert" "mroads" '(60 -31) 1 1 0 )
(command "insert" "mroads" '(61 -30) 1 1 0 )
(command "insert" "mroads" '(35 -23) 1 1 0 )
(command "insert" "mroads" '(24 -16) 1 1 0 )
(command "insert" "mroads" '(36 -16) 1 1 0 )
(command "insert" "mroads" '(108 -31) 1 1 0 )
(command "insert" "mroads" '(37 -21) 1 1 0 )
(command "insert" "mroads" '(2 -25) 1 1 0 )
(command "insert" "mroads" '(109 -30) 1 1 0 )
(command "insert" "mroads" '(7 -16) 1 1 0 )
(command "insert" "mroads" '(38 -26) 1 1 0 )
(command "insert" "mroads" '(40 -18) 1 1 0 )
(command "insert" "mroads" '(114 -32) 1 1 0 )
(command "insert" "mroads" '(116 -30) 1 1 0 )
(command "insert" "mroads" '(6 -21) 1 1 0 )
(command "insert" "mroads" '(111 -31) 1 1 0 )
(command "insert" "mroads" '(19 -15) 1 1 0 )
(command "insert" "mroads" '(41 -30) 1 1 0 )
(command "insert" "mroads" '(5 -32) 1 1 0 )
(command "insert" "mroads" '(33 -32) 1 1 0 )
(command "insert" "mroads" '(41 -32) 1 1 0 )
(command "insert" "mroads" '(7 -29) 1 1 0 )
(command "insert" "mroads" '(85 -32) 1 1 0 )
(command "insert" "mroads" '(9 -15) 1 1 0 )
(command "insert" "mroads" '(33 -26) 1 1 0 )
(command "insert" "mroads" '(22 -31) 1 1 0 )
(command "insert" "mroads" '(93 -32) 1 1 0 )
(command "insert" "mroads" '(8 -20) 1 1 0 )
(command "insert" "mroads" '(37 -15) 1 1 0 )
(command "insert" "mroads" '(35 -28) 1 1 0 )
(command "insert" "mroads" '(9 -17) 1 1 0 )
(command "insert" "mroads" '(96 -30) 1 1 0 )
(command "insert" "mroads" '(36 -31) 1 1 0 )
(command "insert" "mroads" '(15 -15) 1 1 0 )
(command "insert" "mroads" '(97 -31) 1 1 0 )
(command "insert" "mroads" '(37 -30) 1 1 0 )
(command "insert" "mroads" '(38 -29) 1 1 0 )
(command "insert" "mroads" '(83 -31) 1 1 0 )
(command "insert" "mroads" '(39 -24) 1 1 0 )
(command "insert" "mroads" '(5 -15) 1 1 0 )
(command "insert" "mroads" '(3 -19) 1 1 0 )
(command "insert" "mroads" '(4 -20) 1 1 0 )
(command "insert" "mroads" '(19 -20) 1 1 0 )
(command "insert" "mroads" '(92 -30) 1 1 0 )
(command "insert" "mroads" '(16 -31) 1 1 0 )
(command "insert" "mroads" '(93 -31) 1 1 0 )
(command "insert" "mroads" '(17 -30) 1 1 0 )
(command "insert" "mroads" '(32 -18) 1 1 0 )
(command "insert" "mroads" '(11 -32) 1 1 0 )
(command "insert" "mroads" '(33 -19) 1 1 0 )
(command "insert" "mroads" '(40 -29) 1 1 0 )
(command "insert" "mroads" '(8 -27) 1 1 0 )
(command "insert" "mroads" '(63 -32) 1 1 0 )
(command "insert" "mroads" '(5 -21) 1 1 0 )
(command "insert" "mroads" '(24 -30) 1 1 0 )
(command "insert" "mroads" '(14 -17) 1 1 0 )
(command "insert" "mroads" '(71 -32) 1 1 0 )
(command "insert" "mroads" '(10 -17) 1 1 0 )
(command "insert" "mroads" '(25 -31) 1 1 0 )
(command "insert" "mroads" '(99 -32) 1 1 0 )
(command "insert" "mroads" '(111 -32) 1 1 0 )
(command "insert" "mroads" '(107 -32) 1 1 0 )
(command "insert" "mroads" '(38 -20) 1 1 0 )
(command "insert" "mroads" '(12 -31) 1 1 0 )
(command "insert" "mroads" '(27 -17) 1 1 0 )
(command "insert" "mroads" '(39 -17) 1 1 0 )
(command "insert" "mroads" '(13 -30) 1 1 0 )
(command "insert" "mroads" '(41 -24) 1 1 0 )
(command "insert" "mroads" '(3 -24) 1 1 0 )
(command "insert" "mroads" '(56 -32) 1 1 0 )
(command "insert" "mroads" '(4 -19) 1 1 0 )
(command "insert" "mroads" '(26 -32) 1 1 0 )
(command "insert" "mroads" '(5 -18) 1 1 0 )
(command "insert" "mroads" '(20 -30) 1 1 0 )
(command "insert" "mroads" '(6 -25) 1 1 0 )
(command "insert" "mroads" '(21 -31) 1 1 0 )
(command "insert" "mroads" '(40 -22) 1 1 0 )
(command "insert" "mroads" '(78 -32) 1 1 0 )
(command "insert" "mroads" '(41 -18) 1 1 0 )
(command "insert" "mroads" '(18 -20) 1 1 0 )
(command "insert" "mroads" '(33 -20) 1 1 0 )
(command "insert" "mroads" '(69 -31) 1 1 0 )
(command "insert" "mroads" '(34 -19) 1 1 0 )
(command "insert" "mroads" '(32 -15) 1 1 0 )
(command "insert" "mroads" '(15 -32) 1 1 0 )
(command "insert" "mroads" '(64 -32) 1 1 0 )
(command "insert" "mroads" '(35 -16) 1 1 0 )
(command "insert" "mroads" '(38 -15) 1 1 0 )
(command "insert" "mroads" '(77 -32) 1 1 0 )
(command "insert" "mroads" '(1 -31) 1 1 0 )
(command "insert" "mroads" '(28 -17) 1 1 0 )
(command "insert" "mroads" '(2 -28) 1 1 0 )
(command "insert" "mroads" '(48 -30) 1 1 0 )
(command "insert" "mroads" '(113 -32) 1 1 0 )
(command "insert" "mroads" '(49 -31) 1 1 0 )
(command "insert" "mroads" '(4 -26) 1 1 0 )
(command "insert" "mroads" '(28 -15) 1 1 0 )
(command "insert" "mroads" '(5 -27) 1 1 0 )
(command "insert" "mroads" '(40 -26) 1 1 0 )
(command "insert" "mroads" '(4 -32) 1 1 0 )
(command "insert" "mroads" '(7 -21) 1 1 0 )
(command "insert" "mroads" '(18 -15) 1 1 0 )
(command "insert" "mroads" '(40 -32) 1 1 0 )
(command "insert" "mroads" '(34 -20) 1 1 0 )
(command "insert" "mroads" '(58 -31) 1 1 0 )
(command "insert" "mroads" '(44 -30) 1 1 0 )
(command "insert" "mroads" '(59 -30) 1 1 0 )
(command "insert" "mroads" '(92 -32) 1 1 0 )
(command "insert" "mroads" '(45 -31) 1 1 0 )
(command "insert" "mroads" '(6 -17) 1 1 0 )
(command "insert" "mroads" '(106 -31) 1 1 0 )
(command "insert" "mroads" '(35 -25) 1 1 0 )
(command "insert" "mroads" '(24 -18) 1 1 0 )
(command "insert" "mroads" '(107 -30) 1 1 0 )
(command "insert" "mroads" '(36 -18) 1 1 0 )
(command "insert" "mroads" '(25 -19) 1 1 0 )
(command "insert" "mroads" '(13 -16) 1 1 0 )
(command "insert" "mroads" '(37 -19) 1 1 0 )
(command "insert" "mroads" '(2 -23) 1 1 0 )
(command "insert" "mroads" '(38 -24) 1 1 0 )
(command "insert" "mroads" '(39 -29) 1 1 0 )
(command "insert" "mroads" '(54 -31) 1 1 0 )
(command "insert" "mroads" '(115 -31) 1 1 0 )
(command "insert" "mroads" '(55 -30) 1 1 0 )
(command "insert" "mroads" '(22 -20) 1 1 0 )
(command "insert" "mroads" '(30 -20) 1 1 0 )
(command "insert" "mroads" '(19 -17) 1 1 0 )
(command "insert" "mroads" '(102 -31) 1 1 0 )
(command "insert" "mroads" '(41 -28) 1 1 0 )
(command "insert" "mroads" '(31 -17) 1 1 0 )
(command "insert" "mroads" '(103 -30) 1 1 0 )
(command "insert" "mroads" '(10 -32) 1 1 0 )
(command "insert" "mroads" '(22 -32) 1 1 0 )
(command "insert" "mroads" '(18 -32) 1 1 0 )
(command "insert" "mroads" '(33 -24) 1 1 0 )
(command "insert" "mroads" '(62 -32) 1 1 0 )
(command "insert" "mroads" '(110 -30) 1 1 0 )
(command "insert" "mroads" '(34 -31) 1 1 0 )
(command "insert" "mroads" '(8 -22) 1 1 0 )
(command "insert" "mroads" '(23 -17) 1 1 0 )
(command "insert" "mroads" '(70 -32) 1 1 0 )
(command "insert" "mroads" '(35 -30) 1 1 0 )
(command "insert" "mroads" '(98 -32) 1 1 0 )
(command "insert" "mroads" '(36 -25) 1 1 0 )
(command "insert" "mroads" '(10 -20) 1 1 0 )
(command "insert" "mroads" '(25 -20) 1 1 0 )
(command "insert" "mroads" '(82 -31) 1 1 0 )
(command "insert" "mroads" '(106 -32) 1 1 0 )
(command "insert" "mroads" '(37 -28) 1 1 0 )
(command "insert" "mroads" '(26 -19) 1 1 0 )
(command "insert" "mroads" '(38 -19) 1 1 0 )
(command "insert" "mroads" '(3 -15) 1 1 0 )
(command "insert" "mroads" '(39 -26) 1 1 0 )
(command "insert" "mroads" '(51 -31) 1 1 0 )
(command "insert" "mroads" '(3 -21) 1 1 0 )
(command "insert" "mroads" '(25 -32) 1 1 0 )
(command "insert" "mroads" '(90 -30) 1 1 0 )
(command "insert" "mroads" '(30 -31) 1 1 0 )
(command "insert" "mroads" '(4 -22) 1 1 0 )
(command "insert" "mroads" '(91 -31) 1 1 0 )
(command "insert" "mroads" '(31 -30) 1 1 0 )
(command "insert" "mroads" '(5 -23) 1 1 0 )
(command "insert" "mroads" '(20 -17) 1 1 0 )
(command "insert" "mroads" '(16 -17) 1 1 0 )
(command "insert" "mroads" '(21 -20) 1 1 0 )
(command "insert" "mroads" '(32 -20) 1 1 0 )
(command "insert" "mroads" '(33 -17) 1 1 0 )
(command "insert" "mroads" '(34 -22) 1 1 0 )
(command "insert" "mroads" '(8 -29) 1 1 0 )
(command "insert" "mroads" '(61 -31) 1 1 0 )
(command "insert" "mroads" '(86 -30) 1 1 0 )
(command "insert" "mroads" '(10 -31) 1 1 0 )
(command "insert" "mroads" '(6 -19) 1 1 0 )
(command "insert" "mroads" '(87 -31) 1 1 0 )
(command "insert" "mroads" '(11 -30) 1 1 0 )
(command "insert" "mroads" '(76 -32) 1 1 0 )
(command "insert" "mroads" '(27 -19) 1 1 0 )
(command "insert" "mroads" '(39 -19) 1 1 0 )
(command "insert" "mroads" '(28 -20) 1 1 0 )
(command "insert" "mroads" '(3 -26) 1 1 0 )
(command "insert" "mroads" '(40 -15) 1 1 0 )
(command "insert" "mroads" '(4 -29) 1 1 0 )
(command "insert" "mroads" '(19 -31) 1 1 0 )
(command "insert" "mroads" '(7 -26) 1 1 0 )
(command "insert" "mroads" '(5 -16) 1 1 0 )
(command "insert" "mroads" '(3 -32) 1 1 0 )
(command "insert" "mroads" '(66 -30) 1 1 0 )
(command "insert" "mroads" '(6 -31) 1 1 0 )
(command "insert" "mroads" '(67 -31) 1 1 0 )
(command "insert" "mroads" '(7 -30) 1 1 0 )
(command "insert" "mroads" '(22 -18) 1 1 0 )
(command "insert" "mroads" '(55 -32) 1 1 0 )
(command "insert" "mroads" '(18 -18) 1 1 0 )
(command "insert" "mroads" '(83 -32) 1 1 0 )
(command "insert" "mroads" '(114 -30) 1 1 0 )
(command "insert" "mroads" '(34 -17) 1 1 0 )
(command "insert" "mroads" '(91 -32) 1 1 0 )
(command "insert" "mroads" '(14 -30) 1 1 0 )
(command "insert" "mroads" '(36 -15) 1 1 0 )
(command "insert" "mroads" '(15 -31) 1 1 0 )
(command "insert" "mroads" '(35 -18) 1 1 0 )
(command "insert" "mroads" '(12 -16) 1 1 0 )
(command "insert" "mroads" '(36 -21) 1 1 0 )
(command "insert" "mroads" '(1 -29) 1 1 0 )
(command "insert" "mroads" '(63 -31) 1 1 0 )
(command "insert" "mroads" '(28 -19) 1 1 0 )
(command "insert" "mroads" '(2 -26) 1 1 0 )
(command "insert" "mroads" '(26 -15) 1 1 0 )
(command "insert" "mroads" '(12 -15) 1 1 0 )
(command "insert" "mroads" '(29 -18) 1 1 0 )
(command "insert" "mroads" '(5 -25) 1 1 0 )
(command "insert" "mroads" '(16 -15) 1 1 0 )
(command "insert" "mroads" '(6 -22) 1 1 0 )
(command "insert" "mroads" '(30 -19) 1 1 0 )
(command "insert" "mroads" '(41 -25) 1 1 0 )
(command "insert" "mroads" '(56 -31) 1 1 0 )
(command "insert" "mroads" '(9 -32) 1 1 0 )
(command "insert" "mroads" '(42 -30) 1 1 0 )
(command "insert" "mroads" '(23 -16) 1 1 0 )
(command "insert" "mroads" '(43 -31) 1 1 0 )
(command "insert" "mroads" '(17 -32) 1 1 0 )
(command "insert" "mroads" '(22 -15) 1 1 0 )
(command "insert" "mroads" '(61 -32) 1 1 0 )
(command "insert" "mroads" '(52 -30) 1 1 0 )
(command "insert" "mroads" '(105 -30) 1 1 0 )
(command "insert" "mroads" '(69 -32) 1 1 0 )
(command "insert" "mroads" '(34 -24) 1 1 0 )
(command "insert" "mroads" '(8 -17) 1 1 0 )
(command "insert" "mroads" '(97 -32) 1 1 0 )
(command "insert" "mroads" '(35 -27) 1 1 0 )
(command "insert" "mroads" '(24 -20) 1 1 0 )
(command "insert" "mroads" '(105 -32) 1 1 0 )
(command "insert" "mroads" '(36 -28) 1 1 0 )
(command "insert" "mroads" '(1 -22) 1 1 0 )
(command "insert" "mroads" '(6 -29) 1 1 0 )
(command "insert" "mroads" '(37 -17) 1 1 0 )
(command "insert" "mroads" '(2 -21) 1 1 0 )
(command "insert" "mroads" '(38 -30) 1 1 0 )
(command "insert" "mroads" '(53 -30) 1 1 0 )
(command "insert" "mroads" '(112 -32) 1 1 0 )
(command "insert" "mroads" '(39 -31) 1 1 0 )
(command "insert" "mroads" '(100 -31) 1 1 0 )
(command "insert" "mroads" '(24 -32) 1 1 0 )
(command "insert" "mroads" '(101 -30) 1 1 0 )
(command "insert" "mroads" '(19 -19) 1 1 0 )
(command "insert" "mroads" '(31 -19) 1 1 0 )
(command "insert" "mroads" '(20 -20) 1 1 0 )
(command "insert" "mroads" '(47 -31) 1 1 0 )
(command "insert" "mroads" '(32 -31) 1 1 0 )
(command "insert" "mroads" '(18 -30) 1 1 0 )
(command "insert" "mroads" '(33 -30) 1 1 0 )
(command "insert" "mroads" '(34 -29) 1 1 0 )
(command "insert" "mroads" '(8 -24) 1 1 0 )
(command "insert" "mroads" '(39 -32) 1 1 0 )
(command "insert" "mroads" '(80 -31) 1 1 0 )
(command "insert" "mroads" '(81 -30) 1 1 0 )
(command "insert" "mroads" '(36 -27) 1 1 0 )
(command "insert" "mroads" '(10 -18) 1 1 0 )
(command "insert" "mroads" '(75 -32) 1 1 0 )
(command "insert" "mroads" '(37 -26) 1 1 0 )
(command "insert" "mroads" '(26 -17) 1 1 0 )
(command "insert" "mroads" '(38 -17) 1 1 0 )
(command "insert" "mroads" '(39 -20) 1 1 0 )
(command "insert" "mroads" '(88 -30) 1 1 0 )
(command "insert" "mroads" '(28 -31) 1 1 0 )
(command "insert" "mroads" '(89 -31) 1 1 0 )
(command "insert" "mroads" '(29 -30) 1 1 0 )
(command "insert" "mroads" '(3 -23) 1 1 0 )
(command "insert" "mroads" '(4 -16) 1 1 0 )
(command "insert" "mroads" '(2 -32) 1 1 0 )
(command "insert" "mroads" '(76 -31) 1 1 0 )
(command "insert" "mroads" '(46 -32) 1 1 0 )
(command "insert" "mroads" '(20 -19) 1 1 0 )
(command "insert" "mroads" '(33 -29) 1 1 0 )
(command "insert" "mroads" '(77 -30) 1 1 0 )
(command "insert" "mroads" '(6 -26) 1 1 0 )
(command "insert" "mroads" '(21 -18) 1 1 0 )
(command "insert" "mroads" '(54 -32) 1 1 0 )
(command "insert" "mroads" '(33 -23) 1 1 0 )
(command "insert" "mroads" '(90 -32) 1 1 0 )
(command "insert" "mroads" '(84 -30) 1 1 0 )
(command "insert" "mroads" '(8 -31) 1 1 0 )
(command "insert" "mroads" '(95 -31) 1 1 0 )
(command "insert" "mroads" '(85 -31) 1 1 0 )
(command "insert" "mroads" '(9 -30) 1 1 0 )
(command "insert" "mroads" '(15 -16) 1 1 0 )
(command "insert" "mroads" '(11 -16) 1 1 0 )
(command "insert" "mroads" '(1 -26) 1 1 0 )
(command "insert" "mroads" '(40 -21) 1 1 0 )
(command "insert" "mroads" '(73 -31) 1 1 0 )
(command "insert" "mroads" '(3 -28) 1 1 0 )
(command "insert" "mroads" '(64 -30) 1 1 0 )
(command "insert" "mroads" '(4 -31) 1 1 0 )
(command "insert" "mroads" '(65 -31) 1 1 0 )
(command "insert" "mroads" '(5 -30) 1 1 0 )
(command "insert" "mroads" '(40 -23) 1 1 0 )
(command "insert" "mroads" '(112 -30) 1 1 0 )
(command "insert" "mroads" '(8 -32) 1 1 0 )
(command "insert" "mroads" '(41 -22) 1 1 0 )
(command "insert" "mroads" '(22 -16) 1 1 0 )
(command "insert" "mroads" '(113 -31) 1 1 0 )
(command "insert" "mroads" '(18 -16) 1 1 0 )
(command "insert" "mroads" '(16 -32) 1 1 0 )
(command "insert" "mroads" '(60 -32) 1 1 0 )
(command "insert" "mroads" '(68 -32) 1 1 0 )
(command "insert" "mroads" '(96 -32) 1 1 0 )
(command "insert" "mroads" '(60 -30) 1 1 0 )
(command "insert" "mroads" '(104 -32) 1 1 0 )
(command "insert" "mroads" '(35 -20) 1 1 0 )
(command "insert" "mroads" '(24 -15) 1 1 0 )
(command "insert" "mroads" '(36 -23) 1 1 0 )
(command "insert" "mroads" '(108 -30) 1 1 0 )
(command "insert" "mroads" '(37 -22) 1 1 0 )
(command "insert" "mroads" '(2 -24) 1 1 0 )
(command "insert" "mroads" '(109 -31) 1 1 0 )
(command "insert" "mroads" '(29 -16) 1 1 0 )
(command "insert" "mroads" '(30 -15) 1 1 0 )
(command "insert" "mroads" '(25 -18) 1 1 0 )
(command "insert" "mroads" '(40 -30) 1 1 0 )
(command "insert" "mroads" '(30 -17) 1 1 0 )
(command "insert" "mroads" '(7 -17) 1 1 0 )
(command "insert" "mroads" '(31 -20) 1 1 0 )
(command "insert" "mroads" '(20 -15) 1 1 0 )
(command "insert" "mroads" '(33 -31) 1 1 0 )
(command "insert" "mroads" '(23 -18) 1 1 0 )
(command "insert" "mroads" '(47 -32) 1 1 0 )
(command "insert" "mroads" '(33 -27) 1 1 0 )
(command "insert" "mroads" '(38 -32) 1 1 0 )
(command "insert" "mroads" '(10 -15) 1 1 0 )
(command "insert" "mroads" '(8 -19) 1 1 0 )
(command "insert" "mroads" '(35 -29) 1 1 0 )
(command "insert" "mroads" '(9 -18) 1 1 0 )
(command "insert" "mroads" '(74 -32) 1 1 0 )
(command "insert" "mroads" '(52 -32) 1 1 0 )
(command "insert" "mroads" '(36 -30) 1 1 0 )
(command "insert" "mroads" '(51 -30) 1 1 0 )
(command "insert" "mroads" '(41 -27) 1 1 0 )
(command "insert" "mroads" '(82 -32) 1 1 0 )
(command "insert" "mroads" '(37 -31) 1 1 0 )
(command "insert" "mroads" '(26 -20) 1 1 0 )
(command "insert" "mroads" '(7 -19) 1 1 0 )
(command "insert" "mroads" '(98 -31) 1 1 0 )
(command "insert" "mroads" '(38 -28) 1 1 0 )
(command "insert" "mroads" '(40 -19) 1 1 0 )
(command "insert" "mroads" '(99 -30) 1 1 0 )
(command "insert" "mroads" '(39 -25) 1 1 0 )
(command "insert" "mroads" '(3 -16) 1 1 0 )
(command "insert" "mroads" '(1 -32) 1 1 0 )
(command "insert" "mroads" '(6 -15) 1 1 0 )
(command "insert" "mroads" '(46 -31) 1 1 0 )
(command "insert" "mroads" '(53 -32) 1 1 0 )
(command "insert" "mroads" '(16 -30) 1 1 0 )
(command "insert" "mroads" '(47 -30) 1 1 0 )
(command "insert" "mroads" '(17 -31) 1 1 0 )
(command "insert" "mroads" '(32 -17) 1 1 0 )
(command "insert" "mroads" '(7 -28) 1 1 0 )
(command "insert" "mroads" '(89 -32) 1 1 0 )
(command "insert" "mroads" '(7 -24) 1 1 0 )
(command "insert" "mroads" '(94 -31) 1 1 0 )
(command "insert" "mroads" '(33 -28) 1 1 0 )
(command "insert" "mroads" '(95 -30) 1 1 0 )
(command "insert" "mroads" '(34 -27) 1 1 0 )
(command "insert" "mroads" '(8 -26) 1 1 0 )
(command "insert" "mroads" '(14 -16) 1 1 0 )
(command "insert" "mroads" '(10 -16) 1 1 0 )
(command "insert" "mroads" '(37 -24) 1 1 0 )
(command "insert" "mroads" '(68 -30) 1 1 0 )
(command "insert" "mroads" '(26 -31) 1 1 0 )
(command "insert" "mroads" '(26 -18) 1 1 0 )
(command "insert" "mroads" '(38 -23) 1 1 0 )
(command "insert" "mroads" '(83 -30) 1 1 0 )
(command "insert" "mroads" '(27 -30) 1 1 0 )
(command "insert" "mroads" '(39 -22) 1 1 0 )
(command "insert" "mroads" '(13 -31) 1 1 0 )
(command "insert" "mroads" '(74 -31) 1 1 0 )
(command "insert" "mroads" '(3 -25) 1 1 0 )
(command "insert" "mroads" '(75 -30) 1 1 0 )
(command "insert" "mroads" '(4 -18) 1 1 0 )
(command "insert" "mroads" '(62 -30) 1 1 0 )
(command "insert" "mroads" '(5 -19) 1 1 0 )
(command "insert" "mroads" '(23 -32) 1 1 0 )
(command "insert" "mroads" '(6 -24) 1 1 0 )
(command "insert" "mroads" '(21 -16) 1 1 0 )
(command "insert" "mroads" '(17 -16) 1 1 0 )
(command "insert" "mroads" '(41 -19) 1 1 0 )
(command "insert" "mroads" '(31 -32) 1 1 0 )
(command "insert" "mroads" '(59 -32) 1 1 0 )
(command "insert" "mroads" '(33 -21) 1 1 0 )
(command "insert" "mroads" '(23 -30) 1 1 0 )
(command "insert" "mroads" '(34 -18) 1 1 0 )
(command "insert" "mroads" '(67 -32) 1 1 0 )
(command "insert" "mroads" '(6 -20) 1 1 0 )
(command "insert" "mroads" '(70 -31) 1 1 0 )
(command "insert" "mroads" '(33 -15) 1 1 0 )
(command "insert" "mroads" '(71 -30) 1 1 0 )
(command "insert" "mroads" '(11 -18) 1 1 0 )
(command "insert" "mroads" '(35 -17) 1 1 0 )
(command "insert" "mroads" '(1 -24) 1 1 0 )
(command "insert" "mroads" '(39 -15) 1 1 0 )
(command "insert" "mroads" '(28 -16) 1 1 0 )
(command "insert" "mroads" '(2 -31) 1 1 0 )
(command "insert" "mroads" '(12 -30) 1 1 0 )
(command "insert" "mroads" '(41 -31) 1 1 0 )
(command "insert" "mroads" '(79 -31) 1 1 0 )
(command "insert" "mroads" '(3 -30) 1 1 0 )
(command "insert" "mroads" '(40 -17) 1 1 0 )
(command "insert" "mroads" '(4 -25) 1 1 0 )
(command "insert" "mroads" '(50 -31) 1 1 0 )
(command "insert" "mroads" '(5 -28) 1 1 0 )
(command "insert" "mroads" '(29 -15) 1 1 0 )
(command "insert" "mroads" '(40 -25) 1 1 0 )
(command "insert" "mroads" '(41 -20) 1 1 0 )
(command "insert" "mroads" '(58 -30) 1 1 0 )
(command "insert" "mroads" '(37 -32) 1 1 0 )
(command "insert" "mroads" '(59 -31) 1 1 0 )
(command "insert" "mroads" '(41 -16) 1 1 0 )
(command "insert" "mroads" '(45 -32) 1 1 0 )
(command "insert" "mroads" '(73 -32) 1 1 0 )
(command "insert" "mroads" '(106 -30) 1 1 0 )
(command "insert" "mroads" '(35 -22) 1 1 0 )
(command "insert" "mroads" '(24 -17) 1 1 0 )
(command "insert" "mroads" '(107 -31) 1 1 0 )
(command "insert" "mroads" '(81 -32) 1 1 0 )
(command "insert" "mroads" '(36 -17) 1 1 0 )
(command "insert" "mroads" '(13 -17) 1 1 0 )
(command "insert" "mroads" '(37 -20) 1 1 0 )
(command "insert" "mroads" '(2 -22) 1 1 0 )
(command "insert" "mroads" '(72 -30) 1 1 0 )
(command "insert" "mroads" '(38 -27) 1 1 0 )
(command "insert" "mroads" '(54 -30) 1 1 0 )
(command "insert" "mroads" '(34 -23) 1 1 0 )
(command "insert" "mroads" '(55 -31) 1 1 0 )
(command "insert" "mroads" '(116 -31) 1 1 0 )
(command "insert" "mroads" '(102 -30) 1 1 0 )
(command "insert" "mroads" '(41 -29) 1 1 0 )
(command "insert" "mroads" '(103 -31) 1 1 0 )
(command "insert" "mroads" '(88 -32) 1 1 0 )
(command "insert" "mroads" '(84 -31) 1 1 0 )
(command "insert" "mroads" '(8 -15) 1 1 0 )
(command "insert" "mroads" '(33 -25) 1 1 0 )
(command "insert" "mroads" '(34 -30) 1 1 0 )
(command "insert" "mroads" '(8 -21) 1 1 0 )
(command "insert" "mroads" '(35 -31) 1 1 0 )
(command "insert" "mroads" '(9 -16) 1 1 0 )
(command "insert" "mroads" '(14 -15) 1 1 0 )
(command "insert" "mroads" '(40 -28) 1 1 0 )
(command "insert" "mroads" '(96 -31) 1 1 0 )
(command "insert" "mroads" '(36 -24) 1 1 0 )
(command "insert" "mroads" '(78 -31) 1 1 0 )
(command "insert" "mroads" '(82 -30) 1 1 0 )
(command "insert" "mroads" '(97 -30) 1 1 0 )
(command "insert" "mroads" '(37 -29) 1 1 0 )
(command "insert" "mroads" '(31 -31) 1 1 0 )
(command "insert" "mroads" '(38 -18) 1 1 0 )
(command "insert" "mroads" '(103 -32) 1 1 0 )
(command "insert" "mroads" '(39 -27) 1 1 0 )
(command "insert" "mroads" '(4 -15) 1 1 0 )
(command "insert" "mroads" '(7 -23) 1 1 0 )
(command "insert" "mroads" '(3 -18) 1 1 0 )
(command "insert" "mroads" '(30 -30) 1 1 0 )
(command "insert" "mroads" '(4 -21) 1 1 0 )
(command "insert" "mroads" '(79 -30) 1 1 0 )
(command "insert" "mroads" '(20 -16) 1 1 0 )
(command "insert" "mroads" '(92 -31) 1 1 0 )
(command "insert" "mroads" '(16 -16) 1 1 0 )
(command "insert" "mroads" '(30 -32) 1 1 0 )
(command "insert" "mroads" '(93 -30) 1 1 0 )
(command "insert" "mroads" '(58 -32) 1 1 0 )
(command "insert" "mroads" '(32 -19) 1 1 0 )
(command "insert" "mroads" '(33 -18) 1 1 0 )
(command "insert" "mroads" '(66 -32) 1 1 0 )
(command "insert" "mroads" '(110 -32) 1 1 0 )
(command "insert" "mroads" '(34 -25) 1 1 0 )
(command "insert" "mroads" '(8 -28) 1 1 0 )
(command "insert" "mroads" '(57 -30) 1 1 0 )
(command "insert" "mroads" '(24 -31) 1 1 0 )
(command "insert" "mroads" '(10 -30) 1 1 0 )
(command "insert" "mroads" '(25 -30) 1 1 0 )
(command "insert" "mroads" '(11 -31) 1 1 0 )
(command "insert" "mroads" '(72 -31) 1 1 0 )
(command "insert" "mroads" '(27 -16) 1 1 0 )
(command "insert" "mroads" '(49 -32) 1 1 0 )
(command "insert" "mroads" '(73 -30) 1 1 0 )
(command "insert" "mroads" '(3 -27) 1 1 0 )
(command "insert" "mroads" '(4 -28) 1 1 0 )
(command "insert" "mroads" '(41 -15) 1 1 0 )
(command "insert" "mroads" '(5 -17) 1 1 0 )
(command "insert" "mroads" '(20 -31) 1 1 0 )
(command "insert" "mroads" '(6 -30) 1 1 0 )
(command "insert" "mroads" '(21 -30) 1 1 0 )
(command "insert" "mroads" '(7 -31) 1 1 0 )
(command "insert" "mroads" '(68 -31) 1 1 0 )
(command "insert" "mroads" '(36 -32) 1 1 0 )
(command "insert" "mroads" '(69 -30) 1 1 0 )
(command "insert" "mroads" '(34 -16) 1 1 0 )
(command "insert" "mroads" '(44 -32) 1 1 0 )
(command "insert" "mroads" '(72 -32) 1 1 0 )
(command "insert" "mroads" '(6 -16) 1 1 0 )
(command "insert" "mroads" '(80 -32) 1 1 0 )
(command "insert" "mroads" '(11 -20) 1 1 0 )
(command "insert" "mroads" '(35 -19) 1 1 0 )
(command "insert" "mroads" '(36 -20) 1 1 0 )
(command "insert" "mroads" '(1 -30) 1 1 0 )
(command "insert" "mroads" '(28 -18) 1 1 0 )
(command "insert" "mroads" '(2 -29) 1 1 0 )
(command "insert" "mroads" '(48 -31) 1 1 0 )
(command "insert" "mroads" '(29 -19) 1 1 0 )
(command "insert" "mroads" '(27 -15) 1 1 0 )
(command "insert" "mroads" '(49 -30) 1 1 0 )
(command "insert" "mroads" '(4 -27) 1 1 0 )
(command "insert" "mroads" '(32 -32) 1 1 0 )
(command "insert" "mroads" '(5 -26) 1 1 0 )
(command "insert" "mroads" '(51 -32) 1 1 0 )
(command "insert" "mroads" '(40 -27) 1 1 0 )
(command "insert" "mroads" '(30 -18) 1 1 0 )
(command "insert" "mroads" '(17 -15) 1 1 0 )
(command "insert" "mroads" '(41 -26) 1 1 0 )
(command "insert" "mroads" '(56 -30) 1 1 0 )
(command "insert" "mroads" '(57 -31) 1 1 0 )
(command "insert" "mroads" '(86 -31) 1 1 0 )
(command "insert" "mroads" '(104 -30) 1 1 0 )
(command "insert" "mroads" '(44 -31) 1 1 0 )
(command "insert" "mroads" '(23 -15) 1 1 0 )
(command "insert" "mroads" '(105 -31) 1 1 0 )
(command "insert" "mroads" '(45 -30) 1 1 0 )
(command "insert" "mroads" '(8 -16) 1 1 0 )
(command "insert" "mroads" '(35 -24) 1 1 0 )
(command "insert" "mroads" '(50 -32) 1 1 0 )
(command "insert" "mroads" '(24 -19) 1 1 0 )
(command "insert" "mroads" '(36 -19) 1 1 0 )
(command "insert" "mroads" '(1 -23) 1 1 0 )
(command "insert" "mroads" '(104 -31) 1 1 0 )
(command "insert" "mroads" '(13 -15) 1 1 0 )
(command "insert" "mroads" '(37 -18) 1 1 0 )
(command "insert" "mroads" '(102 -32) 1 1 0 )
(command "insert" "mroads" '(38 -25) 1 1 0 )
(command "insert" "mroads" '(53 -31) 1 1 0 )
(command "insert" "mroads" '(78 -30) 1 1 0 )
(command "insert" "mroads" '(39 -28) 1 1 0 )
(command "insert" "mroads" '(84 -32) 1 1 0 )
(command "insert" "mroads" '(100 -30) 1 1 0 )
(command "insert" "mroads" '(115 -30) 1 1 0 )
(command "insert" "mroads" '(25 -17) 1 1 0 )
(command "insert" "mroads" '(101 -31) 1 1 0 )
(command "insert" "mroads" '(21 -32) 1 1 0 )
(command "insert" "mroads" '(19 -16) 1 1 0 )
(command "insert" "mroads" '(31 -16) 1 1 0 )
(command "insert" "mroads" '(29 -32) 1 1 0 )
(command "insert" "mroads" '(41 -17) 1 1 0 )
(command "insert" "mroads" '(32 -30) 1 1 0 )
(command "insert" "mroads" '(65 -32) 1 1 0 )
(command "insert" "mroads" '(52 -31) 1 1 0 )
(command "insert" "mroads" '(7 -20) 1 1 0 )
(command "insert" "mroads" '(110 -31) 1 1 0 )
(command "insert" "mroads" '(34 -28) 1 1 0 )
(command "insert" "mroads" '(8 -23) 1 1 0 )
(command "insert" "mroads" '(80 -30) 1 1 0 )
(command "insert" "mroads" '(111 -30) 1 1 0 )
(command "insert" "mroads" '(57 -32) 1 1 0 )
(command "insert" "mroads" '(81 -31) 1 1 0 )
(command "insert" "mroads" '(36 -26) 1 1 0 )
(command "insert" "mroads" '(40 -24) 1 1 0 )
(command "insert" "mroads" '(37 -27) 1 1 0 )
(command "insert" "mroads" '(26 -16) 1 1 0 )
(command "insert" "mroads" '(38 -16) 1 1 0 )
(command "insert" "mroads" '(39 -21) 1 1 0 )
(command "insert" "mroads" '(28 -30) 1 1 0 )
(command "insert" "mroads" '(29 -31) 1 1 0 )
(command "insert" "mroads" '(3 -20) 1 1 0 )
(command "insert" "mroads" '(90 -31) 1 1 0 )
(command "insert" "mroads" '(4 -23) 1 1 0 )
(command "insert" "mroads" '(76 -30) 1 1 0 )
(command "insert" "mroads" '(91 -30) 1 1 0 )
(command "insert" "mroads" '(7 -27) 1 1 0 )
(command "insert" "mroads" '(5 -22) 1 1 0 )
(command "insert" "mroads" '(20 -18) 1 1 0 )
(command "insert" "mroads" '(77 -31) 1 1 0 )
(command "insert" "mroads" '(21 -19) 1 1 0 )
(command "insert" "mroads" '(7 -32) 1 1 0 )
(command "insert" "mroads" '(35 -32) 1 1 0 )
(command "insert" "mroads" '(113 -30) 1 1 0 )
(command "insert" "mroads" '(33 -16) 1 1 0 )
(command "insert" "mroads" '(43 -32) 1 1 0 )
(command "insert" "mroads" '(8 -30) 1 1 0 )
(command "insert" "mroads" '(40 -16) 1 1 0 )
(command "insert" "mroads" '(87 -32) 1 1 0 )
(command "insert" "mroads" '(9 -31) 1 1 0 )
(command "insert" "mroads" '(95 -32) 1 1 0 )
(command "insert" "mroads" '(15 -17) 1 1 0 )
(command "insert" "mroads" '(87 -30) 1 1 0 )
(command "insert" "mroads" '(11 -17) 1 1 0 )
(command "insert" "mroads" '(27 -18) 1 1 0 )
(command "insert" "mroads" '(1 -27) 1 1 0 )
(command "insert" "mroads" '(39 -18) 1 1 0 )
(command "insert" "mroads" '(14 -32) 1 1 0 )
(command "insert" "mroads" '(3 -29) 1 1 0 )
(command "insert" "mroads" '(4 -30) 1 1 0 )
(command "insert" "mroads" '(19 -30) 1 1 0 )
(command "layer" "m" "Commmer" "" )
(command "insert" "Commmer" '(32 -1) 1 1 0 )
(command "insert" "Commmer" '(35 -1) 1 1 0 )
(command "insert" "Commmer" '(21 -2) 1 1 0 )
(command "insert" "Commmer" '(16 -2) 1 1 0 )
(command "insert" "Commmer" '(26 -2) 1 1 0 )
(command "insert" "Commmer" '(28 -1) 1 1 0 )
(command "insert" "Commmer" '(23 -2) 1 1 0 )
(command "insert" "Commmer" '(34 -2) 1 1 0 )
(command "insert" "Commmer" '(27 -2) 1 1 0 )
(command "insert" "Commmer" '(32 -2) 1 1 0 )
(command "insert" "Commmer" '(18 -1) 1 1 0 )
(command "insert" "Commmer" '(31 -1) 1 1 0 )
(command "insert" "Commmer" '(22 -2) 1 1 0 )
(command "insert" "Commmer" '(21 -1) 1 1 0 )
(command "insert" "Commmer" '(34 -1) 1 1 0 )
(command "insert" "Commmer" '(17 -2) 1 1 0 )
(command "insert" "Commmer" '(28 -2) 1 1 0 )
(command "insert" "Commmer" '(24 -1) 1 1 0 )
(command "insert" "Commmer" '(33 -2) 1 1 0 )
(command "insert" "Commmer" '(30 -1) 1 1 0 )
(command "insert" "Commmer" '(27 -1) 1 1 0 )
(command "insert" "Commmer" '(18 -2) 1 1 0 )
(command "insert" "Commmer" '(20 -1) 1 1 0 )
(command "insert" "Commmer" '(17 -1) 1 1 0 )
(command "insert" "Commmer" '(19 -2) 1 1 0 )
(command "insert" "Commmer" '(29 -2) 1 1 0 )
(command "insert" "Commmer" '(24 -2) 1 1 0 )
(command "insert" "Commmer" '(23 -1) 1 1 0 )
(command "insert" "Commmer" '(15 -1) 1 1 0 )
(command "insert" "Commmer" '(33 -1) 1 1 0 )
(command "insert" "Commmer" '(35 -2) 1 1 0 )
(command "insert" "Commmer" '(26 -1) 1 1 0 )
(command "insert" "Commmer" '(15 -2) 1 1 0 )
(command "insert" "Commmer" '(20 -2) 1 1 0 )
(command "insert" "Commmer" '(30 -2) 1 1 0 )
(command "insert" "Commmer" '(16 -1) 1 1 0 )
(command "insert" "Commmer" '(29 -1) 1 1 0 )
(command "insert" "Commmer" '(31 -2) 1 1 0 )
(command "insert" "Commmer" '(25 -2) 1 1 0 )
(command "insert" "Commmer" '(22 -1) 1 1 0 )
(command "insert" "Commmer" '(19 -1) 1 1 0 )
(command "insert" "Commmer" '(25 -1) 1 1 0 )
(command "layer" "m" "ped" "" )
(command "insert" "ped" '(1 -3) 1 1 0 )
(command "insert" "ped" '(2 -18) 1 1 0 )
(command "insert" "ped" '(2 -8) 1 1 0 )
(command "insert" "ped" '(1 -17) 1 1 0 )
(command "insert" "ped" '(2 -1) 1 1 0 )
(command "insert" "ped" '(1 -15) 1 1 0 )
(command "insert" "ped" '(6 -2) 1 1 0 )
(command "insert" "ped" '(1 -6) 1 1 0 )
(command "insert" "ped" '(2 -12) 1 1 0 )
(command "insert" "ped" '(5 -1) 1 1 0 )
(command "insert" "ped" '(2 -5) 1 1 0 )
(command "insert" "ped" '(1 -11) 1 1 0 )
(command "insert" "ped" '(1 -20) 1 1 0 )
(command "insert" "ped" '(1 -2) 1 1 0 )
(command "insert" "ped" '(2 -19) 1 1 0 )
(command "insert" "ped" '(2 -9) 1 1 0 )
(command "insert" "ped" '(8 -1) 1 1 0 )
(command "insert" "ped" '(1 -16) 1 1 0 )
(command "insert" "ped" '(1 -14) 1 1 0 )
(command "insert" "ped" '(1 -5) 1 1 0 )
(command "insert" "ped" '(2 -13) 1 1 0 )
(command "insert" "ped" '(7 -2) 1 1 0 )
(command "insert" "ped" '(2 -2) 1 1 0 )
(command "insert" "ped" '(1 -10) 1 1 0 )
(command "insert" "ped" '(4 -1) 1 1 0 )
(command "insert" "ped" '(1 -1) 1 1 0 )
(command "insert" "ped" '(2 -16) 1 1 0 )
(command "insert" "ped" '(3 -2) 1 1 0 )
(command "insert" "ped" '(2 -6) 1 1 0 )
(command "insert" "ped" '(8 -2) 1 1 0 )
(command "insert" "ped" '(7 -1) 1 1 0 )
(command "insert" "ped" '(1 -13) 1 1 0 )
(command "insert" "ped" '(2 -20) 1 1 0 )
(command "insert" "ped" '(1 -4) 1 1 0 )
(command "insert" "ped" '(2 -10) 1 1 0 )
(command "insert" "ped" '(1 -19) 1 1 0 )
(command "insert" "ped" '(2 -3) 1 1 0 )
(command "insert" "ped" '(1 -9) 1 1 0 )
(command "insert" "ped" '(4 -2) 1 1 0 )
(command "insert" "ped" '(2 -14) 1 1 0 )
(command "insert" "ped" '(2 -17) 1 1 0 )
(command "insert" "ped" '(2 -7) 1 1 0 )
(command "insert" "ped" '(1 -12) 1 1 0 )
(command "insert" "ped" '(6 -1) 1 1 0 )
(command "insert" "ped" '(3 -1) 1 1 0 )
(command "insert" "ped" '(2 -11) 1 1 0 )
(command "insert" "ped" '(1 -18) 1 1 0 )
(command "insert" "ped" '(1 -8) 1 1 0 )
(command "insert" "ped" '(1 -7) 1 1 0 )
(command "insert" "ped" '(2 -15) 1 1 0 )
(command "insert" "ped" '(5 -2) 1 1 0 )
(command "insert" "ped" '(2 -4) 1 1 0 )
(command "layer" "m" "edge" "" )
(command "insert" "edge" '(44 -2) 1 1 0 )
(command "insert" "edge" '(47 -2) 1 1 0 )
(command "insert" "edge" '(45 -1) 1 1 0 )
(command "insert" "edge" '(41 -2) 1 1 0 )
(command "insert" "edge" '(38 -1) 1 1 0 )
(command "insert" "edge" '(46 -1) 1 1 0 )
(command "insert" "edge" '(43 -1) 1 1 0 )
(command "insert" "edge" '(36 -2) 1 1 0 )
(command "insert" "edge" '(44 -1) 1 1 0 )
(command "insert" "edge" '(37 -2) 1 1 0 )
(command "insert" "edge" '(42 -2) 1 1 0 )
(command "insert" "edge" '(41 -1) 1 1 0 )
(command "insert" "edge" '(45 -2) 1 1 0 )
(command "insert" "edge" '(40 -2) 1 1 0 )
(command "insert" "edge" '(39 -1) 1 1 0 )
(command "insert" "edge" '(36 -1) 1 1 0 )
(command "insert" "edge" '(43 -2) 1 1 0 )
(command "insert" "edge" '(47 -1) 1 1 0 )
(command "insert" "edge" '(40 -1) 1 1 0 )
(command "insert" "edge" '(38 -2) 1 1 0 )
(command "insert" "edge" '(42 -1) 1 1 0 )
(command "insert" "edge" '(37 -1) 1 1 0 )
(command "insert" "edge" '(46 -2) 1 1 0 )
(command "insert" "edge" '(39 -2) 1 1 0 )
(command "layer" "m" "mroads" "" )
(command "insert" "mroads" '(5 -31) 1 1 0 )
(command "insert" "mroads" '(66 -31) 1 1 0 )
(command "insert" "mroads" '(6 -28) 1 1 0 )
(command "insert" "mroads" '(67 -30) 1 1 0 )
(command "insert" "mroads" '(7 -25) 1 1 0 )
(command "insert" "mroads" '(22 -19) 1 1 0 )
(command "insert" "mroads" '(18 -19) 1 1 0 )
(command "insert" "mroads" '(38 -21) 1 1 0 )
(command "insert" "mroads" '(114 -31) 1 1 0 )
(command "insert" "mroads" '(13 -32) 1 1 0 )
(command "insert" "mroads" '(35 -15) 1 1 0 )
(command "insert" "mroads" '(14 -31) 1 1 0 )
(command "insert" "mroads" '(15 -30) 1 1 0 )
(command "insert" "mroads" '(35 -21) 1 1 0 )
(command "insert" "mroads" '(12 -17) 1 1 0 )
(command "insert" "mroads" '(36 -22) 1 1 0 )
(command "insert" "mroads" '(1 -28) 1 1 0 )
(command "insert" "mroads" '(25 -15) 1 1 0 )
(command "insert" "mroads" '(39 -16) 1 1 0 )
(command "insert" "mroads" '(63 -30) 1 1 0 )
(command "insert" "mroads" '(37 -23) 1 1 0 )
(command "insert" "mroads" '(2 -27) 1 1 0 )
(command "insert" "mroads" '(109 -32) 1 1 0 )
(command "insert" "mroads" '(29 -17) 1 1 0 )
(command "insert" "mroads" '(31 -15) 1 1 0 )
(command "insert" "mroads" '(5 -24) 1 1 0 )
(command "insert" "mroads" '(20 -32) 1 1 0 )
(command "insert" "mroads" '(6 -23) 1 1 0 )
(command "insert" "mroads" '(30 -16) 1 1 0 )
(command "insert" "mroads" '(28 -32) 1 1 0 )
(command "insert" "mroads" '(7 -22) 1 1 0 )
(command "insert" "mroads" '(41 -23) 1 1 0 )
(command "insert" "mroads" '(42 -31) 1 1 0 )
(command "insert" "mroads" '(23 -19) 1 1 0 )
(command "insert" "mroads" '(21 -15) 1 1 0 )
(command "insert" "mroads" '(43 -30) 1 1 0 )
(command "insert" "mroads" '(116 -32) 1 1 0 )
(command "insert" "mroads" '(8 -18) 1 1 0 )
(command "insert" "mroads" '(11 -15) 1 1 0 )
(command "insert" "mroads" '(35 -26) 1 1 0 )
(command "insert" "mroads" '(9 -19) 1 1 0 )
(command "insert" "mroads" '(36 -29) 1 1 0 )
(command "insert" "mroads" '(1 -21) 1 1 0 )
(command "insert" "mroads" '(25 -16) 1 1 0 )
(command "insert" "mroads" '(29 -20) 1 1 0 )
(command "insert" "mroads" '(37 -16) 1 1 0 )
(command "insert" "mroads" '(98 -30) 1 1 0 )
(command "insert" "mroads" '(38 -31) 1 1 0 )
(command "insert" "mroads" '(99 -31) 1 1 0 )
(command "insert" "mroads" '(39 -30) 1 1 0 )
(command "insert" "mroads" '(3 -17) 1 1 0 )
(command "insert" "mroads" '(19 -18) 1 1 0 )
(command "insert" "mroads" '(7 -15) 1 1 0 )
(command "insert" "mroads" '(31 -18) 1 1 0 )
(command "insert" "mroads" '(46 -30) 1 1 0 )
(command "insert" "mroads" '(6 -32) 1 1 0 )
(command "insert" "mroads" '(34 -32) 1 1 0 )
(command "insert" "mroads" '(32 -16) 1 1 0 )
(command "insert" "mroads" '(94 -30) 1 1 0 )
(command "insert" "mroads" '(18 -31) 1 1 0 )
(command "insert" "mroads" '(42 -32) 1 1 0 )
(command "insert" "mroads" '(86 -32) 1 1 0 )
(command "insert" "mroads" '(34 -26) 1 1 0 )
(command "insert" "mroads" '(8 -25) 1 1 0 )
(command "insert" "mroads" '(94 -32) 1 1 0 )
(command "insert" "mroads" '(9 -20) 1 1 0 )
(command "insert" "mroads" '(10 -19) 1 1 0 )
(command "insert" "mroads" '(37 -25) 1 1 0 )
(command "insert" "mroads" '(26 -30) 1 1 0 )
(command "insert" "mroads" '(7 -18) 1 1 0 )
(command "insert" "mroads" '(38 -22) 1 1 0 )
(command "insert" "mroads" '(27 -31) 1 1 0 )
(command "insert" "mroads" '(40 -20) 1 1 0 )
(command "insert" "mroads" '(39 -23) 1 1 0 )
(command "insert" "mroads" '(88 -31) 1 1 0 )
(command "insert" "mroads" '(74 -30) 1 1 0 )
(command "insert" "mroads" '(89 -30) 1 1 0 )
(command "insert" "mroads" '(3 -22) 1 1 0 )
(command "insert" "mroads" '(75 -31) 1 1 0 )
(command "insert" "mroads" '(4 -17) 1 1 0 )
(command "insert" "mroads" '(5 -20) 1 1 0 )
(command "insert" "mroads" '(6 -27) 1 1 0 )
(command "insert" "mroads" '(21 -17) 1 1 0 )
(command "insert" "mroads" '(17 -17) 1 1 0 )
(command "insert" "mroads" '(22 -30) 1 1 0 )
(command "insert" "mroads" '(33 -22) 1 1 0 )
(command "insert" "mroads" '(23 -31) 1 1 0 )
(command "insert" "mroads" '(12 -32) 1 1 0 )
(command "insert" "mroads" '(34 -21) 1 1 0 )
(command "insert" "mroads" '(70 -30) 1 1 0 )
(command "insert" "mroads" '(85 -30) 1 1 0 )
(command "insert" "mroads" '(48 -32) 1 1 0 )
(command "insert" "mroads" '(71 -31) 1 1 0 )
(command "insert" "mroads" '(34 -15) 1 1 0 )
(command "insert" "mroads" '(11 -19) 1 1 0 )
(command "insert" "mroads" '(100 -32) 1 1 0 )
(command "insert" "mroads" '(27 -20) 1 1 0 )
(command "insert" "mroads" '(1 -25) 1 1 0 )
(command "insert" "mroads" '(108 -32) 1 1 0 )
(command "insert" "mroads" '(2 -30) 1 1 0 )
(command "insert" "mroads" '(3 -31) 1 1 0 )
(command "insert" "mroads" '(64 -31) 1 1 0 )
(command "insert" "mroads" '(4 -24) 1 1 0 )
(command "insert" "mroads" '(19 -32) 1 1 0 )
(command "insert" "mroads" '(62 -31) 1 1 0 )
(command "insert" "mroads" '(50 -30) 1 1 0 )
(command "insert" "mroads" '(65 -30) 1 1 0 )
(command "insert" "mroads" '(5 -29) 1 1 0 )
(command "insert" "mroads" '(27 -32) 1 1 0 )
(command "insert" "mroads" '(6 -18) 1 1 0 )
(command "insert" "mroads" '(101 -32) 1 1 0 )
(command "insert" "mroads" '(112 -31) 1 1 0 )
(command "insert" "mroads" '(41 -21) 1 1 0 )
(command "insert" "mroads" '(22 -17) 1 1 0 )
(command "insert" "mroads" '(79 -32) 1 1 0 )
(command "insert" "mroads" '(18 -17) 1 1 0 )
(command "insert" "mroads" '(23 -20) 1 1 0 )
(command "insert" "mroads" '(40 -31) 1 1 0 )
(command "insert" "mroads" '(115 -32) 1 1 0 )
(command "insert" "mroads" '(60 -31) 1 1 0 )
(command "insert" "mroads" '(61 -30) 1 1 0 )
(command "insert" "mroads" '(35 -23) 1 1 0 )
(command "insert" "mroads" '(24 -16) 1 1 0 )
(command "insert" "mroads" '(36 -16) 1 1 0 )
(command "insert" "mroads" '(108 -31) 1 1 0 )
(command "insert" "mroads" '(37 -21) 1 1 0 )
(command "insert" "mroads" '(2 -25) 1 1 0 )
(command "insert" "mroads" '(109 -30) 1 1 0 )
(command "insert" "mroads" '(7 -16) 1 1 0 )
(command "insert" "mroads" '(38 -26) 1 1 0 )
(command "insert" "mroads" '(40 -18) 1 1 0 )
(command "insert" "mroads" '(114 -32) 1 1 0 )
(command "insert" "mroads" '(116 -30) 1 1 0 )
(command "insert" "mroads" '(6 -21) 1 1 0 )
(command "insert" "mroads" '(111 -31) 1 1 0 )
(command "insert" "mroads" '(19 -15) 1 1 0 )
(command "insert" "mroads" '(41 -30) 1 1 0 )
(command "insert" "mroads" '(5 -32) 1 1 0 )
(command "insert" "mroads" '(33 -32) 1 1 0 )
(command "insert" "mroads" '(41 -32) 1 1 0 )
(command "insert" "mroads" '(7 -29) 1 1 0 )
(command "insert" "mroads" '(85 -32) 1 1 0 )
(command "insert" "mroads" '(9 -15) 1 1 0 )
(command "insert" "mroads" '(33 -26) 1 1 0 )
(command "insert" "mroads" '(22 -31) 1 1 0 )
(command "insert" "mroads" '(93 -32) 1 1 0 )
(command "insert" "mroads" '(8 -20) 1 1 0 )
(command "insert" "mroads" '(37 -15) 1 1 0 )
(command "insert" "mroads" '(35 -28) 1 1 0 )
(command "insert" "mroads" '(9 -17) 1 1 0 )
(command "insert" "mroads" '(96 -30) 1 1 0 )
(command "insert" "mroads" '(36 -31) 1 1 0 )
(command "insert" "mroads" '(15 -15) 1 1 0 )
(command "insert" "mroads" '(97 -31) 1 1 0 )
(command "insert" "mroads" '(37 -30) 1 1 0 )
(command "insert" "mroads" '(38 -29) 1 1 0 )
(command "insert" "mroads" '(83 -31) 1 1 0 )
(command "insert" "mroads" '(39 -24) 1 1 0 )
(command "insert" "mroads" '(5 -15) 1 1 0 )
(command "insert" "mroads" '(3 -19) 1 1 0 )
(command "insert" "mroads" '(4 -20) 1 1 0 )
(command "insert" "mroads" '(19 -20) 1 1 0 )
(command "insert" "mroads" '(92 -30) 1 1 0 )
(command "insert" "mroads" '(16 -31) 1 1 0 )
(command "insert" "mroads" '(93 -31) 1 1 0 )
(command "insert" "mroads" '(17 -30) 1 1 0 )
(command "insert" "mroads" '(32 -18) 1 1 0 )
(command "insert" "mroads" '(11 -32) 1 1 0 )
(command "insert" "mroads" '(33 -19) 1 1 0 )
(command "insert" "mroads" '(40 -29) 1 1 0 )
(command "insert" "mroads" '(8 -27) 1 1 0 )
(command "insert" "mroads" '(63 -32) 1 1 0 )
(command "insert" "mroads" '(5 -21) 1 1 0 )
(command "insert" "mroads" '(24 -30) 1 1 0 )
(command "insert" "mroads" '(14 -17) 1 1 0 )
(command "insert" "mroads" '(71 -32) 1 1 0 )
(command "insert" "mroads" '(10 -17) 1 1 0 )
(command "insert" "mroads" '(25 -31) 1 1 0 )
(command "insert" "mroads" '(99 -32) 1 1 0 )
(command "insert" "mroads" '(111 -32) 1 1 0 )
(command "insert" "mroads" '(107 -32) 1 1 0 )
(command "insert" "mroads" '(38 -20) 1 1 0 )
(command "insert" "mroads" '(12 -31) 1 1 0 )
(command "insert" "mroads" '(27 -17) 1 1 0 )
(command "insert" "mroads" '(39 -17) 1 1 0 )
(command "insert" "mroads" '(13 -30) 1 1 0 )
(command "insert" "mroads" '(41 -24) 1 1 0 )
(command "insert" "mroads" '(3 -24) 1 1 0 )
(command "insert" "mroads" '(56 -32) 1 1 0 )
(command "insert" "mroads" '(4 -19) 1 1 0 )
(command "insert" "mroads" '(26 -32) 1 1 0 )
(command "insert" "mroads" '(5 -18) 1 1 0 )
(command "insert" "mroads" '(20 -30) 1 1 0 )
(command "insert" "mroads" '(6 -25) 1 1 0 )
(command "insert" "mroads" '(21 -31) 1 1 0 )
(command "insert" "mroads" '(40 -22) 1 1 0 )
(command "insert" "mroads" '(78 -32) 1 1 0 )
(command "insert" "mroads" '(41 -18) 1 1 0 )
(command "insert" "mroads" '(18 -20) 1 1 0 )
(command "insert" "mroads" '(33 -20) 1 1 0 )
(command "insert" "mroads" '(69 -31) 1 1 0 )
(command "insert" "mroads" '(34 -19) 1 1 0 )
(command "insert" "mroads" '(32 -15) 1 1 0 )
(command "insert" "mroads" '(15 -32) 1 1 0 )
(command "insert" "mroads" '(64 -32) 1 1 0 )
(command "insert" "mroads" '(35 -16) 1 1 0 )
(command "insert" "mroads" '(38 -15) 1 1 0 )
(command "insert" "mroads" '(77 -32) 1 1 0 )
(command "insert" "mroads" '(1 -31) 1 1 0 )
(command "insert" "mroads" '(28 -17) 1 1 0 )
(command "insert" "mroads" '(2 -28) 1 1 0 )
(command "insert" "mroads" '(48 -30) 1 1 0 )
(command "insert" "mroads" '(113 -32) 1 1 0 )
(command "insert" "mroads" '(49 -31) 1 1 0 )
(command "insert" "mroads" '(4 -26) 1 1 0 )
(command "insert" "mroads" '(28 -15) 1 1 0 )
(command "insert" "mroads" '(5 -27) 1 1 0 )
(command "insert" "mroads" '(40 -26) 1 1 0 )
(command "insert" "mroads" '(4 -32) 1 1 0 )
(command "insert" "mroads" '(7 -21) 1 1 0 )
(command "insert" "mroads" '(18 -15) 1 1 0 )
(command "insert" "mroads" '(40 -32) 1 1 0 )
(command "insert" "mroads" '(34 -20) 1 1 0 )
(command "insert" "mroads" '(58 -31) 1 1 0 )
(command "insert" "mroads" '(44 -30) 1 1 0 )
(command "insert" "mroads" '(59 -30) 1 1 0 )
(command "insert" "mroads" '(92 -32) 1 1 0 )
(command "insert" "mroads" '(45 -31) 1 1 0 )
(command "insert" "mroads" '(6 -17) 1 1 0 )
(command "insert" "mroads" '(106 -31) 1 1 0 )
(command "insert" "mroads" '(35 -25) 1 1 0 )
(command "insert" "mroads" '(24 -18) 1 1 0 )
(command "insert" "mroads" '(107 -30) 1 1 0 )
(command "insert" "mroads" '(36 -18) 1 1 0 )
(command "insert" "mroads" '(25 -19) 1 1 0 )
(command "insert" "mroads" '(13 -16) 1 1 0 )
(command "insert" "mroads" '(37 -19) 1 1 0 )
(command "insert" "mroads" '(2 -23) 1 1 0 )
(command "insert" "mroads" '(38 -24) 1 1 0 )
(command "insert" "mroads" '(39 -29) 1 1 0 )
(command "insert" "mroads" '(54 -31) 1 1 0 )
(command "insert" "mroads" '(115 -31) 1 1 0 )
(command "insert" "mroads" '(55 -30) 1 1 0 )
(command "insert" "mroads" '(22 -20) 1 1 0 )
(command "insert" "mroads" '(30 -20) 1 1 0 )
(command "insert" "mroads" '(19 -17) 1 1 0 )
(command "insert" "mroads" '(102 -31) 1 1 0 )
(command "insert" "mroads" '(41 -28) 1 1 0 )
(command "insert" "mroads" '(31 -17) 1 1 0 )
(command "insert" "mroads" '(103 -30) 1 1 0 )
(command "insert" "mroads" '(10 -32) 1 1 0 )
(command "insert" "mroads" '(22 -32) 1 1 0 )
(command "insert" "mroads" '(18 -32) 1 1 0 )
(command "insert" "mroads" '(33 -24) 1 1 0 )
(command "insert" "mroads" '(62 -32) 1 1 0 )
(command "insert" "mroads" '(110 -30) 1 1 0 )
(command "insert" "mroads" '(34 -31) 1 1 0 )
(command "insert" "mroads" '(8 -22) 1 1 0 )
(command "insert" "mroads" '(23 -17) 1 1 0 )
(command "insert" "mroads" '(70 -32) 1 1 0 )
(command "insert" "mroads" '(35 -30) 1 1 0 )
(command "insert" "mroads" '(98 -32) 1 1 0 )
(command "insert" "mroads" '(36 -25) 1 1 0 )
(command "insert" "mroads" '(10 -20) 1 1 0 )
(command "insert" "mroads" '(25 -20) 1 1 0 )
(command "insert" "mroads" '(82 -31) 1 1 0 )
(command "insert" "mroads" '(106 -32) 1 1 0 )
(command "insert" "mroads" '(37 -28) 1 1 0 )
(command "insert" "mroads" '(26 -19) 1 1 0 )
(command "insert" "mroads" '(38 -19) 1 1 0 )
(command "insert" "mroads" '(3 -15) 1 1 0 )
(command "insert" "mroads" '(39 -26) 1 1 0 )
(command "insert" "mroads" '(51 -31) 1 1 0 )
(command "insert" "mroads" '(3 -21) 1 1 0 )
(command "insert" "mroads" '(25 -32) 1 1 0 )
(command "insert" "mroads" '(90 -30) 1 1 0 )
(command "insert" "mroads" '(30 -31) 1 1 0 )
(command "insert" "mroads" '(4 -22) 1 1 0 )
(command "insert" "mroads" '(91 -31) 1 1 0 )
(command "insert" "mroads" '(31 -30) 1 1 0 )
(command "insert" "mroads" '(5 -23) 1 1 0 )
(command "insert" "mroads" '(20 -17) 1 1 0 )
(command "insert" "mroads" '(16 -17) 1 1 0 )
(command "insert" "mroads" '(21 -20) 1 1 0 )
(command "insert" "mroads" '(32 -20) 1 1 0 )
(command "insert" "mroads" '(33 -17) 1 1 0 )
(command "insert" "mroads" '(34 -22) 1 1 0 )
(command "insert" "mroads" '(8 -29) 1 1 0 )
(command "insert" "mroads" '(61 -31) 1 1 0 )
(command "insert" "mroads" '(86 -30) 1 1 0 )
(command "insert" "mroads" '(10 -31) 1 1 0 )
(command "insert" "mroads" '(6 -19) 1 1 0 )
(command "insert" "mroads" '(87 -31) 1 1 0 )
(command "insert" "mroads" '(11 -30) 1 1 0 )
(command "insert" "mroads" '(76 -32) 1 1 0 )
(command "insert" "mroads" '(27 -19) 1 1 0 )
(command "insert" "mroads" '(39 -19) 1 1 0 )
(command "insert" "mroads" '(28 -20) 1 1 0 )
(command "insert" "mroads" '(3 -26) 1 1 0 )
(command "insert" "mroads" '(40 -15) 1 1 0 )
(command "insert" "mroads" '(4 -29) 1 1 0 )
(command "insert" "mroads" '(19 -31) 1 1 0 )
(command "insert" "mroads" '(7 -26) 1 1 0 )
(command "insert" "mroads" '(5 -16) 1 1 0 )
(command "insert" "mroads" '(3 -32) 1 1 0 )
(command "insert" "mroads" '(66 -30) 1 1 0 )
(command "insert" "mroads" '(6 -31) 1 1 0 )
(command "insert" "mroads" '(67 -31) 1 1 0 )
(command "insert" "mroads" '(7 -30) 1 1 0 )
(command "insert" "mroads" '(22 -18) 1 1 0 )
(command "insert" "mroads" '(55 -32) 1 1 0 )
(command "insert" "mroads" '(18 -18) 1 1 0 )
(command "insert" "mroads" '(83 -32) 1 1 0 )
(command "insert" "mroads" '(114 -30) 1 1 0 )
(command "insert" "mroads" '(34 -17) 1 1 0 )
(command "insert" "mroads" '(91 -32) 1 1 0 )
(command "insert" "mroads" '(14 -30) 1 1 0 )
(command "insert" "mroads" '(36 -15) 1 1 0 )
(command "insert" "mroads" '(15 -31) 1 1 0 )
(command "insert" "mroads" '(35 -18) 1 1 0 )
(command "insert" "mroads" '(12 -16) 1 1 0 )
(command "insert" "mroads" '(36 -21) 1 1 0 )
(command "insert" "mroads" '(1 -29) 1 1 0 )
(command "insert" "mroads" '(63 -31) 1 1 0 )
(command "insert" "mroads" '(28 -19) 1 1 0 )
(command "insert" "mroads" '(2 -26) 1 1 0 )
(command "insert" "mroads" '(26 -15) 1 1 0 )
(command "insert" "mroads" '(12 -15) 1 1 0 )
(command "insert" "mroads" '(29 -18) 1 1 0 )
(command "insert" "mroads" '(5 -25) 1 1 0 )
(command "insert" "mroads" '(16 -15) 1 1 0 )
(command "insert" "mroads" '(6 -22) 1 1 0 )
(command "insert" "mroads" '(30 -19) 1 1 0 )
(command "insert" "mroads" '(41 -25) 1 1 0 )
(command "insert" "mroads" '(56 -31) 1 1 0 )
(command "insert" "mroads" '(9 -32) 1 1 0 )
(command "insert" "mroads" '(42 -30) 1 1 0 )
(command "insert" "mroads" '(23 -16) 1 1 0 )
(command "insert" "mroads" '(43 -31) 1 1 0 )
(command "insert" "mroads" '(17 -32) 1 1 0 )
(command "insert" "mroads" '(22 -15) 1 1 0 )
(command "insert" "mroads" '(61 -32) 1 1 0 )
(command "insert" "mroads" '(52 -30) 1 1 0 )
(command "insert" "mroads" '(105 -30) 1 1 0 )
(command "insert" "mroads" '(69 -32) 1 1 0 )
(command "insert" "mroads" '(34 -24) 1 1 0 )
(command "insert" "mroads" '(8 -17) 1 1 0 )
(command "insert" "mroads" '(97 -32) 1 1 0 )
(command "insert" "mroads" '(35 -27) 1 1 0 )
(command "insert" "mroads" '(24 -20) 1 1 0 )
(command "insert" "mroads" '(105 -32) 1 1 0 )
(command "insert" "mroads" '(36 -28) 1 1 0 )
(command "insert" "mroads" '(1 -22) 1 1 0 )
(command "insert" "mroads" '(6 -29) 1 1 0 )
(command "insert" "mroads" '(37 -17) 1 1 0 )
(command "insert" "mroads" '(2 -21) 1 1 0 )
(command "insert" "mroads" '(38 -30) 1 1 0 )
(command "insert" "mroads" '(53 -30) 1 1 0 )
(command "insert" "mroads" '(112 -32) 1 1 0 )
(command "insert" "mroads" '(39 -31) 1 1 0 )
(command "insert" "mroads" '(100 -31) 1 1 0 )
(command "insert" "mroads" '(24 -32) 1 1 0 )
(command "insert" "mroads" '(101 -30) 1 1 0 )
(command "insert" "mroads" '(19 -19) 1 1 0 )
(command "insert" "mroads" '(31 -19) 1 1 0 )
(command "insert" "mroads" '(20 -20) 1 1 0 )
(command "insert" "mroads" '(47 -31) 1 1 0 )
(command "insert" "mroads" '(32 -31) 1 1 0 )
(command "insert" "mroads" '(18 -30) 1 1 0 )
(command "insert" "mroads" '(33 -30) 1 1 0 )
(command "insert" "mroads" '(34 -29) 1 1 0 )
(command "insert" "mroads" '(8 -24) 1 1 0 )
(command "insert" "mroads" '(39 -32) 1 1 0 )
(command "insert" "mroads" '(80 -31) 1 1 0 )
(command "insert" "mroads" '(81 -30) 1 1 0 )
(command "insert" "mroads" '(36 -27) 1 1 0 )
(command "insert" "mroads" '(10 -18) 1 1 0 )
(command "insert" "mroads" '(75 -32) 1 1 0 )
(command "insert" "mroads" '(37 -26) 1 1 0 )
(command "insert" "mroads" '(26 -17) 1 1 0 )
(command "insert" "mroads" '(38 -17) 1 1 0 )
(command "insert" "mroads" '(39 -20) 1 1 0 )
(command "insert" "mroads" '(88 -30) 1 1 0 )
(command "insert" "mroads" '(28 -31) 1 1 0 )
(command "insert" "mroads" '(89 -31) 1 1 0 )
(command "insert" "mroads" '(29 -30) 1 1 0 )
(command "insert" "mroads" '(3 -23) 1 1 0 )
(command "insert" "mroads" '(4 -16) 1 1 0 )
(command "insert" "mroads" '(2 -32) 1 1 0 )
(command "insert" "mroads" '(76 -31) 1 1 0 )
(command "insert" "mroads" '(46 -32) 1 1 0 )
(command "insert" "mroads" '(20 -19) 1 1 0 )
(command "insert" "mroads" '(33 -29) 1 1 0 )
(command "insert" "mroads" '(77 -30) 1 1 0 )
(command "insert" "mroads" '(6 -26) 1 1 0 )
(command "insert" "mroads" '(21 -18) 1 1 0 )
(command "insert" "mroads" '(54 -32) 1 1 0 )
(command "insert" "mroads" '(33 -23) 1 1 0 )
(command "insert" "mroads" '(90 -32) 1 1 0 )
(command "insert" "mroads" '(84 -30) 1 1 0 )
(command "insert" "mroads" '(8 -31) 1 1 0 )
(command "insert" "mroads" '(95 -31) 1 1 0 )
(command "insert" "mroads" '(85 -31) 1 1 0 )
(command "insert" "mroads" '(9 -30) 1 1 0 )
(command "insert" "mroads" '(15 -16) 1 1 0 )
(command "insert" "mroads" '(11 -16) 1 1 0 )
(command "insert" "mroads" '(1 -26) 1 1 0 )
(command "insert" "mroads" '(40 -21) 1 1 0 )
(command "insert" "mroads" '(73 -31) 1 1 0 )
(command "insert" "mroads" '(3 -28) 1 1 0 )
(command "insert" "mroads" '(64 -30) 1 1 0 )
(command "insert" "mroads" '(4 -31) 1 1 0 )
(command "insert" "mroads" '(65 -31) 1 1 0 )
(command "insert" "mroads" '(5 -30) 1 1 0 )
(command "insert" "mroads" '(40 -23) 1 1 0 )
(command "insert" "mroads" '(112 -30) 1 1 0 )
(command "insert" "mroads" '(8 -32) 1 1 0 )
(command "insert" "mroads" '(41 -22) 1 1 0 )
(command "insert" "mroads" '(22 -16) 1 1 0 )
(command "insert" "mroads" '(113 -31) 1 1 0 )
(command "insert" "mroads" '(18 -16) 1 1 0 )
(command "insert" "mroads" '(16 -32) 1 1 0 )
(command "insert" "mroads" '(60 -32) 1 1 0 )
(command "insert" "mroads" '(68 -32) 1 1 0 )
(command "insert" "mroads" '(96 -32) 1 1 0 )
(command "insert" "mroads" '(60 -30) 1 1 0 )
(command "insert" "mroads" '(104 -32) 1 1 0 )
(command "insert" "mroads" '(35 -20) 1 1 0 )
(command "insert" "mroads" '(24 -15) 1 1 0 )
(command "insert" "mroads" '(36 -23) 1 1 0 )
(command "insert" "mroads" '(108 -30) 1 1 0 )
(command "insert" "mroads" '(37 -22) 1 1 0 )
(command "insert" "mroads" '(2 -24) 1 1 0 )
(command "insert" "mroads" '(109 -31) 1 1 0 )
(command "insert" "mroads" '(29 -16) 1 1 0 )
(command "insert" "mroads" '(30 -15) 1 1 0 )
(command "insert" "mroads" '(25 -18) 1 1 0 )
(command "insert" "mroads" '(40 -30) 1 1 0 )
(command "insert" "mroads" '(30 -17) 1 1 0 )
(command "insert" "mroads" '(7 -17) 1 1 0 )
(command "insert" "mroads" '(31 -20) 1 1 0 )
(command "insert" "mroads" '(20 -15) 1 1 0 )
(command "insert" "mroads" '(33 -31) 1 1 0 )
(command "insert" "mroads" '(23 -18) 1 1 0 )
(command "insert" "mroads" '(47 -32) 1 1 0 )
(command "insert" "mroads" '(33 -27) 1 1 0 )
(command "insert" "mroads" '(38 -32) 1 1 0 )
(command "insert" "mroads" '(10 -15) 1 1 0 )
(command "insert" "mroads" '(8 -19) 1 1 0 )
(command "insert" "mroads" '(35 -29) 1 1 0 )
(command "insert" "mroads" '(9 -18) 1 1 0 )
(command "insert" "mroads" '(74 -32) 1 1 0 )
(command "insert" "mroads" '(52 -32) 1 1 0 )
(command "insert" "mroads" '(36 -30) 1 1 0 )
(command "insert" "mroads" '(51 -30) 1 1 0 )
(command "insert" "mroads" '(41 -27) 1 1 0 )
(command "insert" "mroads" '(82 -32) 1 1 0 )
(command "insert" "mroads" '(37 -31) 1 1 0 )
(command "insert" "mroads" '(26 -20) 1 1 0 )
(command "insert" "mroads" '(7 -19) 1 1 0 )
(command "insert" "mroads" '(98 -31) 1 1 0 )
(command "insert" "mroads" '(38 -28) 1 1 0 )
(command "insert" "mroads" '(40 -19) 1 1 0 )
(command "insert" "mroads" '(99 -30) 1 1 0 )
(command "insert" "mroads" '(39 -25) 1 1 0 )
(command "insert" "mroads" '(3 -16) 1 1 0 )
(command "insert" "mroads" '(1 -32) 1 1 0 )
(command "insert" "mroads" '(6 -15) 1 1 0 )
(command "insert" "mroads" '(46 -31) 1 1 0 )
(command "insert" "mroads" '(53 -32) 1 1 0 )
(command "insert" "mroads" '(16 -30) 1 1 0 )
(command "insert" "mroads" '(47 -30) 1 1 0 )
(command "insert" "mroads" '(17 -31) 1 1 0 )
(command "insert" "mroads" '(32 -17) 1 1 0 )
(command "insert" "mroads" '(7 -28) 1 1 0 )
(command "insert" "mroads" '(89 -32) 1 1 0 )
(command "insert" "mroads" '(7 -24) 1 1 0 )
(command "insert" "mroads" '(94 -31) 1 1 0 )
(command "insert" "mroads" '(33 -28) 1 1 0 )
(command "insert" "mroads" '(95 -30) 1 1 0 )
(command "insert" "mroads" '(34 -27) 1 1 0 )
(command "insert" "mroads" '(8 -26) 1 1 0 )
(command "insert" "mroads" '(14 -16) 1 1 0 )
(command "insert" "mroads" '(10 -16) 1 1 0 )
(command "insert" "mroads" '(37 -24) 1 1 0 )
(command "insert" "mroads" '(68 -30) 1 1 0 )
(command "insert" "mroads" '(26 -31) 1 1 0 )
(command "insert" "mroads" '(26 -18) 1 1 0 )
(command "insert" "mroads" '(38 -23) 1 1 0 )
(command "insert" "mroads" '(83 -30) 1 1 0 )
(command "insert" "mroads" '(27 -30) 1 1 0 )
(command "insert" "mroads" '(39 -22) 1 1 0 )
(command "insert" "mroads" '(13 -31) 1 1 0 )
(command "insert" "mroads" '(74 -31) 1 1 0 )
(command "insert" "mroads" '(3 -25) 1 1 0 )
(command "insert" "mroads" '(75 -30) 1 1 0 )
(command "insert" "mroads" '(4 -18) 1 1 0 )
(command "insert" "mroads" '(62 -30) 1 1 0 )
(command "insert" "mroads" '(5 -19) 1 1 0 )
(command "insert" "mroads" '(23 -32) 1 1 0 )
(command "insert" "mroads" '(6 -24) 1 1 0 )
(command "insert" "mroads" '(21 -16) 1 1 0 )
(command "insert" "mroads" '(17 -16) 1 1 0 )
(command "insert" "mroads" '(41 -19) 1 1 0 )
(command "insert" "mroads" '(31 -32) 1 1 0 )
(command "insert" "mroads" '(59 -32) 1 1 0 )
(command "insert" "mroads" '(33 -21) 1 1 0 )
(command "insert" "mroads" '(23 -30) 1 1 0 )
(command "insert" "mroads" '(34 -18) 1 1 0 )
(command "insert" "mroads" '(67 -32) 1 1 0 )
(command "insert" "mroads" '(6 -20) 1 1 0 )
(command "insert" "mroads" '(70 -31) 1 1 0 )
(command "insert" "mroads" '(33 -15) 1 1 0 )
(command "insert" "mroads" '(71 -30) 1 1 0 )
(command "insert" "mroads" '(11 -18) 1 1 0 )
(command "insert" "mroads" '(35 -17) 1 1 0 )
(command "insert" "mroads" '(1 -24) 1 1 0 )
(command "insert" "mroads" '(39 -15) 1 1 0 )
(command "insert" "mroads" '(28 -16) 1 1 0 )
(command "insert" "mroads" '(2 -31) 1 1 0 )
(command "insert" "mroads" '(12 -30) 1 1 0 )
(command "insert" "mroads" '(41 -31) 1 1 0 )
(command "insert" "mroads" '(79 -31) 1 1 0 )
(command "insert" "mroads" '(3 -30) 1 1 0 )
(command "insert" "mroads" '(40 -17) 1 1 0 )
(command "insert" "mroads" '(4 -25) 1 1 0 )
(command "insert" "mroads" '(50 -31) 1 1 0 )
(command "insert" "mroads" '(5 -28) 1 1 0 )
(command "insert" "mroads" '(29 -15) 1 1 0 )
(command "insert" "mroads" '(40 -25) 1 1 0 )
(command "insert" "mroads" '(41 -20) 1 1 0 )
(command "insert" "mroads" '(58 -30) 1 1 0 )
(command "insert" "mroads" '(37 -32) 1 1 0 )
(command "insert" "mroads" '(59 -31) 1 1 0 )
(command "insert" "mroads" '(41 -16) 1 1 0 )
(command "insert" "mroads" '(45 -32) 1 1 0 )
(command "insert" "mroads" '(73 -32) 1 1 0 )
(command "insert" "mroads" '(106 -30) 1 1 0 )
(command "insert" "mroads" '(35 -22) 1 1 0 )
(command "insert" "mroads" '(24 -17) 1 1 0 )
(command "insert" "mroads" '(107 -31) 1 1 0 )
(command "insert" "mroads" '(81 -32) 1 1 0 )
(command "insert" "mroads" '(36 -17) 1 1 0 )
(command "insert" "mroads" '(13 -17) 1 1 0 )
(command "insert" "mroads" '(37 -20) 1 1 0 )
(command "insert" "mroads" '(2 -22) 1 1 0 )
(command "insert" "mroads" '(72 -30) 1 1 0 )
(command "insert" "mroads" '(38 -27) 1 1 0 )
(command "insert" "mroads" '(54 -30) 1 1 0 )
(command "insert" "mroads" '(34 -23) 1 1 0 )
(command "insert" "mroads" '(55 -31) 1 1 0 )
(command "insert" "mroads" '(116 -31) 1 1 0 )
(command "insert" "mroads" '(102 -30) 1 1 0 )
(command "insert" "mroads" '(41 -29) 1 1 0 )
(command "insert" "mroads" '(103 -31) 1 1 0 )
(command "insert" "mroads" '(88 -32) 1 1 0 )
(command "insert" "mroads" '(84 -31) 1 1 0 )
(command "insert" "mroads" '(8 -15) 1 1 0 )
(command "insert" "mroads" '(33 -25) 1 1 0 )
(command "insert" "mroads" '(34 -30) 1 1 0 )
(command "insert" "mroads" '(8 -21) 1 1 0 )
(command "insert" "mroads" '(35 -31) 1 1 0 )
(command "insert" "mroads" '(9 -16) 1 1 0 )
(command "insert" "mroads" '(14 -15) 1 1 0 )
(command "insert" "mroads" '(40 -28) 1 1 0 )
(command "insert" "mroads" '(96 -31) 1 1 0 )
(command "insert" "mroads" '(36 -24) 1 1 0 )
(command "insert" "mroads" '(78 -31) 1 1 0 )
(command "insert" "mroads" '(82 -30) 1 1 0 )
(command "insert" "mroads" '(97 -30) 1 1 0 )
(command "insert" "mroads" '(37 -29) 1 1 0 )
(command "insert" "mroads" '(31 -31) 1 1 0 )
(command "insert" "mroads" '(38 -18) 1 1 0 )
(command "insert" "mroads" '(103 -32) 1 1 0 )
(command "insert" "mroads" '(39 -27) 1 1 0 )
(command "insert" "mroads" '(4 -15) 1 1 0 )
(command "insert" "mroads" '(7 -23) 1 1 0 )
(command "insert" "mroads" '(3 -18) 1 1 0 )
(command "insert" "mroads" '(30 -30) 1 1 0 )
(command "insert" "mroads" '(4 -21) 1 1 0 )
(command "insert" "mroads" '(79 -30) 1 1 0 )
(command "insert" "mroads" '(20 -16) 1 1 0 )
(command "insert" "mroads" '(92 -31) 1 1 0 )
(command "insert" "mroads" '(16 -16) 1 1 0 )
(command "insert" "mroads" '(30 -32) 1 1 0 )
(command "insert" "mroads" '(93 -30) 1 1 0 )
(command "insert" "mroads" '(58 -32) 1 1 0 )
(command "insert" "mroads" '(32 -19) 1 1 0 )
(command "insert" "mroads" '(33 -18) 1 1 0 )
(command "insert" "mroads" '(66 -32) 1 1 0 )
(command "insert" "mroads" '(110 -32) 1 1 0 )
(command "insert" "mroads" '(34 -25) 1 1 0 )
(command "insert" "mroads" '(8 -28) 1 1 0 )
(command "insert" "mroads" '(57 -30) 1 1 0 )
(command "insert" "mroads" '(24 -31) 1 1 0 )
(command "insert" "mroads" '(10 -30) 1 1 0 )
(command "insert" "mroads" '(25 -30) 1 1 0 )
(command "insert" "mroads" '(11 -31) 1 1 0 )
(command "insert" "mroads" '(72 -31) 1 1 0 )
(command "insert" "mroads" '(27 -16) 1 1 0 )
(command "insert" "mroads" '(49 -32) 1 1 0 )
(command "insert" "mroads" '(73 -30) 1 1 0 )
(command "insert" "mroads" '(3 -27) 1 1 0 )
(command "insert" "mroads" '(4 -28) 1 1 0 )
(command "insert" "mroads" '(41 -15) 1 1 0 )
(command "insert" "mroads" '(5 -17) 1 1 0 )
(command "insert" "mroads" '(20 -31) 1 1 0 )
(command "insert" "mroads" '(6 -30) 1 1 0 )
(command "insert" "mroads" '(21 -30) 1 1 0 )
(command "insert" "mroads" '(7 -31) 1 1 0 )
(command "insert" "mroads" '(68 -31) 1 1 0 )
(command "insert" "mroads" '(36 -32) 1 1 0 )
(command "insert" "mroads" '(69 -30) 1 1 0 )
(command "insert" "mroads" '(34 -16) 1 1 0 )
(command "insert" "mroads" '(44 -32) 1 1 0 )
(command "insert" "mroads" '(72 -32) 1 1 0 )
(command "insert" "mroads" '(6 -16) 1 1 0 )
(command "insert" "mroads" '(80 -32) 1 1 0 )
(command "insert" "mroads" '(11 -20) 1 1 0 )
(command "insert" "mroads" '(35 -19) 1 1 0 )
(command "insert" "mroads" '(36 -20) 1 1 0 )
(command "insert" "mroads" '(1 -30) 1 1 0 )
(command "insert" "mroads" '(28 -18) 1 1 0 )
(command "insert" "mroads" '(2 -29) 1 1 0 )
(command "insert" "mroads" '(48 -31) 1 1 0 )
(command "insert" "mroads" '(29 -19) 1 1 0 )
(command "insert" "mroads" '(27 -15) 1 1 0 )
(command "insert" "mroads" '(49 -30) 1 1 0 )
(command "insert" "mroads" '(4 -27) 1 1 0 )
(command "insert" "mroads" '(32 -32) 1 1 0 )
(command "insert" "mroads" '(5 -26) 1 1 0 )
(command "insert" "mroads" '(51 -32) 1 1 0 )
(command "insert" "mroads" '(40 -27) 1 1 0 )
(command "insert" "mroads" '(30 -18) 1 1 0 )
(command "insert" "mroads" '(17 -15) 1 1 0 )
(command "insert" "mroads" '(41 -26) 1 1 0 )
(command "insert" "mroads" '(56 -30) 1 1 0 )
(command "insert" "mroads" '(57 -31) 1 1 0 )
(command "insert" "mroads" '(86 -31) 1 1 0 )
(command "insert" "mroads" '(104 -30) 1 1 0 )
(command "insert" "mroads" '(44 -31) 1 1 0 )
(command "insert" "mroads" '(23 -15) 1 1 0 )
(command "insert" "mroads" '(105 -31) 1 1 0 )
(command "insert" "mroads" '(45 -30) 1 1 0 )
(command "insert" "mroads" '(8 -16) 1 1 0 )
(command "insert" "mroads" '(35 -24) 1 1 0 )
(command "insert" "mroads" '(50 -32) 1 1 0 )
(command "insert" "mroads" '(24 -19) 1 1 0 )
(command "insert" "mroads" '(36 -19) 1 1 0 )
(command "insert" "mroads" '(1 -23) 1 1 0 )
(command "insert" "mroads" '(104 -31) 1 1 0 )
(command "insert" "mroads" '(13 -15) 1 1 0 )
(command "insert" "mroads" '(37 -18) 1 1 0 )
(command "insert" "mroads" '(102 -32) 1 1 0 )
(command "insert" "mroads" '(38 -25) 1 1 0 )
(command "insert" "mroads" '(53 -31) 1 1 0 )
(command "insert" "mroads" '(78 -30) 1 1 0 )
(command "insert" "mroads" '(39 -28) 1 1 0 )
(command "insert" "mroads" '(84 -32) 1 1 0 )
(command "insert" "mroads" '(100 -30) 1 1 0 )
(command "insert" "mroads" '(115 -30) 1 1 0 )
(command "insert" "mroads" '(25 -17) 1 1 0 )
(command "insert" "mroads" '(101 -31) 1 1 0 )
(command "insert" "mroads" '(21 -32) 1 1 0 )
(command "insert" "mroads" '(19 -16) 1 1 0 )
(command "insert" "mroads" '(31 -16) 1 1 0 )
(command "insert" "mroads" '(29 -32) 1 1 0 )
(command "insert" "mroads" '(41 -17) 1 1 0 )
(command "insert" "mroads" '(32 -30) 1 1 0 )
(command "insert" "mroads" '(65 -32) 1 1 0 )
(command "insert" "mroads" '(52 -31) 1 1 0 )
(command "insert" "mroads" '(7 -20) 1 1 0 )
(command "insert" "mroads" '(110 -31) 1 1 0 )
(command "insert" "mroads" '(34 -28) 1 1 0 )
(command "insert" "mroads" '(8 -23) 1 1 0 )
(command "insert" "mroads" '(80 -30) 1 1 0 )
(command "insert" "mroads" '(111 -30) 1 1 0 )
(command "insert" "mroads" '(57 -32) 1 1 0 )
(command "insert" "mroads" '(81 -31) 1 1 0 )
(command "insert" "mroads" '(36 -26) 1 1 0 )
(command "insert" "mroads" '(40 -24) 1 1 0 )
(command "insert" "mroads" '(37 -27) 1 1 0 )
(command "insert" "mroads" '(26 -16) 1 1 0 )
(command "insert" "mroads" '(38 -16) 1 1 0 )
(command "insert" "mroads" '(39 -21) 1 1 0 )
(command "insert" "mroads" '(28 -30) 1 1 0 )
(command "insert" "mroads" '(29 -31) 1 1 0 )
(command "insert" "mroads" '(3 -20) 1 1 0 )
(command "insert" "mroads" '(90 -31) 1 1 0 )
(command "insert" "mroads" '(4 -23) 1 1 0 )
(command "insert" "mroads" '(76 -30) 1 1 0 )
(command "insert" "mroads" '(91 -30) 1 1 0 )
(command "insert" "mroads" '(7 -27) 1 1 0 )
(command "insert" "mroads" '(5 -22) 1 1 0 )
(command "insert" "mroads" '(20 -18) 1 1 0 )
(command "insert" "mroads" '(77 -31) 1 1 0 )
(command "insert" "mroads" '(21 -19) 1 1 0 )
(command "insert" "mroads" '(7 -32) 1 1 0 )
(command "insert" "mroads" '(35 -32) 1 1 0 )
(command "insert" "mroads" '(113 -30) 1 1 0 )
(command "insert" "mroads" '(33 -16) 1 1 0 )
(command "insert" "mroads" '(43 -32) 1 1 0 )
(command "insert" "mroads" '(8 -30) 1 1 0 )
(command "insert" "mroads" '(40 -16) 1 1 0 )
(command "insert" "mroads" '(87 -32) 1 1 0 )
(command "insert" "mroads" '(9 -31) 1 1 0 )
(command "insert" "mroads" '(95 -32) 1 1 0 )
(command "insert" "mroads" '(15 -17) 1 1 0 )
(command "insert" "mroads" '(87 -30) 1 1 0 )
(command "insert" "mroads" '(11 -17) 1 1 0 )
(command "insert" "mroads" '(27 -18) 1 1 0 )
(command "insert" "mroads" '(1 -27) 1 1 0 )
(command "insert" "mroads" '(39 -18) 1 1 0 )
(command "insert" "mroads" '(14 -32) 1 1 0 )
(command "insert" "mroads" '(3 -29) 1 1 0 )
(command "insert" "mroads" '(4 -30) 1 1 0 )
(command "insert" "mroads" '(19 -30) 1 1 0 )
(command "layer" "m" "ped" "" )
(command "insert" "ped" '(1 -3) 1 1 0 )
(command "insert" "ped" '(2 -18) 1 1 0 )
(command "insert" "ped" '(2 -8) 1 1 0 )
(command "insert" "ped" '(1 -17) 1 1 0 )
(command "insert" "ped" '(2 -1) 1 1 0 )
(command "insert" "ped" '(1 -15) 1 1 0 )
(command "insert" "ped" '(6 -2) 1 1 0 )
(command "insert" "ped" '(1 -6) 1 1 0 )
(command "insert" "ped" '(2 -12) 1 1 0 )
(command "insert" "ped" '(5 -1) 1 1 0 )
(command "insert" "ped" '(2 -5) 1 1 0 )
(command "insert" "ped" '(1 -11) 1 1 0 )
(command "insert" "ped" '(1 -20) 1 1 0 )
(command "insert" "ped" '(1 -2) 1 1 0 )
(command "insert" "ped" '(2 -19) 1 1 0 )
(command "insert" "ped" '(2 -9) 1 1 0 )
(command "insert" "ped" '(8 -1) 1 1 0 )
(command "insert" "ped" '(1 -16) 1 1 0 )
(command "insert" "ped" '(1 -14) 1 1 0 )
(command "insert" "ped" '(1 -5) 1 1 0 )
(command "insert" "ped" '(2 -13) 1 1 0 )
(command "insert" "ped" '(7 -2) 1 1 0 )
(command "insert" "ped" '(2 -2) 1 1 0 )
(command "insert" "ped" '(1 -10) 1 1 0 )
(command "insert" "ped" '(4 -1) 1 1 0 )
(command "insert" "ped" '(1 -1) 1 1 0 )
(command "insert" "ped" '(2 -16) 1 1 0 )
(command "insert" "ped" '(3 -2) 1 1 0 )
(command "insert" "ped" '(2 -6) 1 1 0 )
(command "insert" "ped" '(8 -2) 1 1 0 )
(command "insert" "ped" '(7 -1) 1 1 0 )
(command "insert" "ped" '(1 -13) 1 1 0 )
(command "insert" "ped" '(2 -20) 1 1 0 )
(command "insert" "ped" '(1 -4) 1 1 0 )
(command "insert" "ped" '(2 -10) 1 1 0 )
(command "insert" "ped" '(1 -19) 1 1 0 )
(command "insert" "ped" '(2 -3) 1 1 0 )
(command "insert" "ped" '(1 -9) 1 1 0 )
(command "insert" "ped" '(4 -2) 1 1 0 )
(command "insert" "ped" '(2 -14) 1 1 0 )
(command "insert" "ped" '(2 -17) 1 1 0 )
(command "insert" "ped" '(2 -7) 1 1 0 )
(command "insert" "ped" '(1 -12) 1 1 0 )
(command "insert" "ped" '(6 -1) 1 1 0 )
(command "insert" "ped" '(3 -1) 1 1 0 )
(command "insert" "ped" '(2 -11) 1 1 0 )
(command "insert" "ped" '(1 -18) 1 1 0 )
(command "insert" "ped" '(1 -8) 1 1 0 )
(command "insert" "ped" '(1 -7) 1 1 0 )
(command "insert" "ped" '(2 -15) 1 1 0 )
(command "insert" "ped" '(5 -2) 1 1 0 )
(command "insert" "ped" '(2 -4) 1 1 0 )
(command "layer" "m" "edge" "" )
(command "insert" "edge" '(2 -39) 1 1 0 )
(command "insert" "edge" '(2 -41) 1 1 0 )
(command "insert" "edge" '(2 -43) 1 1 0 )
(command "insert" "edge" '(1 -46) 1 1 0 )
(command "insert" "edge" '(2 -47) 1 1 0 )
(command "insert" "edge" '(2 -45) 1 1 0 )
(command "insert" "edge" '(1 -39) 1 1 0 )
(command "insert" "edge" '(1 -42) 1 1 0 )
(command "insert" "edge" '(2 -42) 1 1 0 )
(command "insert" "edge" '(1 -43) 1 1 0 )
(command "insert" "edge" '(1 -44) 1 1 0 )
(command "insert" "edge" '(1 -45) 1 1 0 )
(command "insert" "edge" '(1 -40) 1 1 0 )
(command "insert" "edge" '(1 -47) 1 1 0 )
(command "insert" "edge" '(1 -41) 1 1 0 )
(command "insert" "edge" '(2 -40) 1 1 0 )
(command "insert" "edge" '(2 -46) 1 1 0 )
(command "insert" "edge" '(2 -44) 1 1 0 )
(command "layer" "m" "Res" "" )
(command "insert" "Res" '(273 -50) 1 1 0 )
(command "insert" "Res" '(275 -50) 1 1 0 )
(command "insert" "Res" '(275 -48) 1 1 0 )
(command "insert" "Res" '(271 -53) 1 1 0 )
(command "insert" "Res" '(271 -51) 1 1 0 )
(command "insert" "Res" '(274 -48) 1 1 0 )
(command "insert" "Res" '(270 -53) 1 1 0 )
(command "insert" "Res" '(274 -50) 1 1 0 )
(command "insert" "Res" '(273 -48) 1 1 0 )
(command "insert" "Res" '(272 -52) 1 1 0 )
(command "insert" "Res" '(273 -49) 1 1 0 )
(command "insert" "Res" '(271 -52) 1 1 0 )
(command "insert" "Res" '(275 -49) 1 1 0 )
(command "insert" "Res" '(274 -49) 1 1 0 )
(command "insert" "Res" '(270 -51) 1 1 0 )
(command "insert" "Res" '(272 -53) 1 1 0 )
(command "insert" "Res" '(270 -52) 1 1 0 )
(command "insert" "Res" '(272 -51) 1 1 0 )
(command "layer" "m" "ped" "" )
(command "insert" "ped" '(1 -3) 1 1 0 )
(command "insert" "ped" '(2 -18) 1 1 0 )
(command "insert" "ped" '(2 -8) 1 1 0 )
(command "insert" "ped" '(1 -17) 1 1 0 )
(command "insert" "ped" '(2 -1) 1 1 0 )
(command "insert" "ped" '(1 -15) 1 1 0 )
(command "insert" "ped" '(6 -2) 1 1 0 )
(command "insert" "ped" '(1 -6) 1 1 0 )
(command "insert" "ped" '(2 -12) 1 1 0 )
(command "insert" "ped" '(5 -1) 1 1 0 )
(command "insert" "ped" '(2 -5) 1 1 0 )
(command "insert" "ped" '(1 -11) 1 1 0 )
(command "insert" "ped" '(1 -20) 1 1 0 )
(command "insert" "ped" '(1 -2) 1 1 0 )
(command "insert" "ped" '(2 -19) 1 1 0 )
(command "insert" "ped" '(2 -9) 1 1 0 )
(command "insert" "ped" '(8 -1) 1 1 0 )
(command "insert" "ped" '(1 -16) 1 1 0 )
(command "insert" "ped" '(1 -14) 1 1 0 )
(command "insert" "ped" '(1 -5) 1 1 0 )
(command "insert" "ped" '(2 -13) 1 1 0 )
(command "insert" "ped" '(7 -2) 1 1 0 )
(command "insert" "ped" '(2 -2) 1 1 0 )
(command "insert" "ped" '(1 -10) 1 1 0 )
(command "insert" "ped" '(4 -1) 1 1 0 )
(command "insert" "ped" '(1 -1) 1 1 0 )
(command "insert" "ped" '(2 -16) 1 1 0 )
(command "insert" "ped" '(3 -2) 1 1 0 )
(command "insert" "ped" '(2 -6) 1 1 0 )
(command "insert" "ped" '(8 -2) 1 1 0 )
(command "insert" "ped" '(7 -1) 1 1 0 )
(command "insert" "ped" '(1 -13) 1 1 0 )
(command "insert" "ped" '(2 -20) 1 1 0 )
(command "insert" "ped" '(1 -4) 1 1 0 )
(command "insert" "ped" '(2 -10) 1 1 0 )
(command "insert" "ped" '(1 -19) 1 1 0 )
(command "insert" "ped" '(2 -3) 1 1 0 )
(command "insert" "ped" '(1 -9) 1 1 0 )
(command "insert" "ped" '(4 -2) 1 1 0 )
(command "insert" "ped" '(2 -14) 1 1 0 )
(command "insert" "ped" '(2 -17) 1 1 0 )
(command "insert" "ped" '(2 -7) 1 1 0 )
(command "insert" "ped" '(1 -12) 1 1 0 )
(command "insert" "ped" '(6 -1) 1 1 0 )
(command "insert" "ped" '(3 -1) 1 1 0 )
(command "insert" "ped" '(2 -11) 1 1 0 )
(command "insert" "ped" '(1 -18) 1 1 0 )
(command "insert" "ped" '(1 -8) 1 1 0 )
(command "insert" "ped" '(1 -7) 1 1 0 )
(command "insert" "ped" '(2 -15) 1 1 0 )
(command "insert" "ped" '(5 -2) 1 1 0 )
(command "insert" "ped" '(2 -4) 1 1 0 )
(command "layer" "m" "Commmer" "" )
(command "insert" "Commmer" '(32 -1) 1 1 0 )
(command "insert" "Commmer" '(23 -1) 1 1 0 )
(command "insert" "Commmer" '(21 -2) 1 1 0 )
(command "insert" "Commmer" '(16 -2) 1 1 0 )
(command "insert" "Commmer" '(26 -2) 1 1 0 )
(command "insert" "Commmer" '(28 -1) 1 1 0 )
(command "insert" "Commmer" '(25 -1) 1 1 0 )
(command "insert" "Commmer" '(27 -2) 1 1 0 )
(command "insert" "Commmer" '(32 -2) 1 1 0 )
(command "insert" "Commmer" '(18 -1) 1 1 0 )
(command "insert" "Commmer" '(31 -1) 1 1 0 )
(command "insert" "Commmer" '(22 -2) 1 1 0 )
(command "insert" "Commmer" '(21 -1) 1 1 0 )
(command "insert" "Commmer" '(23 -2) 1 1 0 )
(command "insert" "Commmer" '(17 -2) 1 1 0 )
(command "insert" "Commmer" '(28 -2) 1 1 0 )
(command "insert" "Commmer" '(34 -1) 1 1 0 )
(command "insert" "Commmer" '(24 -1) 1 1 0 )
(command "insert" "Commmer" '(33 -2) 1 1 0 )
(command "insert" "Commmer" '(30 -1) 1 1 0 )
(command "insert" "Commmer" '(27 -1) 1 1 0 )
(command "insert" "Commmer" '(18 -2) 1 1 0 )
(command "insert" "Commmer" '(20 -1) 1 1 0 )
(command "insert" "Commmer" '(17 -1) 1 1 0 )
(command "insert" "Commmer" '(19 -2) 1 1 0 )
(command "insert" "Commmer" '(29 -2) 1 1 0 )
(command "insert" "Commmer" '(24 -2) 1 1 0 )
(command "insert" "Commmer" '(34 -2) 1 1 0 )
(command "insert" "Commmer" '(35 -1) 1 1 0 )
(command "insert" "Commmer" '(15 -1) 1 1 0 )
(command "insert" "Commmer" '(33 -1) 1 1 0 )
(command "insert" "Commmer" '(35 -2) 1 1 0 )
(command "insert" "Commmer" '(15 -2) 1 1 0 )
(command "insert" "Commmer" '(26 -1) 1 1 0 )
(command "insert" "Commmer" '(20 -2) 1 1 0 )
(command "insert" "Commmer" '(30 -2) 1 1 0 )
(command "insert" "Commmer" '(16 -1) 1 1 0 )
(command "insert" "Commmer" '(29 -1) 1 1 0 )
(command "insert" "Commmer" '(31 -2) 1 1 0 )
(command "insert" "Commmer" '(25 -2) 1 1 0 )
(command "insert" "Commmer" '(22 -1) 1 1 0 )
(command "insert" "Commmer" '(19 -1) 1 1 0 )
(command "layer" "m" "edge" "" )
(command "insert" "edge" '(44 -2) 1 1 0 )
(command "insert" "edge" '(47 -2) 1 1 0 )
(command "insert" "edge" '(45 -1) 1 1 0 )
(command "insert" "edge" '(40 -1) 1 1 0 )
(command "insert" "edge" '(38 -1) 1 1 0 )
(command "insert" "edge" '(46 -1) 1 1 0 )
(command "insert" "edge" '(43 -1) 1 1 0 )
(command "insert" "edge" '(40 -2) 1 1 0 )
(command "insert" "edge" '(45 -2) 1 1 0 )
(command "insert" "edge" '(36 -1) 1 1 0 )
(command "insert" "edge" '(42 -2) 1 1 0 )
(command "insert" "edge" '(37 -1) 1 1 0 )
(command "insert" "edge" '(44 -1) 1 1 0 )
(command "insert" "edge" '(41 -1) 1 1 0 )
(command "insert" "edge" '(39 -1) 1 1 0 )
(command "insert" "edge" '(37 -2) 1 1 0 )
(command "insert" "edge" '(43 -2) 1 1 0 )
(command "insert" "edge" '(47 -1) 1 1 0 )
(command "insert" "edge" '(41 -2) 1 1 0 )
(command "insert" "edge" '(38 -2) 1 1 0 )
(command "insert" "edge" '(42 -1) 1 1 0 )
(command "insert" "edge" '(36 -2) 1 1 0 )
(command "insert" "edge" '(46 -2) 1 1 0 )
(command "insert" "edge" '(39 -2) 1 1 0 )
(command "layer" "m" "edge" "" )
(command "insert" "edge" '(2 -39) 1 1 0 )
(command "insert" "edge" '(2 -41) 1 1 0 )
(command "insert" "edge" '(2 -43) 1 1 0 )
(command "insert" "edge" '(1 -46) 1 1 0 )
(command "insert" "edge" '(2 -47) 1 1 0 )
(command "insert" "edge" '(1 -40) 1 1 0 )
(command "insert" "edge" '(1 -39) 1 1 0 )
(command "insert" "edge" '(1 -42) 1 1 0 )
(command "insert" "edge" '(2 -42) 1 1 0 )
(command "insert" "edge" '(1 -43) 1 1 0 )
(command "insert" "edge" '(1 -44) 1 1 0 )
(command "insert" "edge" '(1 -45) 1 1 0 )
(command "insert" "edge" '(2 -45) 1 1 0 )
(command "insert" "edge" '(1 -47) 1 1 0 )
(command "insert" "edge" '(2 -44) 1 1 0 )
(command "insert" "edge" '(2 -40) 1 1 0 )
(command "insert" "edge" '(2 -46) 1 1 0 )
(command "insert" "edge" '(1 -41) 1 1 0 )
(command "layer" "m" "Commmer" "" )
(command "insert" "Commmer" '(212 -58) 1 1 0 )
(command "insert" "Commmer" '(212 -57) 1 1 0 )
(command "insert" "Commmer" '(210 -57) 1 1 0 )
(command "insert" "Commmer" '(211 -58) 1 1 0 )
(command "insert" "Commmer" '(210 -59) 1 1 0 )
(command "insert" "Commmer" '(211 -59) 1 1 0 )
(command "insert" "Commmer" '(210 -58) 1 1 0 )
(command "insert" "Commmer" '(211 -57) 1 1 0 )
(command "insert" "Commmer" '(212 -59) 1 1 0 )
(command "layer" "m" "Res" "" )
(command "insert" "Res" '(49 -2) 1 1 0 )
(command "insert" "Res" '(48 -1) 1 1 0 )
(command "insert" "Res" '(50 -2) 1 1 0 )
(command "insert" "Res" '(49 -1) 1 1 0 )
(command "insert" "Res" '(50 -1) 1 1 0 )
(command "insert" "Res" '(48 -2) 1 1 0 )
(command "layer" "m" "Res" "" )
(command "insert" "Res" '(182 -84) 1 1 0 )
(command "insert" "Res" '(181 -84) 1 1 0 )
(command "insert" "Res" '(182 -86) 1 1 0 )
(command "insert" "Res" '(181 -86) 1 1 0 )
(command "insert" "Res" '(180 -86) 1 1 0 )
(command "insert" "Res" '(183 -85) 1 1 0 )
(command "insert" "Res" '(185 -84) 1 1 0 )
(command "insert" "Res" '(185 -85) 1 1 0 )
(command "insert" "Res" '(180 -82) 1 1 0 )
(command "insert" "Res" '(185 -86) 1 1 0 )
(command "insert" "Res" '(182 -85) 1 1 0 )
(command "insert" "Res" '(181 -83) 1 1 0 )
(command "insert" "Res" '(183 -84) 1 1 0 )
(command "insert" "Res" '(181 -85) 1 1 0 )
(command "insert" "Res" '(184 -85) 1 1 0 )
(command "insert" "Res" '(183 -86) 1 1 0 )
(command "insert" "Res" '(180 -84) 1 1 0 )
(command "insert" "Res" '(181 -82) 1 1 0 )
(command "insert" "Res" '(182 -83) 1 1 0 )
(command "insert" "Res" '(180 -85) 1 1 0 )
(command "insert" "Res" '(182 -82) 1 1 0 )
(command "insert" "Res" '(180 -83) 1 1 0 )
(command "insert" "Res" '(184 -86) 1 1 0 )
(command "insert" "Res" '(181 -81) 1 1 0 )
(command "insert" "Res" '(180 -81) 1 1 0 )
(command "insert" "Res" '(182 -81) 1 1 0 )
(command "insert" "Res" '(184 -84) 1 1 0 )
(command "layer" "m" "ped" "" )
(command "insert" "ped" '(1 -3) 1 1 0 )
(command "insert" "ped" '(2 -18) 1 1 0 )
(command "insert" "ped" '(2 -8) 1 1 0 )
(command "insert" "ped" '(1 -17) 1 1 0 )
(command "insert" "ped" '(2 -1) 1 1 0 )
(command "insert" "ped" '(1 -15) 1 1 0 )
(command "insert" "ped" '(6 -2) 1 1 0 )
(command "insert" "ped" '(1 -6) 1 1 0 )
(command "insert" "ped" '(2 -12) 1 1 0 )
(command "insert" "ped" '(5 -1) 1 1 0 )
(command "insert" "ped" '(2 -5) 1 1 0 )
(command "insert" "ped" '(1 -11) 1 1 0 )
(command "insert" "ped" '(7 -2) 1 1 0 )
(command "insert" "ped" '(1 -2) 1 1 0 )
(command "insert" "ped" '(2 -19) 1 1 0 )
(command "insert" "ped" '(2 -9) 1 1 0 )
(command "insert" "ped" '(8 -1) 1 1 0 )
(command "insert" "ped" '(1 -16) 1 1 0 )
(command "insert" "ped" '(1 -14) 1 1 0 )
(command "insert" "ped" '(1 -5) 1 1 0 )
(command "insert" "ped" '(2 -13) 1 1 0 )
(command "insert" "ped" '(1 -20) 1 1 0 )
(command "insert" "ped" '(2 -2) 1 1 0 )
(command "insert" "ped" '(1 -10) 1 1 0 )
(command "insert" "ped" '(4 -1) 1 1 0 )
(command "insert" "ped" '(1 -1) 1 1 0 )
(command "insert" "ped" '(2 -16) 1 1 0 )
(command "insert" "ped" '(3 -2) 1 1 0 )
(command "insert" "ped" '(2 -6) 1 1 0 )
(command "insert" "ped" '(8 -2) 1 1 0 )
(command "insert" "ped" '(7 -1) 1 1 0 )
(command "insert" "ped" '(1 -13) 1 1 0 )
(command "insert" "ped" '(2 -20) 1 1 0 )
(command "insert" "ped" '(1 -4) 1 1 0 )
(command "insert" "ped" '(2 -10) 1 1 0 )
(command "insert" "ped" '(1 -19) 1 1 0 )
(command "insert" "ped" '(2 -3) 1 1 0 )
(command "insert" "ped" '(1 -9) 1 1 0 )
(command "insert" "ped" '(4 -2) 1 1 0 )
(command "insert" "ped" '(2 -14) 1 1 0 )
(command "insert" "ped" '(2 -17) 1 1 0 )
(command "insert" "ped" '(2 -7) 1 1 0 )
(command "insert" "ped" '(1 -12) 1 1 0 )
(command "insert" "ped" '(6 -1) 1 1 0 )
(command "insert" "ped" '(3 -1) 1 1 0 )
(command "insert" "ped" '(2 -11) 1 1 0 )
(command "insert" "ped" '(1 -18) 1 1 0 )
(command "insert" "ped" '(1 -8) 1 1 0 )
(command "insert" "ped" '(1 -7) 1 1 0 )
(command "insert" "ped" '(2 -15) 1 1 0 )
(command "insert" "ped" '(5 -2) 1 1 0 )
(command "insert" "ped" '(2 -4) 1 1 0 )
(command "layer" "m" "ped" "" )
(command "insert" "ped" '(1 -3) 1 1 0 )
(command "insert" "ped" '(2 -18) 1 1 0 )
(command "insert" "ped" '(2 -8) 1 1 0 )
(command "insert" "ped" '(1 -17) 1 1 0 )
(command "insert" "ped" '(2 -1) 1 1 0 )
(command "insert" "ped" '(1 -15) 1 1 0 )
(command "insert" "ped" '(6 -2) 1 1 0 )
(command "insert" "ped" '(1 -6) 1 1 0 )
(command "insert" "ped" '(2 -12) 1 1 0 )
(command "insert" "ped" '(5 -1) 1 1 0 )
(command "insert" "ped" '(2 -5) 1 1 0 )
(command "insert" "ped" '(1 -11) 1 1 0 )
(command "insert" "ped" '(1 -20) 1 1 0 )
(command "insert" "ped" '(1 -2) 1 1 0 )
(command "insert" "ped" '(2 -19) 1 1 0 )
(command "insert" "ped" '(2 -9) 1 1 0 )
(command "insert" "ped" '(8 -1) 1 1 0 )
(command "insert" "ped" '(1 -16) 1 1 0 )
(command "insert" "ped" '(1 -14) 1 1 0 )
(command "insert" "ped" '(1 -5) 1 1 0 )
(command "insert" "ped" '(2 -13) 1 1 0 )
(command "insert" "ped" '(7 -2) 1 1 0 )
(command "insert" "ped" '(2 -2) 1 1 0 )
(command "insert" "ped" '(1 -10) 1 1 0 )
(command "insert" "ped" '(4 -1) 1 1 0 )
(command "insert" "ped" '(1 -1) 1 1 0 )
(command "insert" "ped" '(2 -16) 1 1 0 )
(command "insert" "ped" '(3 -2) 1 1 0 )
(command "insert" "ped" '(2 -6) 1 1 0 )
(command "insert" "ped" '(8 -2) 1 1 0 )
(command "insert" "ped" '(7 -1) 1 1 0 )
(command "insert" "ped" '(1 -13) 1 1 0 )
(command "insert" "ped" '(2 -20) 1 1 0 )
(command "insert" "ped" '(1 -4) 1 1 0 )
(command "insert" "ped" '(2 -10) 1 1 0 )
(command "insert" "ped" '(1 -19) 1 1 0 )
(command "insert" "ped" '(2 -3) 1 1 0 )
(command "insert" "ped" '(1 -9) 1 1 0 )
(command "insert" "ped" '(4 -2) 1 1 0 )
(command "insert" "ped" '(2 -14) 1 1 0 )
(command "insert" "ped" '(2 -17) 1 1 0 )
(command "insert" "ped" '(2 -7) 1 1 0 )
(command "insert" "ped" '(1 -12) 1 1 0 )
(command "insert" "ped" '(6 -1) 1 1 0 )
(command "insert" "ped" '(3 -1) 1 1 0 )
(command "insert" "ped" '(2 -11) 1 1 0 )
(command "insert" "ped" '(1 -18) 1 1 0 )
(command "insert" "ped" '(1 -8) 1 1 0 )
(command "insert" "ped" '(1 -7) 1 1 0 )
(command "insert" "ped" '(2 -15) 1 1 0 )
(command "insert" "ped" '(5 -2) 1 1 0 )
(command "insert" "ped" '(2 -4) 1 1 0 )
(command "layer" "m" "ped" "" )
(command "insert" "ped" '(1 -3) 1 1 0 )
(command "insert" "ped" '(2 -18) 1 1 0 )
(command "insert" "ped" '(2 -8) 1 1 0 )
(command "insert" "ped" '(1 -17) 1 1 0 )
(command "insert" "ped" '(2 -1) 1 1 0 )
(command "insert" "ped" '(1 -15) 1 1 0 )
(command "insert" "ped" '(6 -2) 1 1 0 )
(command "insert" "ped" '(1 -6) 1 1 0 )
(command "insert" "ped" '(2 -12) 1 1 0 )
(command "insert" "ped" '(5 -1) 1 1 0 )
(command "insert" "ped" '(2 -5) 1 1 0 )
(command "insert" "ped" '(1 -11) 1 1 0 )
(command "insert" "ped" '(7 -2) 1 1 0 )
(command "insert" "ped" '(1 -2) 1 1 0 )
(command "insert" "ped" '(2 -19) 1 1 0 )
(command "insert" "ped" '(2 -9) 1 1 0 )
(command "insert" "ped" '(8 -1) 1 1 0 )
(command "insert" "ped" '(1 -16) 1 1 0 )
(command "insert" "ped" '(1 -14) 1 1 0 )
(command "insert" "ped" '(1 -5) 1 1 0 )
(command "insert" "ped" '(2 -13) 1 1 0 )
(command "insert" "ped" '(1 -20) 1 1 0 )
(command "insert" "ped" '(2 -2) 1 1 0 )
(command "insert" "ped" '(1 -10) 1 1 0 )
(command "insert" "ped" '(4 -1) 1 1 0 )
(command "insert" "ped" '(1 -1) 1 1 0 )
(command "insert" "ped" '(2 -16) 1 1 0 )
(command "insert" "ped" '(3 -2) 1 1 0 )
(command "insert" "ped" '(2 -6) 1 1 0 )
(command "insert" "ped" '(8 -2) 1 1 0 )
(command "insert" "ped" '(7 -1) 1 1 0 )
(command "insert" "ped" '(1 -13) 1 1 0 )
(command "insert" "ped" '(2 -20) 1 1 0 )
(command "insert" "ped" '(1 -4) 1 1 0 )
(command "insert" "ped" '(2 -10) 1 1 0 )
(command "insert" "ped" '(1 -19) 1 1 0 )
(command "insert" "ped" '(2 -3) 1 1 0 )
(command "insert" "ped" '(1 -9) 1 1 0 )
(command "insert" "ped" '(4 -2) 1 1 0 )
(command "insert" "ped" '(2 -14) 1 1 0 )
(command "insert" "ped" '(2 -17) 1 1 0 )
(command "insert" "ped" '(2 -7) 1 1 0 )
(command "insert" "ped" '(1 -12) 1 1 0 )
(command "insert" "ped" '(6 -1) 1 1 0 )
(command "insert" "ped" '(3 -1) 1 1 0 )
(command "insert" "ped" '(2 -11) 1 1 0 )
(command "insert" "ped" '(1 -18) 1 1 0 )
(command "insert" "ped" '(1 -8) 1 1 0 )
(command "insert" "ped" '(1 -7) 1 1 0 )
(command "insert" "ped" '(2 -15) 1 1 0 )
(command "insert" "ped" '(5 -2) 1 1 0 )
(command "insert" "ped" '(2 -4) 1 1 0 )
(command "layer" "m" "ped" "" )
(command "insert" "ped" '(1 -3) 1 1 0 )
(command "insert" "ped" '(2 -18) 1 1 0 )
(command "insert" "ped" '(2 -8) 1 1 0 )
(command "insert" "ped" '(1 -17) 1 1 0 )
(command "insert" "ped" '(2 -1) 1 1 0 )
(command "insert" "ped" '(1 -15) 1 1 0 )
(command "insert" "ped" '(6 -2) 1 1 0 )
(command "insert" "ped" '(1 -6) 1 1 0 )
(command "insert" "ped" '(2 -12) 1 1 0 )
(command "insert" "ped" '(5 -1) 1 1 0 )
(command "insert" "ped" '(2 -5) 1 1 0 )
(command "insert" "ped" '(1 -11) 1 1 0 )
(command "insert" "ped" '(7 -2) 1 1 0 )
(command "insert" "ped" '(1 -2) 1 1 0 )
(command "insert" "ped" '(2 -19) 1 1 0 )
(command "insert" "ped" '(2 -9) 1 1 0 )
(command "insert" "ped" '(8 -1) 1 1 0 )
(command "insert" "ped" '(1 -16) 1 1 0 )
(command "insert" "ped" '(1 -14) 1 1 0 )
(command "insert" "ped" '(1 -5) 1 1 0 )
(command "insert" "ped" '(2 -13) 1 1 0 )
(command "insert" "ped" '(1 -20) 1 1 0 )
(command "insert" "ped" '(2 -2) 1 1 0 )
(command "insert" "ped" '(1 -10) 1 1 0 )
(command "insert" "ped" '(4 -1) 1 1 0 )
(command "insert" "ped" '(1 -1) 1 1 0 )
(command "insert" "ped" '(2 -16) 1 1 0 )
(command "insert" "ped" '(3 -2) 1 1 0 )
(command "insert" "ped" '(2 -6) 1 1 0 )
(command "insert" "ped" '(8 -2) 1 1 0 )
(command "insert" "ped" '(7 -1) 1 1 0 )
(command "insert" "ped" '(1 -13) 1 1 0 )
(command "insert" "ped" '(2 -20) 1 1 0 )
(command "insert" "ped" '(1 -4) 1 1 0 )
(command "insert" "ped" '(2 -10) 1 1 0 )
(command "insert" "ped" '(1 -19) 1 1 0 )
(command "insert" "ped" '(2 -3) 1 1 0 )
(command "insert" "ped" '(1 -9) 1 1 0 )
(command "insert" "ped" '(4 -2) 1 1 0 )
(command "insert" "ped" '(2 -14) 1 1 0 )
(command "insert" "ped" '(2 -17) 1 1 0 )
(command "insert" "ped" '(2 -7) 1 1 0 )
(command "insert" "ped" '(1 -12) 1 1 0 )
(command "insert" "ped" '(6 -1) 1 1 0 )
(command "insert" "ped" '(3 -1) 1 1 0 )
(command "insert" "ped" '(2 -11) 1 1 0 )
(command "insert" "ped" '(1 -18) 1 1 0 )
(command "insert" "ped" '(1 -8) 1 1 0 )
(command "insert" "ped" '(1 -7) 1 1 0 )
(command "insert" "ped" '(2 -15) 1 1 0 )
(command "insert" "ped" '(5 -2) 1 1 0 )
(command "insert" "ped" '(2 -4) 1 1 0 )
(command "layer" "m" "edge" "" )
(command "insert" "edge" '(2 -39) 1 1 0 )
(command "insert" "edge" '(2 -41) 1 1 0 )
(command "insert" "edge" '(2 -43) 1 1 0 )
(command "insert" "edge" '(1 -46) 1 1 0 )
(command "insert" "edge" '(1 -42) 1 1 0 )
(command "insert" "edge" '(1 -40) 1 1 0 )
(command "insert" "edge" '(1 -39) 1 1 0 )
(command "insert" "edge" '(2 -47) 1 1 0 )
(command "insert" "edge" '(1 -47) 1 1 0 )
(command "insert" "edge" '(2 -46) 1 1 0 )
(command "insert" "edge" '(1 -44) 1 1 0 )
(command "insert" "edge" '(1 -45) 1 1 0 )
(command "insert" "edge" '(2 -45) 1 1 0 )
(command "insert" "edge" '(2 -42) 1 1 0 )
(command "insert" "edge" '(2 -44) 1 1 0 )
(command "insert" "edge" '(2 -40) 1 1 0 )
(command "insert" "edge" '(1 -43) 1 1 0 )
(command "insert" "edge" '(1 -41) 1 1 0 )
(command "layer" "m" "Commmer" "" )
(command "insert" "Commmer" '(32 -1) 1 1 0 )
(command "insert" "Commmer" '(35 -1) 1 1 0 )
(command "insert" "Commmer" '(21 -2) 1 1 0 )
(command "insert" "Commmer" '(16 -2) 1 1 0 )
(command "insert" "Commmer" '(26 -2) 1 1 0 )
(command "insert" "Commmer" '(28 -1) 1 1 0 )
(command "insert" "Commmer" '(25 -1) 1 1 0 )
(command "insert" "Commmer" '(34 -2) 1 1 0 )
(command "insert" "Commmer" '(27 -2) 1 1 0 )
(command "insert" "Commmer" '(32 -2) 1 1 0 )
(command "insert" "Commmer" '(18 -1) 1 1 0 )
(command "insert" "Commmer" '(31 -1) 1 1 0 )
(command "insert" "Commmer" '(22 -2) 1 1 0 )
(command "insert" "Commmer" '(21 -1) 1 1 0 )
(command "insert" "Commmer" '(23 -2) 1 1 0 )
(command "insert" "Commmer" '(17 -2) 1 1 0 )
(command "insert" "Commmer" '(28 -2) 1 1 0 )
(command "insert" "Commmer" '(34 -1) 1 1 0 )
(command "insert" "Commmer" '(24 -1) 1 1 0 )
(command "insert" "Commmer" '(33 -2) 1 1 0 )
(command "insert" "Commmer" '(30 -1) 1 1 0 )
(command "insert" "Commmer" '(27 -1) 1 1 0 )
(command "insert" "Commmer" '(18 -2) 1 1 0 )
(command "insert" "Commmer" '(20 -1) 1 1 0 )
(command "insert" "Commmer" '(17 -1) 1 1 0 )
(command "insert" "Commmer" '(19 -2) 1 1 0 )
(command "insert" "Commmer" '(29 -2) 1 1 0 )
(command "insert" "Commmer" '(24 -2) 1 1 0 )
(command "insert" "Commmer" '(23 -1) 1 1 0 )
(command "insert" "Commmer" '(15 -1) 1 1 0 )
(command "insert" "Commmer" '(33 -1) 1 1 0 )
(command "insert" "Commmer" '(35 -2) 1 1 0 )
(command "insert" "Commmer" '(26 -1) 1 1 0 )
(command "insert" "Commmer" '(15 -2) 1 1 0 )
(command "insert" "Commmer" '(20 -2) 1 1 0 )
(command "insert" "Commmer" '(30 -2) 1 1 0 )
(command "insert" "Commmer" '(16 -1) 1 1 0 )
(command "insert" "Commmer" '(29 -1) 1 1 0 )
(command "insert" "Commmer" '(31 -2) 1 1 0 )
(command "insert" "Commmer" '(25 -2) 1 1 0 )
(command "insert" "Commmer" '(22 -1) 1 1 0 )
(command "insert" "Commmer" '(19 -1) 1 1 0 )
(command "layer" "m" "Commmer" "" )
(command "insert" "Commmer" '(265 -96) 1 1 0 )
(command "insert" "Commmer" '(265 -97) 1 1 0 )
(command "insert" "Commmer" '(264 -97) 1 1 0 )
(command "insert" "Commmer" '(264 -98) 1 1 0 )
(command "insert" "Commmer" '(264 -96) 1 1 0 )
(command "insert" "Commmer" '(265 -98) 1 1 0 )
(command "insert" "Commmer" '(266 -97) 1 1 0 )
(command "insert" "Commmer" '(266 -96) 1 1 0 )
(command "insert" "Commmer" '(266 -98) 1 1 0 )
(command "layer" "m" "ped" "" )
(command "insert" "ped" '(1 -3) 1 1 0 )
(command "insert" "ped" '(2 -18) 1 1 0 )
(command "insert" "ped" '(2 -8) 1 1 0 )
(command "insert" "ped" '(1 -17) 1 1 0 )
(command "insert" "ped" '(2 -1) 1 1 0 )
(command "insert" "ped" '(1 -15) 1 1 0 )
(command "insert" "ped" '(6 -2) 1 1 0 )
(command "insert" "ped" '(1 -6) 1 1 0 )
(command "insert" "ped" '(2 -12) 1 1 0 )
(command "insert" "ped" '(5 -1) 1 1 0 )
(command "insert" "ped" '(2 -5) 1 1 0 )
(command "insert" "ped" '(1 -11) 1 1 0 )
(command "insert" "ped" '(7 -2) 1 1 0 )
(command "insert" "ped" '(1 -2) 1 1 0 )
(command "insert" "ped" '(2 -19) 1 1 0 )
(command "insert" "ped" '(2 -9) 1 1 0 )
(command "insert" "ped" '(8 -1) 1 1 0 )
(command "insert" "ped" '(1 -16) 1 1 0 )
(command "insert" "ped" '(1 -14) 1 1 0 )
(command "insert" "ped" '(1 -5) 1 1 0 )
(command "insert" "ped" '(2 -13) 1 1 0 )
(command "insert" "ped" '(1 -20) 1 1 0 )
(command "insert" "ped" '(2 -2) 1 1 0 )
(command "insert" "ped" '(1 -10) 1 1 0 )
(command "insert" "ped" '(4 -1) 1 1 0 )
(command "insert" "ped" '(1 -1) 1 1 0 )
(command "insert" "ped" '(2 -16) 1 1 0 )
(command "insert" "ped" '(3 -2) 1 1 0 )
(command "insert" "ped" '(2 -6) 1 1 0 )
(command "insert" "ped" '(8 -2) 1 1 0 )
(command "insert" "ped" '(7 -1) 1 1 0 )
(command "insert" "ped" '(1 -13) 1 1 0 )
(command "insert" "ped" '(2 -20) 1 1 0 )
(command "insert" "ped" '(1 -4) 1 1 0 )
(command "insert" "ped" '(2 -10) 1 1 0 )
(command "insert" "ped" '(1 -19) 1 1 0 )
(command "insert" "ped" '(2 -3) 1 1 0 )
(command "insert" "ped" '(1 -9) 1 1 0 )
(command "insert" "ped" '(4 -2) 1 1 0 )
(command "insert" "ped" '(2 -14) 1 1 0 )
(command "insert" "ped" '(2 -17) 1 1 0 )
(command "insert" "ped" '(2 -7) 1 1 0 )
(command "insert" "ped" '(1 -12) 1 1 0 )
(command "insert" "ped" '(6 -1) 1 1 0 )
(command "insert" "ped" '(3 -1) 1 1 0 )
(command "insert" "ped" '(2 -11) 1 1 0 )
(command "insert" "ped" '(1 -18) 1 1 0 )
(command "insert" "ped" '(1 -8) 1 1 0 )
(command "insert" "ped" '(1 -7) 1 1 0 )
(command "insert" "ped" '(2 -15) 1 1 0 )
(command "insert" "ped" '(5 -2) 1 1 0 )
(command "insert" "ped" '(2 -4) 1 1 0 )
(command "layer" "m" "edge" "" )
(command "insert" "edge" '(45 -1) 1 1 0 )
(command "insert" "edge" '(47 -2) 1 1 0 )
(command "insert" "edge" '(44 -2) 1 1 0 )
(command "insert" "edge" '(41 -2) 1 1 0 )
(command "insert" "edge" '(38 -1) 1 1 0 )
(command "insert" "edge" '(46 -1) 1 1 0 )
(command "insert" "edge" '(43 -1) 1 1 0 )
(command "insert" "edge" '(36 -2) 1 1 0 )
(command "insert" "edge" '(44 -1) 1 1 0 )
(command "insert" "edge" '(37 -2) 1 1 0 )
(command "insert" "edge" '(42 -2) 1 1 0 )
(command "insert" "edge" '(41 -1) 1 1 0 )
(command "insert" "edge" '(45 -2) 1 1 0 )
(command "insert" "edge" '(40 -2) 1 1 0 )
(command "insert" "edge" '(39 -1) 1 1 0 )
(command "insert" "edge" '(36 -1) 1 1 0 )
(command "insert" "edge" '(43 -2) 1 1 0 )
(command "insert" "edge" '(47 -1) 1 1 0 )
(command "insert" "edge" '(40 -1) 1 1 0 )
(command "insert" "edge" '(38 -2) 1 1 0 )
(command "insert" "edge" '(42 -1) 1 1 0 )
(command "insert" "edge" '(37 -1) 1 1 0 )
(command "insert" "edge" '(46 -2) 1 1 0 )
(command "insert" "edge" '(39 -2) 1 1 0 )
(command "layer" "m" "edge" "" )
(command "insert" "edge" '(2 -39) 1 1 0 )
(command "insert" "edge" '(2 -41) 1 1 0 )
(command "insert" "edge" '(1 -46) 1 1 0 )
(command "insert" "edge" '(2 -43) 1 1 0 )
(command "insert" "edge" '(2 -47) 1 1 0 )
(command "insert" "edge" '(1 -40) 1 1 0 )
(command "insert" "edge" '(1 -39) 1 1 0 )
(command "insert" "edge" '(1 -42) 1 1 0 )
(command "insert" "edge" '(2 -42) 1 1 0 )
(command "insert" "edge" '(1 -43) 1 1 0 )
(command "insert" "edge" '(1 -44) 1 1 0 )
(command "insert" "edge" '(1 -45) 1 1 0 )
(command "insert" "edge" '(2 -45) 1 1 0 )
(command "insert" "edge" '(1 -47) 1 1 0 )
(command "insert" "edge" '(2 -44) 1 1 0 )
(command "insert" "edge" '(2 -40) 1 1 0 )
(command "insert" "edge" '(2 -46) 1 1 0 )
(command "insert" "edge" '(1 -41) 1 1 0 )
(command "layer" "m" "Commmer" "" )
(command "insert" "Commmer" '(295 -96) 1 1 0 )
(command "insert" "Commmer" '(296 -98) 1 1 0 )
(command "insert" "Commmer" '(295 -97) 1 1 0 )
(command "insert" "Commmer" '(296 -97) 1 1 0 )
(command "insert" "Commmer" '(294 -97) 1 1 0 )
(command "insert" "Commmer" '(296 -96) 1 1 0 )
(command "insert" "Commmer" '(294 -96) 1 1 0 )
(command "insert" "Commmer" '(294 -98) 1 1 0 )
(command "insert" "Commmer" '(295 -98) 1 1 0 )
(command "layer" "m" "ped" "" )
(command "insert" "ped" '(1 -3) 1 1 0 )
(command "insert" "ped" '(2 -18) 1 1 0 )
(command "insert" "ped" '(2 -8) 1 1 0 )
(command "insert" "ped" '(1 -17) 1 1 0 )
(command "insert" "ped" '(2 -1) 1 1 0 )
(command "insert" "ped" '(1 -15) 1 1 0 )
(command "insert" "ped" '(6 -2) 1 1 0 )
(command "insert" "ped" '(1 -6) 1 1 0 )
(command "insert" "ped" '(2 -12) 1 1 0 )
(command "insert" "ped" '(5 -1) 1 1 0 )
(command "insert" "ped" '(2 -5) 1 1 0 )
(command "insert" "ped" '(1 -11) 1 1 0 )
(command "insert" "ped" '(1 -20) 1 1 0 )
(command "insert" "ped" '(1 -2) 1 1 0 )
(command "insert" "ped" '(2 -19) 1 1 0 )
(command "insert" "ped" '(2 -9) 1 1 0 )
(command "insert" "ped" '(8 -1) 1 1 0 )
(command "insert" "ped" '(1 -16) 1 1 0 )
(command "insert" "ped" '(1 -14) 1 1 0 )
(command "insert" "ped" '(1 -5) 1 1 0 )
(command "insert" "ped" '(2 -13) 1 1 0 )
(command "insert" "ped" '(7 -2) 1 1 0 )
(command "insert" "ped" '(2 -2) 1 1 0 )
(command "insert" "ped" '(1 -10) 1 1 0 )
(command "insert" "ped" '(4 -1) 1 1 0 )
(command "insert" "ped" '(1 -1) 1 1 0 )
(command "insert" "ped" '(2 -16) 1 1 0 )
(command "insert" "ped" '(3 -2) 1 1 0 )
(command "insert" "ped" '(2 -6) 1 1 0 )
(command "insert" "ped" '(8 -2) 1 1 0 )
(command "insert" "ped" '(7 -1) 1 1 0 )
(command "insert" "ped" '(1 -13) 1 1 0 )
(command "insert" "ped" '(2 -20) 1 1 0 )
(command "insert" "ped" '(1 -4) 1 1 0 )
(command "insert" "ped" '(2 -10) 1 1 0 )
(command "insert" "ped" '(1 -19) 1 1 0 )
(command "insert" "ped" '(2 -3) 1 1 0 )
(command "insert" "ped" '(1 -9) 1 1 0 )
(command "insert" "ped" '(4 -2) 1 1 0 )
(command "insert" "ped" '(2 -14) 1 1 0 )
(command "insert" "ped" '(2 -17) 1 1 0 )
(command "insert" "ped" '(2 -7) 1 1 0 )
(command "insert" "ped" '(1 -12) 1 1 0 )
(command "insert" "ped" '(6 -1) 1 1 0 )
(command "insert" "ped" '(3 -1) 1 1 0 )
(command "insert" "ped" '(2 -11) 1 1 0 )
(command "insert" "ped" '(1 -18) 1 1 0 )
(command "insert" "ped" '(1 -8) 1 1 0 )
(command "insert" "ped" '(1 -7) 1 1 0 )
(command "insert" "ped" '(2 -15) 1 1 0 )
(command "insert" "ped" '(5 -2) 1 1 0 )
(command "insert" "ped" '(2 -4) 1 1 0 )
(command "layer" "m" "edge" "" )
(command "insert" "edge" '(44 -2) 1 1 0 )
(command "insert" "edge" '(47 -2) 1 1 0 )
(command "insert" "edge" '(45 -1) 1 1 0 )
(command "insert" "edge" '(41 -2) 1 1 0 )
(command "insert" "edge" '(38 -1) 1 1 0 )
(command "insert" "edge" '(46 -1) 1 1 0 )
(command "insert" "edge" '(43 -1) 1 1 0 )
(command "insert" "edge" '(36 -2) 1 1 0 )
(command "insert" "edge" '(45 -2) 1 1 0 )
(command "insert" "edge" '(36 -1) 1 1 0 )
(command "insert" "edge" '(42 -2) 1 1 0 )
(command "insert" "edge" '(41 -1) 1 1 0 )
(command "insert" "edge" '(44 -1) 1 1 0 )
(command "insert" "edge" '(40 -2) 1 1 0 )
(command "insert" "edge" '(39 -1) 1 1 0 )
(command "insert" "edge" '(37 -2) 1 1 0 )
(command "insert" "edge" '(43 -2) 1 1 0 )
(command "insert" "edge" '(47 -1) 1 1 0 )
(command "insert" "edge" '(40 -1) 1 1 0 )
(command "insert" "edge" '(38 -2) 1 1 0 )
(command "insert" "edge" '(42 -1) 1 1 0 )
(command "insert" "edge" '(37 -1) 1 1 0 )
(command "insert" "edge" '(46 -2) 1 1 0 )
(command "insert" "edge" '(39 -2) 1 1 0 )
(command "layer" "m" "edge" "" )
(command "insert" "edge" '(2 -39) 1 1 0 )
(command "insert" "edge" '(2 -41) 1 1 0 )
(command "insert" "edge" '(1 -46) 1 1 0 )
(command "insert" "edge" '(2 -43) 1 1 0 )
(command "insert" "edge" '(2 -47) 1 1 0 )
(command "insert" "edge" '(1 -40) 1 1 0 )
(command "insert" "edge" '(1 -39) 1 1 0 )
(command "insert" "edge" '(1 -42) 1 1 0 )
(command "insert" "edge" '(2 -42) 1 1 0 )
(command "insert" "edge" '(1 -43) 1 1 0 )
(command "insert" "edge" '(1 -44) 1 1 0 )
(command "insert" "edge" '(1 -45) 1 1 0 )
(command "insert" "edge" '(2 -45) 1 1 0 )
(command "insert" "edge" '(1 -47) 1 1 0 )
(command "insert" "edge" '(2 -44) 1 1 0 )
(command "insert" "edge" '(2 -40) 1 1 0 )
(command "insert" "edge" '(2 -46) 1 1 0 )
(command "insert" "edge" '(1 -41) 1 1 0 )
(command "layer" "m" "Commmer" "" )
(command "insert" "Commmer" '(51 -2) 1 1 0 )
(command "insert" "Commmer" '(52 -2) 1 1 0 )
(command "insert" "Commmer" '(53 -1) 1 1 0 )
(command "insert" "Commmer" '(51 -1) 1 1 0 )
(command "insert" "Commmer" '(52 -1) 1 1 0 )
(command "insert" "Commmer" '(53 -2) 1 1 0 )
(command "layer" "m" "ped" "" )
(command "insert" "ped" '(4 -41) 1 1 0 )
(command "insert" "ped" '(30 -41) 1 1 0 )
(command "insert" "ped" '(4 -36) 1 1 0 )
(command "insert" "ped" '(28 -41) 1 1 0 )
(command "insert" "ped" '(9 -41) 1 1 0 )
(command "insert" "ped" '(33 -36) 1 1 0 )
(command "insert" "ped" '(23 -41) 1 1 0 )
(command "insert" "ped" '(6 -35) 1 1 0 )
(command "insert" "ped" '(1 -36) 1 1 0 )
(command "insert" "ped" '(12 -40) 1 1 0 )
(command "insert" "ped" '(19 -40) 1 1 0 )
(command "insert" "ped" '(8 -41) 1 1 0 )
(command "insert" "ped" '(32 -38) 1 1 0 )
(command "insert" "ped" '(22 -41) 1 1 0 )
(command "insert" "ped" '(9 -36) 1 1 0 )
(command "insert" "ped" '(32 -41) 1 1 0 )
(command "insert" "ped" '(35 -36) 1 1 0 )
(command "insert" "ped" '(34 -36) 1 1 0 )
(command "insert" "ped" '(17 -36) 1 1 0 )
(command "insert" "ped" '(7 -41) 1 1 0 )
(command "insert" "ped" '(17 -41) 1 1 0 )
(command "insert" "ped" '(15 -34) 1 1 0 )
(command "insert" "ped" '(16 -38) 1 1 0 )
(command "insert" "ped" '(19 -39) 1 1 0 )
(command "insert" "ped" '(25 -38) 1 1 0 )
(command "insert" "ped" '(6 -41) 1 1 0 )
(command "insert" "ped" '(21 -40) 1 1 0 )
(command "insert" "ped" '(3 -40) 1 1 0 )
(command "insert" "ped" '(27 -39) 1 1 0 )
(command "insert" "ped" '(26 -37) 1 1 0 )
(command "insert" "ped" '(22 -39) 1 1 0 )
(command "insert" "ped" '(21 -37) 1 1 0 )
(command "insert" "ped" '(27 -40) 1 1 0 )
(command "insert" "ped" '(8 -38) 1 1 0 )
(command "insert" "ped" '(23 -38) 1 1 0 )
(command "insert" "ped" '(30 -39) 1 1 0 )
(command "insert" "ped" '(10 -41) 1 1 0 )
(command "insert" "ped" '(9 -39) 1 1 0 )
(command "insert" "ped" '(7 -35) 1 1 0 )
(command "insert" "ped" '(31 -38) 1 1 0 )
(command "insert" "ped" '(11 -36) 1 1 0 )
(command "insert" "ped" '(10 -36) 1 1 0 )
(command "insert" "ped" '(17 -39) 1 1 0 )
(command "insert" "ped" '(16 -41) 1 1 0 )
(command "insert" "ped" '(12 -39) 1 1 0 )
(command "insert" "ped" '(11 -41) 1 1 0 )
(command "insert" "ped" '(18 -36) 1 1 0 )
(command "insert" "ped" '(15 -33) 1 1 0 )
(command "insert" "ped" '(1 -38) 1 1 0 )
(command "insert" "ped" '(20 -37) 1 1 0 )
(command "insert" "ped" '(3 -39) 1 1 0 )
(command "insert" "ped" '(2 -37) 1 1 0 )
(command "insert" "ped" '(26 -38) 1 1 0 )
(command "insert" "ped" '(5 -40) 1 1 0 )
(command "insert" "ped" '(8 -35) 1 1 0 )
(command "insert" "ped" '(23 -37) 1 1 0 )
(command "insert" "ped" '(6 -39) 1 1 0 )
(command "insert" "ped" '(5 -37) 1 1 0 )
(command "insert" "ped" '(29 -40) 1 1 0 )
(command "insert" "ped" '(7 -38) 1 1 0 )
(command "insert" "ped" '(31 -37) 1 1 0 )
(command "insert" "ped" '(17 -34) 1 1 0 )
(command "insert" "ped" '(18 -41) 1 1 0 )
(command "insert" "ped" '(15 -36) 1 1 0 )
(command "insert" "ped" '(13 -41) 1 1 0 )
(command "insert" "ped" '(24 -36) 1 1 0 )
(command "insert" "ped" '(6 -40) 1 1 0 )
(command "insert" "ped" '(2 -38) 1 1 0 )
(command "insert" "ped" '(4 -37) 1 1 0 )
(command "insert" "ped" '(9 -40) 1 1 0 )
(command "insert" "ped" '(23 -40) 1 1 0 )
(command "insert" "ped" '(7 -37) 1 1 0 )
(command "insert" "ped" '(12 -41) 1 1 0 )
(command "insert" "ped" '(32 -39) 1 1 0 )
(command "insert" "ped" '(33 -38) 1 1 0 )
(command "insert" "ped" '(34 -37) 1 1 0 )
(command "insert" "ped" '(7 -40) 1 1 0 )
(command "insert" "ped" '(14 -40) 1 1 0 )
(command "insert" "ped" '(17 -40) 1 1 0 )
(command "insert" "ped" '(24 -40) 1 1 0 )
(command "insert" "ped" '(19 -38) 1 1 0 )
(command "insert" "ped" '(25 -37) 1 1 0 )
(command "insert" "ped" '(7 -33) 1 1 0 )
(command "insert" "ped" '(22 -36) 1 1 0 )
(command "insert" "ped" '(21 -36) 1 1 0 )
(command "insert" "ped" '(8 -39) 1 1 0 )
(command "insert" "ped" '(32 -36) 1 1 0 )
(command "insert" "ped" '(30 -36) 1 1 0 )
(command "insert" "ped" '(9 -38) 1 1 0 )
(command "insert" "ped" '(16 -39) 1 1 0 )
(command "insert" "ped" '(11 -39) 1 1 0 )
(command "insert" "ped" '(10 -37) 1 1 0 )
(command "insert" "ped" '(34 -38) 1 1 0 )
(command "insert" "ped" '(17 -38) 1 1 0 )
(command "insert" "ped" '(11 -40) 1 1 0 )
(command "insert" "ped" '(18 -37) 1 1 0 )
(command "insert" "ped" '(24 -37) 1 1 0 )
(command "insert" "ped" '(19 -37) 1 1 0 )
(command "insert" "ped" '(26 -40) 1 1 0 )
(command "insert" "ped" '(20 -38) 1 1 0 )
(command "insert" "ped" '(3 -38) 1 1 0 )
(command "insert" "ped" '(26 -39) 1 1 0 )
(command "insert" "ped" '(31 -40) 1 1 0 )
(command "insert" "ped" '(21 -39) 1 1 0 )
(command "insert" "ped" '(8 -36) 1 1 0 )
(command "insert" "ped" '(23 -36) 1 1 0 )
(command "insert" "ped" '(6 -36) 1 1 0 )
(command "insert" "ped" '(5 -36) 1 1 0 )
(command "insert" "ped" '(29 -39) 1 1 0 )
(command "insert" "ped" '(16 -36) 1 1 0 )
(command "insert" "ped" '(31 -36) 1 1 0 )
(command "insert" "ped" '(10 -38) 1 1 0 )
(command "insert" "ped" '(17 -33) 1 1 0 )
(command "insert" "ped" '(18 -38) 1 1 0 )
(command "insert" "ped" '(15 -39) 1 1 0 )
(command "insert" "ped" '(13 -40) 1 1 0 )
(command "insert" "ped" '(20 -40) 1 1 0 )
(command "insert" "ped" '(16 -35) 1 1 0 )
(command "insert" "ped" '(3 -37) 1 1 0 )
(command "insert" "ped" '(4 -38) 1 1 0 )
(command "insert" "ped" '(8 -33) 1 1 0 )
(command "insert" "ped" '(6 -33) 1 1 0 )
(command "insert" "ped" '(5 -39) 1 1 0 )
(command "insert" "ped" '(7 -36) 1 1 0 )
(command "insert" "ped" '(15 -41) 1 1 0 )
(command "insert" "ped" '(25 -41) 1 1 0 )
(command "insert" "ped" '(4 -40) 1 1 0 )
(command "insert" "ped" '(6 -38) 1 1 0 )
(command "insert" "ped" '(30 -40) 1 1 0 )
(command "insert" "ped" '(28 -40) 1 1 0 )
(command "insert" "ped" '(33 -37) 1 1 0 )
(command "insert" "ped" '(6 -34) 1 1 0 )
(command "insert" "ped" '(35 -38) 1 1 0 )
(command "insert" "ped" '(14 -41) 1 1 0 )
(command "insert" "ped" '(24 -41) 1 1 0 )
(command "insert" "ped" '(19 -41) 1 1 0 )
(command "insert" "ped" '(25 -36) 1 1 0 )
(command "insert" "ped" '(22 -37) 1 1 0 )
(command "insert" "ped" '(7 -39) 1 1 0 )
(command "insert" "ped" '(8 -40) 1 1 0 )
(command "insert" "ped" '(32 -37) 1 1 0 )
(command "insert" "ped" '(22 -40) 1 1 0 )
(command "insert" "ped" '(30 -37) 1 1 0 )
(command "insert" "ped" '(9 -37) 1 1 0 )
(command "insert" "ped" '(32 -40) 1 1 0 )
(command "insert" "ped" '(1 -37) 1 1 0 )
(command "insert" "ped" '(11 -38) 1 1 0 )
(command "insert" "ped" '(35 -37) 1 1 0 )
(command "insert" "ped" '(17 -37) 1 1 0 )
(command "insert" "ped" '(24 -39) 1 1 0 )
(command "insert" "ped" '(15 -35) 1 1 0 )
(command "insert" "ped" '(19 -36) 1 1 0 )
(command "insert" "ped" '(26 -41) 1 1 0 )
(command "insert" "ped" '(25 -39) 1 1 0 )
(command "insert" "ped" '(16 -33) 1 1 0 )
(command "insert" "ped" '(21 -41) 1 1 0 )
(command "insert" "ped" '(20 -39) 1 1 0 )
(command "insert" "ped" '(3 -41) 1 1 0 )
(command "insert" "ped" '(26 -36) 1 1 0 )
(command "insert" "ped" '(22 -38) 1 1 0 )
(command "insert" "ped" '(21 -38) 1 1 0 )
(command "insert" "ped" '(28 -39) 1 1 0 )
(command "insert" "ped" '(27 -41) 1 1 0 )
(command "insert" "ped" '(8 -37) 1 1 0 )
(command "insert" "ped" '(23 -39) 1 1 0 )
(command "insert" "ped" '(6 -37) 1 1 0 )
(command "insert" "ped" '(30 -38) 1 1 0 )
(command "insert" "ped" '(10 -40) 1 1 0 )
(command "insert" "ped" '(16 -37) 1 1 0 )
(command "insert" "ped" '(31 -39) 1 1 0 )
(command "insert" "ped" '(11 -37) 1 1 0 )
(command "insert" "ped" '(10 -39) 1 1 0 )
(command "insert" "ped" '(16 -40) 1 1 0 )
(command "insert" "ped" '(14 -39) 1 1 0 )
(command "insert" "ped" '(18 -39) 1 1 0 )
(command "insert" "ped" '(15 -38) 1 1 0 )
(command "insert" "ped" '(13 -39) 1 1 0 )
(command "insert" "ped" '(20 -41) 1 1 0 )
(command "insert" "ped" '(20 -36) 1 1 0 )
(command "insert" "ped" '(3 -36) 1 1 0 )
(command "insert" "ped" '(2 -36) 1 1 0 )
(command "insert" "ped" '(5 -41) 1 1 0 )
(command "insert" "ped" '(4 -39) 1 1 0 )
(command "insert" "ped" '(8 -34) 1 1 0 )
(command "insert" "ped" '(31 -41) 1 1 0 )
(command "insert" "ped" '(5 -38) 1 1 0 )
(command "insert" "ped" '(29 -41) 1 1 0 )
(command "insert" "ped" '(16 -34) 1 1 0 )
(command "insert" "ped" '(17 -35) 1 1 0 )
(command "insert" "ped" '(15 -40) 1 1 0 )
(command "insert" "ped" '(7 -34) 1 1 0 )
(command "insert" "ped" '(24 -38) 1 1 0 )
(command "insert" "ped" '(18 -40) 1 1 0 )
(command "insert" "ped" '(25 -40) 1 1 0 )
(command "insert" "ped" '(15 -37) 1 1 0 )
(command "layer" "m" "mroads" "" )
(command "insert" "mroads" '(5 -31) 1 1 0 )
(command "insert" "mroads" '(66 -31) 1 1 0 )
(command "insert" "mroads" '(6 -28) 1 1 0 )
(command "insert" "mroads" '(67 -30) 1 1 0 )
(command "insert" "mroads" '(7 -25) 1 1 0 )
(command "insert" "mroads" '(22 -19) 1 1 0 )
(command "insert" "mroads" '(18 -19) 1 1 0 )
(command "insert" "mroads" '(38 -21) 1 1 0 )
(command "insert" "mroads" '(114 -31) 1 1 0 )
(command "insert" "mroads" '(13 -32) 1 1 0 )
(command "insert" "mroads" '(35 -15) 1 1 0 )
(command "insert" "mroads" '(14 -31) 1 1 0 )
(command "insert" "mroads" '(15 -30) 1 1 0 )
(command "insert" "mroads" '(35 -21) 1 1 0 )
(command "insert" "mroads" '(12 -17) 1 1 0 )
(command "insert" "mroads" '(36 -22) 1 1 0 )
(command "insert" "mroads" '(1 -28) 1 1 0 )
(command "insert" "mroads" '(25 -15) 1 1 0 )
(command "insert" "mroads" '(39 -16) 1 1 0 )
(command "insert" "mroads" '(63 -30) 1 1 0 )
(command "insert" "mroads" '(37 -23) 1 1 0 )
(command "insert" "mroads" '(2 -27) 1 1 0 )
(command "insert" "mroads" '(109 -32) 1 1 0 )
(command "insert" "mroads" '(29 -17) 1 1 0 )
(command "insert" "mroads" '(31 -15) 1 1 0 )
(command "insert" "mroads" '(5 -24) 1 1 0 )
(command "insert" "mroads" '(20 -32) 1 1 0 )
(command "insert" "mroads" '(6 -23) 1 1 0 )
(command "insert" "mroads" '(30 -16) 1 1 0 )
(command "insert" "mroads" '(28 -32) 1 1 0 )
(command "insert" "mroads" '(7 -22) 1 1 0 )
(command "insert" "mroads" '(41 -23) 1 1 0 )
(command "insert" "mroads" '(42 -31) 1 1 0 )
(command "insert" "mroads" '(23 -19) 1 1 0 )
(command "insert" "mroads" '(21 -15) 1 1 0 )
(command "insert" "mroads" '(43 -30) 1 1 0 )
(command "insert" "mroads" '(116 -32) 1 1 0 )
(command "insert" "mroads" '(8 -18) 1 1 0 )
(command "insert" "mroads" '(11 -15) 1 1 0 )
(command "insert" "mroads" '(35 -26) 1 1 0 )
(command "insert" "mroads" '(9 -19) 1 1 0 )
(command "insert" "mroads" '(36 -29) 1 1 0 )
(command "insert" "mroads" '(1 -21) 1 1 0 )
(command "insert" "mroads" '(25 -16) 1 1 0 )
(command "insert" "mroads" '(29 -20) 1 1 0 )
(command "insert" "mroads" '(37 -16) 1 1 0 )
(command "insert" "mroads" '(98 -30) 1 1 0 )
(command "insert" "mroads" '(38 -31) 1 1 0 )
(command "insert" "mroads" '(99 -31) 1 1 0 )
(command "insert" "mroads" '(39 -30) 1 1 0 )
(command "insert" "mroads" '(3 -17) 1 1 0 )
(command "insert" "mroads" '(19 -18) 1 1 0 )
(command "insert" "mroads" '(7 -15) 1 1 0 )
(command "insert" "mroads" '(31 -18) 1 1 0 )
(command "insert" "mroads" '(46 -30) 1 1 0 )
(command "insert" "mroads" '(6 -32) 1 1 0 )
(command "insert" "mroads" '(34 -32) 1 1 0 )
(command "insert" "mroads" '(32 -16) 1 1 0 )
(command "insert" "mroads" '(94 -30) 1 1 0 )
(command "insert" "mroads" '(18 -31) 1 1 0 )
(command "insert" "mroads" '(42 -32) 1 1 0 )
(command "insert" "mroads" '(86 -32) 1 1 0 )
(command "insert" "mroads" '(34 -26) 1 1 0 )
(command "insert" "mroads" '(8 -25) 1 1 0 )
(command "insert" "mroads" '(94 -32) 1 1 0 )
(command "insert" "mroads" '(9 -20) 1 1 0 )
(command "insert" "mroads" '(10 -19) 1 1 0 )
(command "insert" "mroads" '(37 -25) 1 1 0 )
(command "insert" "mroads" '(26 -30) 1 1 0 )
(command "insert" "mroads" '(7 -18) 1 1 0 )
(command "insert" "mroads" '(38 -22) 1 1 0 )
(command "insert" "mroads" '(27 -31) 1 1 0 )
(command "insert" "mroads" '(40 -20) 1 1 0 )
(command "insert" "mroads" '(39 -23) 1 1 0 )
(command "insert" "mroads" '(88 -31) 1 1 0 )
(command "insert" "mroads" '(74 -30) 1 1 0 )
(command "insert" "mroads" '(89 -30) 1 1 0 )
(command "insert" "mroads" '(3 -22) 1 1 0 )
(command "insert" "mroads" '(75 -31) 1 1 0 )
(command "insert" "mroads" '(4 -17) 1 1 0 )
(command "insert" "mroads" '(5 -20) 1 1 0 )
(command "insert" "mroads" '(6 -27) 1 1 0 )
(command "insert" "mroads" '(21 -17) 1 1 0 )
(command "insert" "mroads" '(17 -17) 1 1 0 )
(command "insert" "mroads" '(22 -30) 1 1 0 )
(command "insert" "mroads" '(33 -22) 1 1 0 )
(command "insert" "mroads" '(23 -31) 1 1 0 )
(command "insert" "mroads" '(12 -32) 1 1 0 )
(command "insert" "mroads" '(34 -21) 1 1 0 )
(command "insert" "mroads" '(70 -30) 1 1 0 )
(command "insert" "mroads" '(85 -30) 1 1 0 )
(command "insert" "mroads" '(48 -32) 1 1 0 )
(command "insert" "mroads" '(71 -31) 1 1 0 )
(command "insert" "mroads" '(34 -15) 1 1 0 )
(command "insert" "mroads" '(11 -19) 1 1 0 )
(command "insert" "mroads" '(100 -32) 1 1 0 )
(command "insert" "mroads" '(27 -20) 1 1 0 )
(command "insert" "mroads" '(1 -25) 1 1 0 )
(command "insert" "mroads" '(108 -32) 1 1 0 )
(command "insert" "mroads" '(2 -30) 1 1 0 )
(command "insert" "mroads" '(3 -31) 1 1 0 )
(command "insert" "mroads" '(64 -31) 1 1 0 )
(command "insert" "mroads" '(4 -24) 1 1 0 )
(command "insert" "mroads" '(19 -32) 1 1 0 )
(command "insert" "mroads" '(62 -31) 1 1 0 )
(command "insert" "mroads" '(50 -30) 1 1 0 )
(command "insert" "mroads" '(65 -30) 1 1 0 )
(command "insert" "mroads" '(5 -29) 1 1 0 )
(command "insert" "mroads" '(27 -32) 1 1 0 )
(command "insert" "mroads" '(6 -18) 1 1 0 )
(command "insert" "mroads" '(101 -32) 1 1 0 )
(command "insert" "mroads" '(112 -31) 1 1 0 )
(command "insert" "mroads" '(41 -21) 1 1 0 )
(command "insert" "mroads" '(22 -17) 1 1 0 )
(command "insert" "mroads" '(79 -32) 1 1 0 )
(command "insert" "mroads" '(18 -17) 1 1 0 )
(command "insert" "mroads" '(23 -20) 1 1 0 )
(command "insert" "mroads" '(40 -31) 1 1 0 )
(command "insert" "mroads" '(115 -32) 1 1 0 )
(command "insert" "mroads" '(60 -31) 1 1 0 )
(command "insert" "mroads" '(61 -30) 1 1 0 )
(command "insert" "mroads" '(35 -23) 1 1 0 )
(command "insert" "mroads" '(24 -16) 1 1 0 )
(command "insert" "mroads" '(36 -16) 1 1 0 )
(command "insert" "mroads" '(108 -31) 1 1 0 )
(command "insert" "mroads" '(37 -21) 1 1 0 )
(command "insert" "mroads" '(2 -25) 1 1 0 )
(command "insert" "mroads" '(109 -30) 1 1 0 )
(command "insert" "mroads" '(7 -16) 1 1 0 )
(command "insert" "mroads" '(38 -26) 1 1 0 )
(command "insert" "mroads" '(40 -18) 1 1 0 )
(command "insert" "mroads" '(114 -32) 1 1 0 )
(command "insert" "mroads" '(116 -30) 1 1 0 )
(command "insert" "mroads" '(6 -21) 1 1 0 )
(command "insert" "mroads" '(111 -31) 1 1 0 )
(command "insert" "mroads" '(19 -15) 1 1 0 )
(command "insert" "mroads" '(41 -30) 1 1 0 )
(command "insert" "mroads" '(5 -32) 1 1 0 )
(command "insert" "mroads" '(33 -32) 1 1 0 )
(command "insert" "mroads" '(41 -32) 1 1 0 )
(command "insert" "mroads" '(7 -29) 1 1 0 )
(command "insert" "mroads" '(85 -32) 1 1 0 )
(command "insert" "mroads" '(9 -15) 1 1 0 )
(command "insert" "mroads" '(33 -26) 1 1 0 )
(command "insert" "mroads" '(22 -31) 1 1 0 )
(command "insert" "mroads" '(93 -32) 1 1 0 )
(command "insert" "mroads" '(8 -20) 1 1 0 )
(command "insert" "mroads" '(37 -15) 1 1 0 )
(command "insert" "mroads" '(35 -28) 1 1 0 )
(command "insert" "mroads" '(9 -17) 1 1 0 )
(command "insert" "mroads" '(96 -30) 1 1 0 )
(command "insert" "mroads" '(36 -31) 1 1 0 )
(command "insert" "mroads" '(15 -15) 1 1 0 )
(command "insert" "mroads" '(97 -31) 1 1 0 )
(command "insert" "mroads" '(37 -30) 1 1 0 )
(command "insert" "mroads" '(38 -29) 1 1 0 )
(command "insert" "mroads" '(83 -31) 1 1 0 )
(command "insert" "mroads" '(39 -24) 1 1 0 )
(command "insert" "mroads" '(5 -15) 1 1 0 )
(command "insert" "mroads" '(3 -19) 1 1 0 )
(command "insert" "mroads" '(4 -20) 1 1 0 )
(command "insert" "mroads" '(19 -20) 1 1 0 )
(command "insert" "mroads" '(92 -30) 1 1 0 )
(command "insert" "mroads" '(16 -31) 1 1 0 )
(command "insert" "mroads" '(93 -31) 1 1 0 )
(command "insert" "mroads" '(17 -30) 1 1 0 )
(command "insert" "mroads" '(32 -18) 1 1 0 )
(command "insert" "mroads" '(11 -32) 1 1 0 )
(command "insert" "mroads" '(33 -19) 1 1 0 )
(command "insert" "mroads" '(40 -29) 1 1 0 )
(command "insert" "mroads" '(8 -27) 1 1 0 )
(command "insert" "mroads" '(63 -32) 1 1 0 )
(command "insert" "mroads" '(5 -21) 1 1 0 )
(command "insert" "mroads" '(24 -30) 1 1 0 )
(command "insert" "mroads" '(14 -17) 1 1 0 )
(command "insert" "mroads" '(71 -32) 1 1 0 )
(command "insert" "mroads" '(10 -17) 1 1 0 )
(command "insert" "mroads" '(25 -31) 1 1 0 )
(command "insert" "mroads" '(99 -32) 1 1 0 )
(command "insert" "mroads" '(111 -32) 1 1 0 )
(command "insert" "mroads" '(107 -32) 1 1 0 )
(command "insert" "mroads" '(38 -20) 1 1 0 )
(command "insert" "mroads" '(12 -31) 1 1 0 )
(command "insert" "mroads" '(27 -17) 1 1 0 )
(command "insert" "mroads" '(39 -17) 1 1 0 )
(command "insert" "mroads" '(13 -30) 1 1 0 )
(command "insert" "mroads" '(41 -24) 1 1 0 )
(command "insert" "mroads" '(3 -24) 1 1 0 )
(command "insert" "mroads" '(56 -32) 1 1 0 )
(command "insert" "mroads" '(4 -19) 1 1 0 )
(command "insert" "mroads" '(26 -32) 1 1 0 )
(command "insert" "mroads" '(5 -18) 1 1 0 )
(command "insert" "mroads" '(20 -30) 1 1 0 )
(command "insert" "mroads" '(6 -25) 1 1 0 )
(command "insert" "mroads" '(21 -31) 1 1 0 )
(command "insert" "mroads" '(40 -22) 1 1 0 )
(command "insert" "mroads" '(78 -32) 1 1 0 )
(command "insert" "mroads" '(41 -18) 1 1 0 )
(command "insert" "mroads" '(18 -20) 1 1 0 )
(command "insert" "mroads" '(33 -20) 1 1 0 )
(command "insert" "mroads" '(69 -31) 1 1 0 )
(command "insert" "mroads" '(34 -19) 1 1 0 )
(command "insert" "mroads" '(32 -15) 1 1 0 )
(command "insert" "mroads" '(15 -32) 1 1 0 )
(command "insert" "mroads" '(64 -32) 1 1 0 )
(command "insert" "mroads" '(35 -16) 1 1 0 )
(command "insert" "mroads" '(38 -15) 1 1 0 )
(command "insert" "mroads" '(77 -32) 1 1 0 )
(command "insert" "mroads" '(1 -31) 1 1 0 )
(command "insert" "mroads" '(28 -17) 1 1 0 )
(command "insert" "mroads" '(2 -28) 1 1 0 )
(command "insert" "mroads" '(48 -30) 1 1 0 )
(command "insert" "mroads" '(113 -32) 1 1 0 )
(command "insert" "mroads" '(49 -31) 1 1 0 )
(command "insert" "mroads" '(4 -26) 1 1 0 )
(command "insert" "mroads" '(28 -15) 1 1 0 )
(command "insert" "mroads" '(5 -27) 1 1 0 )
(command "insert" "mroads" '(40 -26) 1 1 0 )
(command "insert" "mroads" '(4 -32) 1 1 0 )
(command "insert" "mroads" '(7 -21) 1 1 0 )
(command "insert" "mroads" '(18 -15) 1 1 0 )
(command "insert" "mroads" '(40 -32) 1 1 0 )
(command "insert" "mroads" '(34 -20) 1 1 0 )
(command "insert" "mroads" '(58 -31) 1 1 0 )
(command "insert" "mroads" '(44 -30) 1 1 0 )
(command "insert" "mroads" '(59 -30) 1 1 0 )
(command "insert" "mroads" '(92 -32) 1 1 0 )
(command "insert" "mroads" '(45 -31) 1 1 0 )
(command "insert" "mroads" '(6 -17) 1 1 0 )
(command "insert" "mroads" '(106 -31) 1 1 0 )
(command "insert" "mroads" '(35 -25) 1 1 0 )
(command "insert" "mroads" '(24 -18) 1 1 0 )
(command "insert" "mroads" '(107 -30) 1 1 0 )
(command "insert" "mroads" '(36 -18) 1 1 0 )
(command "insert" "mroads" '(25 -19) 1 1 0 )
(command "insert" "mroads" '(13 -16) 1 1 0 )
(command "insert" "mroads" '(37 -19) 1 1 0 )
(command "insert" "mroads" '(2 -23) 1 1 0 )
(command "insert" "mroads" '(38 -24) 1 1 0 )
(command "insert" "mroads" '(39 -29) 1 1 0 )
(command "insert" "mroads" '(54 -31) 1 1 0 )
(command "insert" "mroads" '(115 -31) 1 1 0 )
(command "insert" "mroads" '(55 -30) 1 1 0 )
(command "insert" "mroads" '(22 -20) 1 1 0 )
(command "insert" "mroads" '(30 -20) 1 1 0 )
(command "insert" "mroads" '(19 -17) 1 1 0 )
(command "insert" "mroads" '(102 -31) 1 1 0 )
(command "insert" "mroads" '(41 -28) 1 1 0 )
(command "insert" "mroads" '(31 -17) 1 1 0 )
(command "insert" "mroads" '(103 -30) 1 1 0 )
(command "insert" "mroads" '(10 -32) 1 1 0 )
(command "insert" "mroads" '(22 -32) 1 1 0 )
(command "insert" "mroads" '(18 -32) 1 1 0 )
(command "insert" "mroads" '(33 -24) 1 1 0 )
(command "insert" "mroads" '(62 -32) 1 1 0 )
(command "insert" "mroads" '(110 -30) 1 1 0 )
(command "insert" "mroads" '(34 -31) 1 1 0 )
(command "insert" "mroads" '(8 -22) 1 1 0 )
(command "insert" "mroads" '(23 -17) 1 1 0 )
(command "insert" "mroads" '(70 -32) 1 1 0 )
(command "insert" "mroads" '(35 -30) 1 1 0 )
(command "insert" "mroads" '(98 -32) 1 1 0 )
(command "insert" "mroads" '(36 -25) 1 1 0 )
(command "insert" "mroads" '(10 -20) 1 1 0 )
(command "insert" "mroads" '(25 -20) 1 1 0 )
(command "insert" "mroads" '(82 -31) 1 1 0 )
(command "insert" "mroads" '(106 -32) 1 1 0 )
(command "insert" "mroads" '(37 -28) 1 1 0 )
(command "insert" "mroads" '(26 -19) 1 1 0 )
(command "insert" "mroads" '(38 -19) 1 1 0 )
(command "insert" "mroads" '(3 -15) 1 1 0 )
(command "insert" "mroads" '(39 -26) 1 1 0 )
(command "insert" "mroads" '(51 -31) 1 1 0 )
(command "insert" "mroads" '(3 -21) 1 1 0 )
(command "insert" "mroads" '(25 -32) 1 1 0 )
(command "insert" "mroads" '(90 -30) 1 1 0 )
(command "insert" "mroads" '(30 -31) 1 1 0 )
(command "insert" "mroads" '(4 -22) 1 1 0 )
(command "insert" "mroads" '(91 -31) 1 1 0 )
(command "insert" "mroads" '(31 -30) 1 1 0 )
(command "insert" "mroads" '(5 -23) 1 1 0 )
(command "insert" "mroads" '(20 -17) 1 1 0 )
(command "insert" "mroads" '(16 -17) 1 1 0 )
(command "insert" "mroads" '(21 -20) 1 1 0 )
(command "insert" "mroads" '(32 -20) 1 1 0 )
(command "insert" "mroads" '(33 -17) 1 1 0 )
(command "insert" "mroads" '(34 -22) 1 1 0 )
(command "insert" "mroads" '(8 -29) 1 1 0 )
(command "insert" "mroads" '(61 -31) 1 1 0 )
(command "insert" "mroads" '(86 -30) 1 1 0 )
(command "insert" "mroads" '(10 -31) 1 1 0 )
(command "insert" "mroads" '(6 -19) 1 1 0 )
(command "insert" "mroads" '(87 -31) 1 1 0 )
(command "insert" "mroads" '(11 -30) 1 1 0 )
(command "insert" "mroads" '(76 -32) 1 1 0 )
(command "insert" "mroads" '(27 -19) 1 1 0 )
(command "insert" "mroads" '(39 -19) 1 1 0 )
(command "insert" "mroads" '(28 -20) 1 1 0 )
(command "insert" "mroads" '(3 -26) 1 1 0 )
(command "insert" "mroads" '(40 -15) 1 1 0 )
(command "insert" "mroads" '(4 -29) 1 1 0 )
(command "insert" "mroads" '(19 -31) 1 1 0 )
(command "insert" "mroads" '(7 -26) 1 1 0 )
(command "insert" "mroads" '(5 -16) 1 1 0 )
(command "insert" "mroads" '(3 -32) 1 1 0 )
(command "insert" "mroads" '(66 -30) 1 1 0 )
(command "insert" "mroads" '(6 -31) 1 1 0 )
(command "insert" "mroads" '(67 -31) 1 1 0 )
(command "insert" "mroads" '(7 -30) 1 1 0 )
(command "insert" "mroads" '(22 -18) 1 1 0 )
(command "insert" "mroads" '(55 -32) 1 1 0 )
(command "insert" "mroads" '(18 -18) 1 1 0 )
(command "insert" "mroads" '(83 -32) 1 1 0 )
(command "insert" "mroads" '(114 -30) 1 1 0 )
(command "insert" "mroads" '(34 -17) 1 1 0 )
(command "insert" "mroads" '(91 -32) 1 1 0 )
(command "insert" "mroads" '(14 -30) 1 1 0 )
(command "insert" "mroads" '(36 -15) 1 1 0 )
(command "insert" "mroads" '(15 -31) 1 1 0 )
(command "insert" "mroads" '(35 -18) 1 1 0 )
(command "insert" "mroads" '(12 -16) 1 1 0 )
(command "insert" "mroads" '(36 -21) 1 1 0 )
(command "insert" "mroads" '(1 -29) 1 1 0 )
(command "insert" "mroads" '(63 -31) 1 1 0 )
(command "insert" "mroads" '(28 -19) 1 1 0 )
(command "insert" "mroads" '(2 -26) 1 1 0 )
(command "insert" "mroads" '(26 -15) 1 1 0 )
(command "insert" "mroads" '(12 -15) 1 1 0 )
(command "insert" "mroads" '(29 -18) 1 1 0 )
(command "insert" "mroads" '(5 -25) 1 1 0 )
(command "insert" "mroads" '(16 -15) 1 1 0 )
(command "insert" "mroads" '(6 -22) 1 1 0 )
(command "insert" "mroads" '(30 -19) 1 1 0 )
(command "insert" "mroads" '(41 -25) 1 1 0 )
(command "insert" "mroads" '(56 -31) 1 1 0 )
(command "insert" "mroads" '(9 -32) 1 1 0 )
(command "insert" "mroads" '(42 -30) 1 1 0 )
(command "insert" "mroads" '(23 -16) 1 1 0 )
(command "insert" "mroads" '(43 -31) 1 1 0 )
(command "insert" "mroads" '(17 -32) 1 1 0 )
(command "insert" "mroads" '(22 -15) 1 1 0 )
(command "insert" "mroads" '(61 -32) 1 1 0 )
(command "insert" "mroads" '(52 -30) 1 1 0 )
(command "insert" "mroads" '(105 -30) 1 1 0 )
(command "insert" "mroads" '(69 -32) 1 1 0 )
(command "insert" "mroads" '(34 -24) 1 1 0 )
(command "insert" "mroads" '(8 -17) 1 1 0 )
(command "insert" "mroads" '(97 -32) 1 1 0 )
(command "insert" "mroads" '(35 -27) 1 1 0 )
(command "insert" "mroads" '(24 -20) 1 1 0 )
(command "insert" "mroads" '(105 -32) 1 1 0 )
(command "insert" "mroads" '(36 -28) 1 1 0 )
(command "insert" "mroads" '(1 -22) 1 1 0 )
(command "insert" "mroads" '(6 -29) 1 1 0 )
(command "insert" "mroads" '(37 -17) 1 1 0 )
(command "insert" "mroads" '(2 -21) 1 1 0 )
(command "insert" "mroads" '(38 -30) 1 1 0 )
(command "insert" "mroads" '(53 -30) 1 1 0 )
(command "insert" "mroads" '(112 -32) 1 1 0 )
(command "insert" "mroads" '(39 -31) 1 1 0 )
(command "insert" "mroads" '(100 -31) 1 1 0 )
(command "insert" "mroads" '(24 -32) 1 1 0 )
(command "insert" "mroads" '(101 -30) 1 1 0 )
(command "insert" "mroads" '(19 -19) 1 1 0 )
(command "insert" "mroads" '(31 -19) 1 1 0 )
(command "insert" "mroads" '(20 -20) 1 1 0 )
(command "insert" "mroads" '(47 -31) 1 1 0 )
(command "insert" "mroads" '(32 -31) 1 1 0 )
(command "insert" "mroads" '(18 -30) 1 1 0 )
(command "insert" "mroads" '(33 -30) 1 1 0 )
(command "insert" "mroads" '(34 -29) 1 1 0 )
(command "insert" "mroads" '(8 -24) 1 1 0 )
(command "insert" "mroads" '(39 -32) 1 1 0 )
(command "insert" "mroads" '(80 -31) 1 1 0 )
(command "insert" "mroads" '(81 -30) 1 1 0 )
(command "insert" "mroads" '(36 -27) 1 1 0 )
(command "insert" "mroads" '(10 -18) 1 1 0 )
(command "insert" "mroads" '(75 -32) 1 1 0 )
(command "insert" "mroads" '(37 -26) 1 1 0 )
(command "insert" "mroads" '(26 -17) 1 1 0 )
(command "insert" "mroads" '(38 -17) 1 1 0 )
(command "insert" "mroads" '(39 -20) 1 1 0 )
(command "insert" "mroads" '(88 -30) 1 1 0 )
(command "insert" "mroads" '(28 -31) 1 1 0 )
(command "insert" "mroads" '(89 -31) 1 1 0 )
(command "insert" "mroads" '(29 -30) 1 1 0 )
(command "insert" "mroads" '(3 -23) 1 1 0 )
(command "insert" "mroads" '(4 -16) 1 1 0 )
(command "insert" "mroads" '(2 -32) 1 1 0 )
(command "insert" "mroads" '(76 -31) 1 1 0 )
(command "insert" "mroads" '(46 -32) 1 1 0 )
(command "insert" "mroads" '(20 -19) 1 1 0 )
(command "insert" "mroads" '(33 -29) 1 1 0 )
(command "insert" "mroads" '(77 -30) 1 1 0 )
(command "insert" "mroads" '(6 -26) 1 1 0 )
(command "insert" "mroads" '(21 -18) 1 1 0 )
(command "insert" "mroads" '(54 -32) 1 1 0 )
(command "insert" "mroads" '(33 -23) 1 1 0 )
(command "insert" "mroads" '(90 -32) 1 1 0 )
(command "insert" "mroads" '(84 -30) 1 1 0 )
(command "insert" "mroads" '(8 -31) 1 1 0 )
(command "insert" "mroads" '(95 -31) 1 1 0 )
(command "insert" "mroads" '(85 -31) 1 1 0 )
(command "insert" "mroads" '(9 -30) 1 1 0 )
(command "insert" "mroads" '(15 -16) 1 1 0 )
(command "insert" "mroads" '(11 -16) 1 1 0 )
(command "insert" "mroads" '(1 -26) 1 1 0 )
(command "insert" "mroads" '(40 -21) 1 1 0 )
(command "insert" "mroads" '(73 -31) 1 1 0 )
(command "insert" "mroads" '(3 -28) 1 1 0 )
(command "insert" "mroads" '(64 -30) 1 1 0 )
(command "insert" "mroads" '(4 -31) 1 1 0 )
(command "insert" "mroads" '(65 -31) 1 1 0 )
(command "insert" "mroads" '(5 -30) 1 1 0 )
(command "insert" "mroads" '(40 -23) 1 1 0 )
(command "insert" "mroads" '(112 -30) 1 1 0 )
(command "insert" "mroads" '(8 -32) 1 1 0 )
(command "insert" "mroads" '(41 -22) 1 1 0 )
(command "insert" "mroads" '(22 -16) 1 1 0 )
(command "insert" "mroads" '(113 -31) 1 1 0 )
(command "insert" "mroads" '(18 -16) 1 1 0 )
(command "insert" "mroads" '(16 -32) 1 1 0 )
(command "insert" "mroads" '(60 -32) 1 1 0 )
(command "insert" "mroads" '(68 -32) 1 1 0 )
(command "insert" "mroads" '(96 -32) 1 1 0 )
(command "insert" "mroads" '(60 -30) 1 1 0 )
(command "insert" "mroads" '(104 -32) 1 1 0 )
(command "insert" "mroads" '(35 -20) 1 1 0 )
(command "insert" "mroads" '(24 -15) 1 1 0 )
(command "insert" "mroads" '(36 -23) 1 1 0 )
(command "insert" "mroads" '(108 -30) 1 1 0 )
(command "insert" "mroads" '(37 -22) 1 1 0 )
(command "insert" "mroads" '(2 -24) 1 1 0 )
(command "insert" "mroads" '(109 -31) 1 1 0 )
(command "insert" "mroads" '(29 -16) 1 1 0 )
(command "insert" "mroads" '(30 -15) 1 1 0 )
(command "insert" "mroads" '(25 -18) 1 1 0 )
(command "insert" "mroads" '(40 -30) 1 1 0 )
(command "insert" "mroads" '(30 -17) 1 1 0 )
(command "insert" "mroads" '(7 -17) 1 1 0 )
(command "insert" "mroads" '(31 -20) 1 1 0 )
(command "insert" "mroads" '(20 -15) 1 1 0 )
(command "insert" "mroads" '(33 -31) 1 1 0 )
(command "insert" "mroads" '(23 -18) 1 1 0 )
(command "insert" "mroads" '(47 -32) 1 1 0 )
(command "insert" "mroads" '(33 -27) 1 1 0 )
(command "insert" "mroads" '(38 -32) 1 1 0 )
(command "insert" "mroads" '(10 -15) 1 1 0 )
(command "insert" "mroads" '(8 -19) 1 1 0 )
(command "insert" "mroads" '(35 -29) 1 1 0 )
(command "insert" "mroads" '(9 -18) 1 1 0 )
(command "insert" "mroads" '(74 -32) 1 1 0 )
(command "insert" "mroads" '(52 -32) 1 1 0 )
(command "insert" "mroads" '(36 -30) 1 1 0 )
(command "insert" "mroads" '(51 -30) 1 1 0 )
(command "insert" "mroads" '(41 -27) 1 1 0 )
(command "insert" "mroads" '(82 -32) 1 1 0 )
(command "insert" "mroads" '(37 -31) 1 1 0 )
(command "insert" "mroads" '(26 -20) 1 1 0 )
(command "insert" "mroads" '(7 -19) 1 1 0 )
(command "insert" "mroads" '(98 -31) 1 1 0 )
(command "insert" "mroads" '(38 -28) 1 1 0 )
(command "insert" "mroads" '(40 -19) 1 1 0 )
(command "insert" "mroads" '(99 -30) 1 1 0 )
(command "insert" "mroads" '(39 -25) 1 1 0 )
(command "insert" "mroads" '(3 -16) 1 1 0 )
(command "insert" "mroads" '(1 -32) 1 1 0 )
(command "insert" "mroads" '(6 -15) 1 1 0 )
(command "insert" "mroads" '(46 -31) 1 1 0 )
(command "insert" "mroads" '(53 -32) 1 1 0 )
(command "insert" "mroads" '(16 -30) 1 1 0 )
(command "insert" "mroads" '(47 -30) 1 1 0 )
(command "insert" "mroads" '(17 -31) 1 1 0 )
(command "insert" "mroads" '(32 -17) 1 1 0 )
(command "insert" "mroads" '(7 -28) 1 1 0 )
(command "insert" "mroads" '(89 -32) 1 1 0 )
(command "insert" "mroads" '(7 -24) 1 1 0 )
(command "insert" "mroads" '(94 -31) 1 1 0 )
(command "insert" "mroads" '(33 -28) 1 1 0 )
(command "insert" "mroads" '(95 -30) 1 1 0 )
(command "insert" "mroads" '(34 -27) 1 1 0 )
(command "insert" "mroads" '(8 -26) 1 1 0 )
(command "insert" "mroads" '(14 -16) 1 1 0 )
(command "insert" "mroads" '(10 -16) 1 1 0 )
(command "insert" "mroads" '(37 -24) 1 1 0 )
(command "insert" "mroads" '(68 -30) 1 1 0 )
(command "insert" "mroads" '(26 -31) 1 1 0 )
(command "insert" "mroads" '(26 -18) 1 1 0 )
(command "insert" "mroads" '(38 -23) 1 1 0 )
(command "insert" "mroads" '(83 -30) 1 1 0 )
(command "insert" "mroads" '(27 -30) 1 1 0 )
(command "insert" "mroads" '(39 -22) 1 1 0 )
(command "insert" "mroads" '(13 -31) 1 1 0 )
(command "insert" "mroads" '(74 -31) 1 1 0 )
(command "insert" "mroads" '(3 -25) 1 1 0 )
(command "insert" "mroads" '(75 -30) 1 1 0 )
(command "insert" "mroads" '(4 -18) 1 1 0 )
(command "insert" "mroads" '(62 -30) 1 1 0 )
(command "insert" "mroads" '(5 -19) 1 1 0 )
(command "insert" "mroads" '(23 -32) 1 1 0 )
(command "insert" "mroads" '(6 -24) 1 1 0 )
(command "insert" "mroads" '(21 -16) 1 1 0 )
(command "insert" "mroads" '(17 -16) 1 1 0 )
(command "insert" "mroads" '(41 -19) 1 1 0 )
(command "insert" "mroads" '(31 -32) 1 1 0 )
(command "insert" "mroads" '(59 -32) 1 1 0 )
(command "insert" "mroads" '(33 -21) 1 1 0 )
(command "insert" "mroads" '(23 -30) 1 1 0 )
(command "insert" "mroads" '(34 -18) 1 1 0 )
(command "insert" "mroads" '(67 -32) 1 1 0 )
(command "insert" "mroads" '(6 -20) 1 1 0 )
(command "insert" "mroads" '(70 -31) 1 1 0 )
(command "insert" "mroads" '(33 -15) 1 1 0 )
(command "insert" "mroads" '(71 -30) 1 1 0 )
(command "insert" "mroads" '(11 -18) 1 1 0 )
(command "insert" "mroads" '(35 -17) 1 1 0 )
(command "insert" "mroads" '(1 -24) 1 1 0 )
(command "insert" "mroads" '(39 -15) 1 1 0 )
(command "insert" "mroads" '(28 -16) 1 1 0 )
(command "insert" "mroads" '(2 -31) 1 1 0 )
(command "insert" "mroads" '(12 -30) 1 1 0 )
(command "insert" "mroads" '(41 -31) 1 1 0 )
(command "insert" "mroads" '(79 -31) 1 1 0 )
(command "insert" "mroads" '(3 -30) 1 1 0 )
(command "insert" "mroads" '(40 -17) 1 1 0 )
(command "insert" "mroads" '(4 -25) 1 1 0 )
(command "insert" "mroads" '(50 -31) 1 1 0 )
(command "insert" "mroads" '(5 -28) 1 1 0 )
(command "insert" "mroads" '(29 -15) 1 1 0 )
(command "insert" "mroads" '(40 -25) 1 1 0 )
(command "insert" "mroads" '(41 -20) 1 1 0 )
(command "insert" "mroads" '(58 -30) 1 1 0 )
(command "insert" "mroads" '(37 -32) 1 1 0 )
(command "insert" "mroads" '(59 -31) 1 1 0 )
(command "insert" "mroads" '(41 -16) 1 1 0 )
(command "insert" "mroads" '(45 -32) 1 1 0 )
(command "insert" "mroads" '(73 -32) 1 1 0 )
(command "insert" "mroads" '(106 -30) 1 1 0 )
(command "insert" "mroads" '(35 -22) 1 1 0 )
(command "insert" "mroads" '(24 -17) 1 1 0 )
(command "insert" "mroads" '(107 -31) 1 1 0 )
(command "insert" "mroads" '(81 -32) 1 1 0 )
(command "insert" "mroads" '(36 -17) 1 1 0 )
(command "insert" "mroads" '(13 -17) 1 1 0 )
(command "insert" "mroads" '(37 -20) 1 1 0 )
(command "insert" "mroads" '(2 -22) 1 1 0 )
(command "insert" "mroads" '(72 -30) 1 1 0 )
(command "insert" "mroads" '(38 -27) 1 1 0 )
(command "insert" "mroads" '(54 -30) 1 1 0 )
(command "insert" "mroads" '(34 -23) 1 1 0 )
(command "insert" "mroads" '(55 -31) 1 1 0 )
(command "insert" "mroads" '(116 -31) 1 1 0 )
(command "insert" "mroads" '(102 -30) 1 1 0 )
(command "insert" "mroads" '(41 -29) 1 1 0 )
(command "insert" "mroads" '(103 -31) 1 1 0 )
(command "insert" "mroads" '(88 -32) 1 1 0 )
(command "insert" "mroads" '(84 -31) 1 1 0 )
(command "insert" "mroads" '(8 -15) 1 1 0 )
(command "insert" "mroads" '(33 -25) 1 1 0 )
(command "insert" "mroads" '(34 -30) 1 1 0 )
(command "insert" "mroads" '(8 -21) 1 1 0 )
(command "insert" "mroads" '(35 -31) 1 1 0 )
(command "insert" "mroads" '(9 -16) 1 1 0 )
(command "insert" "mroads" '(14 -15) 1 1 0 )
(command "insert" "mroads" '(40 -28) 1 1 0 )
(command "insert" "mroads" '(96 -31) 1 1 0 )
(command "insert" "mroads" '(36 -24) 1 1 0 )
(command "insert" "mroads" '(78 -31) 1 1 0 )
(command "insert" "mroads" '(82 -30) 1 1 0 )
(command "insert" "mroads" '(97 -30) 1 1 0 )
(command "insert" "mroads" '(37 -29) 1 1 0 )
(command "insert" "mroads" '(31 -31) 1 1 0 )
(command "insert" "mroads" '(38 -18) 1 1 0 )
(command "insert" "mroads" '(103 -32) 1 1 0 )
(command "insert" "mroads" '(39 -27) 1 1 0 )
(command "insert" "mroads" '(4 -15) 1 1 0 )
(command "insert" "mroads" '(7 -23) 1 1 0 )
(command "insert" "mroads" '(3 -18) 1 1 0 )
(command "insert" "mroads" '(30 -30) 1 1 0 )
(command "insert" "mroads" '(4 -21) 1 1 0 )
(command "insert" "mroads" '(79 -30) 1 1 0 )
(command "insert" "mroads" '(20 -16) 1 1 0 )
(command "insert" "mroads" '(92 -31) 1 1 0 )
(command "insert" "mroads" '(16 -16) 1 1 0 )
(command "insert" "mroads" '(30 -32) 1 1 0 )
(command "insert" "mroads" '(93 -30) 1 1 0 )
(command "insert" "mroads" '(58 -32) 1 1 0 )
(command "insert" "mroads" '(32 -19) 1 1 0 )
(command "insert" "mroads" '(33 -18) 1 1 0 )
(command "insert" "mroads" '(66 -32) 1 1 0 )
(command "insert" "mroads" '(110 -32) 1 1 0 )
(command "insert" "mroads" '(34 -25) 1 1 0 )
(command "insert" "mroads" '(8 -28) 1 1 0 )
(command "insert" "mroads" '(57 -30) 1 1 0 )
(command "insert" "mroads" '(24 -31) 1 1 0 )
(command "insert" "mroads" '(10 -30) 1 1 0 )
(command "insert" "mroads" '(25 -30) 1 1 0 )
(command "insert" "mroads" '(11 -31) 1 1 0 )
(command "insert" "mroads" '(72 -31) 1 1 0 )
(command "insert" "mroads" '(27 -16) 1 1 0 )
(command "insert" "mroads" '(49 -32) 1 1 0 )
(command "insert" "mroads" '(73 -30) 1 1 0 )
(command "insert" "mroads" '(3 -27) 1 1 0 )
(command "insert" "mroads" '(4 -28) 1 1 0 )
(command "insert" "mroads" '(41 -15) 1 1 0 )
(command "insert" "mroads" '(5 -17) 1 1 0 )
(command "insert" "mroads" '(20 -31) 1 1 0 )
(command "insert" "mroads" '(6 -30) 1 1 0 )
(command "insert" "mroads" '(21 -30) 1 1 0 )
(command "insert" "mroads" '(7 -31) 1 1 0 )
(command "insert" "mroads" '(68 -31) 1 1 0 )
(command "insert" "mroads" '(36 -32) 1 1 0 )
(command "insert" "mroads" '(69 -30) 1 1 0 )
(command "insert" "mroads" '(34 -16) 1 1 0 )
(command "insert" "mroads" '(44 -32) 1 1 0 )
(command "insert" "mroads" '(72 -32) 1 1 0 )
(command "insert" "mroads" '(6 -16) 1 1 0 )
(command "insert" "mroads" '(80 -32) 1 1 0 )
(command "insert" "mroads" '(11 -20) 1 1 0 )
(command "insert" "mroads" '(35 -19) 1 1 0 )
(command "insert" "mroads" '(36 -20) 1 1 0 )
(command "insert" "mroads" '(1 -30) 1 1 0 )
(command "insert" "mroads" '(28 -18) 1 1 0 )
(command "insert" "mroads" '(2 -29) 1 1 0 )
(command "insert" "mroads" '(48 -31) 1 1 0 )
(command "insert" "mroads" '(29 -19) 1 1 0 )
(command "insert" "mroads" '(27 -15) 1 1 0 )
(command "insert" "mroads" '(49 -30) 1 1 0 )
(command "insert" "mroads" '(4 -27) 1 1 0 )
(command "insert" "mroads" '(32 -32) 1 1 0 )
(command "insert" "mroads" '(5 -26) 1 1 0 )
(command "insert" "mroads" '(51 -32) 1 1 0 )
(command "insert" "mroads" '(40 -27) 1 1 0 )
(command "insert" "mroads" '(30 -18) 1 1 0 )
(command "insert" "mroads" '(17 -15) 1 1 0 )
(command "insert" "mroads" '(41 -26) 1 1 0 )
(command "insert" "mroads" '(56 -30) 1 1 0 )
(command "insert" "mroads" '(57 -31) 1 1 0 )
(command "insert" "mroads" '(86 -31) 1 1 0 )
(command "insert" "mroads" '(104 -30) 1 1 0 )
(command "insert" "mroads" '(44 -31) 1 1 0 )
(command "insert" "mroads" '(23 -15) 1 1 0 )
(command "insert" "mroads" '(105 -31) 1 1 0 )
(command "insert" "mroads" '(45 -30) 1 1 0 )
(command "insert" "mroads" '(8 -16) 1 1 0 )
(command "insert" "mroads" '(35 -24) 1 1 0 )
(command "insert" "mroads" '(50 -32) 1 1 0 )
(command "insert" "mroads" '(24 -19) 1 1 0 )
(command "insert" "mroads" '(36 -19) 1 1 0 )
(command "insert" "mroads" '(1 -23) 1 1 0 )
(command "insert" "mroads" '(104 -31) 1 1 0 )
(command "insert" "mroads" '(13 -15) 1 1 0 )
(command "insert" "mroads" '(37 -18) 1 1 0 )
(command "insert" "mroads" '(102 -32) 1 1 0 )
(command "insert" "mroads" '(38 -25) 1 1 0 )
(command "insert" "mroads" '(53 -31) 1 1 0 )
(command "insert" "mroads" '(78 -30) 1 1 0 )
(command "insert" "mroads" '(39 -28) 1 1 0 )
(command "insert" "mroads" '(84 -32) 1 1 0 )
(command "insert" "mroads" '(100 -30) 1 1 0 )
(command "insert" "mroads" '(115 -30) 1 1 0 )
(command "insert" "mroads" '(25 -17) 1 1 0 )
(command "insert" "mroads" '(101 -31) 1 1 0 )
(command "insert" "mroads" '(21 -32) 1 1 0 )
(command "insert" "mroads" '(19 -16) 1 1 0 )
(command "insert" "mroads" '(31 -16) 1 1 0 )
(command "insert" "mroads" '(29 -32) 1 1 0 )
(command "insert" "mroads" '(41 -17) 1 1 0 )
(command "insert" "mroads" '(32 -30) 1 1 0 )
(command "insert" "mroads" '(65 -32) 1 1 0 )
(command "insert" "mroads" '(52 -31) 1 1 0 )
(command "insert" "mroads" '(7 -20) 1 1 0 )
(command "insert" "mroads" '(110 -31) 1 1 0 )
(command "insert" "mroads" '(34 -28) 1 1 0 )
(command "insert" "mroads" '(8 -23) 1 1 0 )
(command "insert" "mroads" '(80 -30) 1 1 0 )
(command "insert" "mroads" '(111 -30) 1 1 0 )
(command "insert" "mroads" '(57 -32) 1 1 0 )
(command "insert" "mroads" '(81 -31) 1 1 0 )
(command "insert" "mroads" '(36 -26) 1 1 0 )
(command "insert" "mroads" '(40 -24) 1 1 0 )
(command "insert" "mroads" '(37 -27) 1 1 0 )
(command "insert" "mroads" '(26 -16) 1 1 0 )
(command "insert" "mroads" '(38 -16) 1 1 0 )
(command "insert" "mroads" '(39 -21) 1 1 0 )
(command "insert" "mroads" '(28 -30) 1 1 0 )
(command "insert" "mroads" '(29 -31) 1 1 0 )
(command "insert" "mroads" '(3 -20) 1 1 0 )
(command "insert" "mroads" '(90 -31) 1 1 0 )
(command "insert" "mroads" '(4 -23) 1 1 0 )
(command "insert" "mroads" '(76 -30) 1 1 0 )
(command "insert" "mroads" '(91 -30) 1 1 0 )
(command "insert" "mroads" '(7 -27) 1 1 0 )
(command "insert" "mroads" '(5 -22) 1 1 0 )
(command "insert" "mroads" '(20 -18) 1 1 0 )
(command "insert" "mroads" '(77 -31) 1 1 0 )
(command "insert" "mroads" '(21 -19) 1 1 0 )
(command "insert" "mroads" '(7 -32) 1 1 0 )
(command "insert" "mroads" '(35 -32) 1 1 0 )
(command "insert" "mroads" '(113 -30) 1 1 0 )
(command "insert" "mroads" '(33 -16) 1 1 0 )
(command "insert" "mroads" '(43 -32) 1 1 0 )
(command "insert" "mroads" '(8 -30) 1 1 0 )
(command "insert" "mroads" '(40 -16) 1 1 0 )
(command "insert" "mroads" '(87 -32) 1 1 0 )
(command "insert" "mroads" '(9 -31) 1 1 0 )
(command "insert" "mroads" '(95 -32) 1 1 0 )
(command "insert" "mroads" '(15 -17) 1 1 0 )
(command "insert" "mroads" '(87 -30) 1 1 0 )
(command "insert" "mroads" '(11 -17) 1 1 0 )
(command "insert" "mroads" '(27 -18) 1 1 0 )
(command "insert" "mroads" '(1 -27) 1 1 0 )
(command "insert" "mroads" '(39 -18) 1 1 0 )
(command "insert" "mroads" '(14 -32) 1 1 0 )
(command "insert" "mroads" '(3 -29) 1 1 0 )
(command "insert" "mroads" '(4 -30) 1 1 0 )
(command "insert" "mroads" '(19 -30) 1 1 0 )
(command "layer" "m" "ped" "" )
(command "insert" "ped" '(1 -3) 1 1 0 )
(command "insert" "ped" '(2 -18) 1 1 0 )
(command "insert" "ped" '(2 -8) 1 1 0 )
(command "insert" "ped" '(1 -17) 1 1 0 )
(command "insert" "ped" '(2 -1) 1 1 0 )
(command "insert" "ped" '(1 -15) 1 1 0 )
(command "insert" "ped" '(6 -2) 1 1 0 )
(command "insert" "ped" '(1 -6) 1 1 0 )
(command "insert" "ped" '(2 -12) 1 1 0 )
(command "insert" "ped" '(5 -1) 1 1 0 )
(command "insert" "ped" '(2 -5) 1 1 0 )
(command "insert" "ped" '(1 -11) 1 1 0 )
(command "insert" "ped" '(7 -2) 1 1 0 )
(command "insert" "ped" '(1 -2) 1 1 0 )
(command "insert" "ped" '(2 -19) 1 1 0 )
(command "insert" "ped" '(2 -9) 1 1 0 )
(command "insert" "ped" '(8 -1) 1 1 0 )
(command "insert" "ped" '(1 -16) 1 1 0 )
(command "insert" "ped" '(1 -14) 1 1 0 )
(command "insert" "ped" '(1 -5) 1 1 0 )
(command "insert" "ped" '(2 -13) 1 1 0 )
(command "insert" "ped" '(1 -20) 1 1 0 )
(command "insert" "ped" '(2 -2) 1 1 0 )
(command "insert" "ped" '(1 -10) 1 1 0 )
(command "insert" "ped" '(4 -1) 1 1 0 )
(command "insert" "ped" '(1 -1) 1 1 0 )
(command "insert" "ped" '(2 -16) 1 1 0 )
(command "insert" "ped" '(3 -2) 1 1 0 )
(command "insert" "ped" '(2 -6) 1 1 0 )
(command "insert" "ped" '(8 -2) 1 1 0 )
(command "insert" "ped" '(7 -1) 1 1 0 )
(command "insert" "ped" '(1 -13) 1 1 0 )
(command "insert" "ped" '(2 -20) 1 1 0 )
(command "insert" "ped" '(1 -4) 1 1 0 )
(command "insert" "ped" '(2 -10) 1 1 0 )
(command "insert" "ped" '(1 -19) 1 1 0 )
(command "insert" "ped" '(2 -3) 1 1 0 )
(command "insert" "ped" '(1 -9) 1 1 0 )
(command "insert" "ped" '(4 -2) 1 1 0 )
(command "insert" "ped" '(2 -14) 1 1 0 )
(command "insert" "ped" '(2 -17) 1 1 0 )
(command "insert" "ped" '(2 -7) 1 1 0 )
(command "insert" "ped" '(1 -12) 1 1 0 )
(command "insert" "ped" '(6 -1) 1 1 0 )
(command "insert" "ped" '(3 -1) 1 1 0 )
(command "insert" "ped" '(2 -11) 1 1 0 )
(command "insert" "ped" '(1 -18) 1 1 0 )
(command "insert" "ped" '(1 -8) 1 1 0 )
(command "insert" "ped" '(1 -7) 1 1 0 )
(command "insert" "ped" '(2 -15) 1 1 0 )
(command "insert" "ped" '(5 -2) 1 1 0 )
(command "insert" "ped" '(2 -4) 1 1 0 )
(command "layer" "m" "mroads" "" )
(command "insert" "mroads" '(5 -31) 1 1 0 )
(command "insert" "mroads" '(66 -31) 1 1 0 )
(command "insert" "mroads" '(6 -28) 1 1 0 )
(command "insert" "mroads" '(67 -30) 1 1 0 )
(command "insert" "mroads" '(7 -25) 1 1 0 )
(command "insert" "mroads" '(22 -19) 1 1 0 )
(command "insert" "mroads" '(18 -19) 1 1 0 )
(command "insert" "mroads" '(38 -21) 1 1 0 )
(command "insert" "mroads" '(114 -31) 1 1 0 )
(command "insert" "mroads" '(13 -32) 1 1 0 )
(command "insert" "mroads" '(35 -15) 1 1 0 )
(command "insert" "mroads" '(14 -31) 1 1 0 )
(command "insert" "mroads" '(15 -30) 1 1 0 )
(command "insert" "mroads" '(35 -21) 1 1 0 )
(command "insert" "mroads" '(12 -17) 1 1 0 )
(command "insert" "mroads" '(36 -22) 1 1 0 )
(command "insert" "mroads" '(1 -28) 1 1 0 )
(command "insert" "mroads" '(25 -15) 1 1 0 )
(command "insert" "mroads" '(39 -16) 1 1 0 )
(command "insert" "mroads" '(63 -30) 1 1 0 )
(command "insert" "mroads" '(37 -23) 1 1 0 )
(command "insert" "mroads" '(2 -27) 1 1 0 )
(command "insert" "mroads" '(109 -32) 1 1 0 )
(command "insert" "mroads" '(29 -17) 1 1 0 )
(command "insert" "mroads" '(31 -15) 1 1 0 )
(command "insert" "mroads" '(5 -24) 1 1 0 )
(command "insert" "mroads" '(20 -32) 1 1 0 )
(command "insert" "mroads" '(6 -23) 1 1 0 )
(command "insert" "mroads" '(30 -16) 1 1 0 )
(command "insert" "mroads" '(28 -32) 1 1 0 )
(command "insert" "mroads" '(7 -22) 1 1 0 )
(command "insert" "mroads" '(41 -23) 1 1 0 )
(command "insert" "mroads" '(42 -31) 1 1 0 )
(command "insert" "mroads" '(23 -19) 1 1 0 )
(command "insert" "mroads" '(21 -15) 1 1 0 )
(command "insert" "mroads" '(43 -30) 1 1 0 )
(command "insert" "mroads" '(116 -32) 1 1 0 )
(command "insert" "mroads" '(8 -18) 1 1 0 )
(command "insert" "mroads" '(11 -15) 1 1 0 )
(command "insert" "mroads" '(35 -26) 1 1 0 )
(command "insert" "mroads" '(9 -19) 1 1 0 )
(command "insert" "mroads" '(36 -29) 1 1 0 )
(command "insert" "mroads" '(1 -21) 1 1 0 )
(command "insert" "mroads" '(25 -16) 1 1 0 )
(command "insert" "mroads" '(29 -20) 1 1 0 )
(command "insert" "mroads" '(37 -16) 1 1 0 )
(command "insert" "mroads" '(98 -30) 1 1 0 )
(command "insert" "mroads" '(38 -31) 1 1 0 )
(command "insert" "mroads" '(99 -31) 1 1 0 )
(command "insert" "mroads" '(39 -30) 1 1 0 )
(command "insert" "mroads" '(3 -17) 1 1 0 )
(command "insert" "mroads" '(19 -18) 1 1 0 )
(command "insert" "mroads" '(7 -15) 1 1 0 )
(command "insert" "mroads" '(31 -18) 1 1 0 )
(command "insert" "mroads" '(46 -30) 1 1 0 )
(command "insert" "mroads" '(47 -31) 1 1 0 )
(command "insert" "mroads" '(34 -32) 1 1 0 )
(command "insert" "mroads" '(32 -16) 1 1 0 )
(command "insert" "mroads" '(94 -30) 1 1 0 )
(command "insert" "mroads" '(18 -31) 1 1 0 )
(command "insert" "mroads" '(42 -32) 1 1 0 )
(command "insert" "mroads" '(86 -32) 1 1 0 )
(command "insert" "mroads" '(34 -26) 1 1 0 )
(command "insert" "mroads" '(8 -25) 1 1 0 )
(command "insert" "mroads" '(94 -32) 1 1 0 )
(command "insert" "mroads" '(9 -20) 1 1 0 )
(command "insert" "mroads" '(10 -19) 1 1 0 )
(command "insert" "mroads" '(37 -25) 1 1 0 )
(command "insert" "mroads" '(26 -30) 1 1 0 )
(command "insert" "mroads" '(41 -28) 1 1 0 )
(command "insert" "mroads" '(38 -22) 1 1 0 )
(command "insert" "mroads" '(27 -31) 1 1 0 )
(command "insert" "mroads" '(6 -30) 1 1 0 )
(command "insert" "mroads" '(39 -23) 1 1 0 )
(command "insert" "mroads" '(88 -31) 1 1 0 )
(command "insert" "mroads" '(74 -30) 1 1 0 )
(command "insert" "mroads" '(89 -30) 1 1 0 )
(command "insert" "mroads" '(3 -22) 1 1 0 )
(command "insert" "mroads" '(75 -31) 1 1 0 )
(command "insert" "mroads" '(4 -17) 1 1 0 )
(command "insert" "mroads" '(5 -20) 1 1 0 )
(command "insert" "mroads" '(6 -27) 1 1 0 )
(command "insert" "mroads" '(21 -17) 1 1 0 )
(command "insert" "mroads" '(17 -17) 1 1 0 )
(command "insert" "mroads" '(22 -30) 1 1 0 )
(command "insert" "mroads" '(33 -22) 1 1 0 )
(command "insert" "mroads" '(23 -31) 1 1 0 )
(command "insert" "mroads" '(12 -32) 1 1 0 )
(command "insert" "mroads" '(34 -21) 1 1 0 )
(command "insert" "mroads" '(70 -30) 1 1 0 )
(command "insert" "mroads" '(85 -30) 1 1 0 )
(command "insert" "mroads" '(48 -32) 1 1 0 )
(command "insert" "mroads" '(71 -31) 1 1 0 )
(command "insert" "mroads" '(34 -15) 1 1 0 )
(command "insert" "mroads" '(11 -19) 1 1 0 )
(command "insert" "mroads" '(100 -32) 1 1 0 )
(command "insert" "mroads" '(27 -20) 1 1 0 )
(command "insert" "mroads" '(1 -25) 1 1 0 )
(command "insert" "mroads" '(108 -32) 1 1 0 )
(command "insert" "mroads" '(2 -30) 1 1 0 )
(command "insert" "mroads" '(3 -31) 1 1 0 )
(command "insert" "mroads" '(64 -31) 1 1 0 )
(command "insert" "mroads" '(4 -24) 1 1 0 )
(command "insert" "mroads" '(19 -32) 1 1 0 )
(command "insert" "mroads" '(62 -31) 1 1 0 )
(command "insert" "mroads" '(50 -30) 1 1 0 )
(command "insert" "mroads" '(65 -30) 1 1 0 )
(command "insert" "mroads" '(5 -29) 1 1 0 )
(command "insert" "mroads" '(27 -32) 1 1 0 )
(command "insert" "mroads" '(6 -18) 1 1 0 )
(command "insert" "mroads" '(101 -32) 1 1 0 )
(command "insert" "mroads" '(112 -31) 1 1 0 )
(command "insert" "mroads" '(41 -21) 1 1 0 )
(command "insert" "mroads" '(22 -17) 1 1 0 )
(command "insert" "mroads" '(79 -32) 1 1 0 )
(command "insert" "mroads" '(18 -17) 1 1 0 )
(command "insert" "mroads" '(23 -20) 1 1 0 )
(command "insert" "mroads" '(40 -31) 1 1 0 )
(command "insert" "mroads" '(115 -32) 1 1 0 )
(command "insert" "mroads" '(60 -31) 1 1 0 )
(command "insert" "mroads" '(61 -30) 1 1 0 )
(command "insert" "mroads" '(35 -23) 1 1 0 )
(command "insert" "mroads" '(24 -16) 1 1 0 )
(command "insert" "mroads" '(36 -16) 1 1 0 )
(command "insert" "mroads" '(108 -31) 1 1 0 )
(command "insert" "mroads" '(37 -21) 1 1 0 )
(command "insert" "mroads" '(2 -25) 1 1 0 )
(command "insert" "mroads" '(109 -30) 1 1 0 )
(command "insert" "mroads" '(41 -30) 1 1 0 )
(command "insert" "mroads" '(38 -26) 1 1 0 )
(command "insert" "mroads" '(40 -18) 1 1 0 )
(command "insert" "mroads" '(114 -32) 1 1 0 )
(command "insert" "mroads" '(116 -30) 1 1 0 )
(command "insert" "mroads" '(6 -21) 1 1 0 )
(command "insert" "mroads" '(111 -31) 1 1 0 )
(command "insert" "mroads" '(19 -15) 1 1 0 )
(command "insert" "mroads" '(7 -16) 1 1 0 )
(command "insert" "mroads" '(5 -32) 1 1 0 )
(command "insert" "mroads" '(33 -32) 1 1 0 )
(command "insert" "mroads" '(41 -32) 1 1 0 )
(command "insert" "mroads" '(41 -19) 1 1 0 )
(command "insert" "mroads" '(85 -32) 1 1 0 )
(command "insert" "mroads" '(9 -15) 1 1 0 )
(command "insert" "mroads" '(33 -26) 1 1 0 )
(command "insert" "mroads" '(31 -32) 1 1 0 )
(command "insert" "mroads" '(93 -32) 1 1 0 )
(command "insert" "mroads" '(8 -20) 1 1 0 )
(command "insert" "mroads" '(37 -15) 1 1 0 )
(command "insert" "mroads" '(35 -28) 1 1 0 )
(command "insert" "mroads" '(9 -17) 1 1 0 )
(command "insert" "mroads" '(96 -30) 1 1 0 )
(command "insert" "mroads" '(36 -31) 1 1 0 )
(command "insert" "mroads" '(15 -15) 1 1 0 )
(command "insert" "mroads" '(97 -31) 1 1 0 )
(command "insert" "mroads" '(37 -30) 1 1 0 )
(command "insert" "mroads" '(38 -29) 1 1 0 )
(command "insert" "mroads" '(33 -21) 1 1 0 )
(command "insert" "mroads" '(39 -24) 1 1 0 )
(command "insert" "mroads" '(5 -15) 1 1 0 )
(command "insert" "mroads" '(3 -19) 1 1 0 )
(command "insert" "mroads" '(4 -20) 1 1 0 )
(command "insert" "mroads" '(19 -20) 1 1 0 )
(command "insert" "mroads" '(92 -30) 1 1 0 )
(command "insert" "mroads" '(16 -31) 1 1 0 )
(command "insert" "mroads" '(93 -31) 1 1 0 )
(command "insert" "mroads" '(17 -30) 1 1 0 )
(command "insert" "mroads" '(32 -18) 1 1 0 )
(command "insert" "mroads" '(11 -32) 1 1 0 )
(command "insert" "mroads" '(33 -19) 1 1 0 )
(command "insert" "mroads" '(40 -29) 1 1 0 )
(command "insert" "mroads" '(8 -27) 1 1 0 )
(command "insert" "mroads" '(63 -32) 1 1 0 )
(command "insert" "mroads" '(46 -32) 1 1 0 )
(command "insert" "mroads" '(24 -30) 1 1 0 )
(command "insert" "mroads" '(14 -17) 1 1 0 )
(command "insert" "mroads" '(71 -32) 1 1 0 )
(command "insert" "mroads" '(10 -17) 1 1 0 )
(command "insert" "mroads" '(25 -31) 1 1 0 )
(command "insert" "mroads" '(99 -32) 1 1 0 )
(command "insert" "mroads" '(111 -32) 1 1 0 )
(command "insert" "mroads" '(107 -32) 1 1 0 )
(command "insert" "mroads" '(38 -20) 1 1 0 )
(command "insert" "mroads" '(12 -31) 1 1 0 )
(command "insert" "mroads" '(27 -17) 1 1 0 )
(command "insert" "mroads" '(39 -17) 1 1 0 )
(command "insert" "mroads" '(13 -30) 1 1 0 )
(command "insert" "mroads" '(41 -24) 1 1 0 )
(command "insert" "mroads" '(3 -24) 1 1 0 )
(command "insert" "mroads" '(56 -32) 1 1 0 )
(command "insert" "mroads" '(4 -19) 1 1 0 )
(command "insert" "mroads" '(26 -32) 1 1 0 )
(command "insert" "mroads" '(5 -18) 1 1 0 )
(command "insert" "mroads" '(20 -30) 1 1 0 )
(command "insert" "mroads" '(40 -19) 1 1 0 )
(command "insert" "mroads" '(21 -31) 1 1 0 )
(command "insert" "mroads" '(40 -22) 1 1 0 )
(command "insert" "mroads" '(78 -32) 1 1 0 )
(command "insert" "mroads" '(41 -18) 1 1 0 )
(command "insert" "mroads" '(18 -20) 1 1 0 )
(command "insert" "mroads" '(33 -20) 1 1 0 )
(command "insert" "mroads" '(69 -31) 1 1 0 )
(command "insert" "mroads" '(34 -19) 1 1 0 )
(command "insert" "mroads" '(32 -15) 1 1 0 )
(command "insert" "mroads" '(15 -32) 1 1 0 )
(command "insert" "mroads" '(64 -32) 1 1 0 )
(command "insert" "mroads" '(35 -16) 1 1 0 )
(command "insert" "mroads" '(38 -15) 1 1 0 )
(command "insert" "mroads" '(77 -32) 1 1 0 )
(command "insert" "mroads" '(1 -31) 1 1 0 )
(command "insert" "mroads" '(28 -17) 1 1 0 )
(command "insert" "mroads" '(2 -28) 1 1 0 )
(command "insert" "mroads" '(48 -30) 1 1 0 )
(command "insert" "mroads" '(113 -32) 1 1 0 )
(command "insert" "mroads" '(49 -31) 1 1 0 )
(command "insert" "mroads" '(4 -26) 1 1 0 )
(command "insert" "mroads" '(28 -15) 1 1 0 )
(command "insert" "mroads" '(5 -27) 1 1 0 )
(command "insert" "mroads" '(40 -26) 1 1 0 )
(command "insert" "mroads" '(4 -32) 1 1 0 )
(command "insert" "mroads" '(7 -21) 1 1 0 )
(command "insert" "mroads" '(18 -15) 1 1 0 )
(command "insert" "mroads" '(40 -32) 1 1 0 )
(command "insert" "mroads" '(84 -32) 1 1 0 )
(command "insert" "mroads" '(58 -31) 1 1 0 )
(command "insert" "mroads" '(44 -30) 1 1 0 )
(command "insert" "mroads" '(59 -30) 1 1 0 )
(command "insert" "mroads" '(92 -32) 1 1 0 )
(command "insert" "mroads" '(45 -31) 1 1 0 )
(command "insert" "mroads" '(40 -27) 1 1 0 )
(command "insert" "mroads" '(106 -31) 1 1 0 )
(command "insert" "mroads" '(105 -32) 1 1 0 )
(command "insert" "mroads" '(35 -25) 1 1 0 )
(command "insert" "mroads" '(24 -18) 1 1 0 )
(command "insert" "mroads" '(107 -30) 1 1 0 )
(command "insert" "mroads" '(36 -18) 1 1 0 )
(command "insert" "mroads" '(25 -19) 1 1 0 )
(command "insert" "mroads" '(13 -16) 1 1 0 )
(command "insert" "mroads" '(37 -19) 1 1 0 )
(command "insert" "mroads" '(2 -23) 1 1 0 )
(command "insert" "mroads" '(38 -24) 1 1 0 )
(command "insert" "mroads" '(39 -29) 1 1 0 )
(command "insert" "mroads" '(54 -31) 1 1 0 )
(command "insert" "mroads" '(115 -31) 1 1 0 )
(command "insert" "mroads" '(55 -30) 1 1 0 )
(command "insert" "mroads" '(22 -20) 1 1 0 )
(command "insert" "mroads" '(30 -20) 1 1 0 )
(command "insert" "mroads" '(19 -17) 1 1 0 )
(command "insert" "mroads" '(102 -31) 1 1 0 )
(command "insert" "mroads" '(7 -18) 1 1 0 )
(command "insert" "mroads" '(31 -17) 1 1 0 )
(command "insert" "mroads" '(103 -30) 1 1 0 )
(command "insert" "mroads" '(10 -32) 1 1 0 )
(command "insert" "mroads" '(18 -32) 1 1 0 )
(command "insert" "mroads" '(33 -24) 1 1 0 )
(command "insert" "mroads" '(62 -32) 1 1 0 )
(command "insert" "mroads" '(110 -30) 1 1 0 )
(command "insert" "mroads" '(34 -31) 1 1 0 )
(command "insert" "mroads" '(8 -22) 1 1 0 )
(command "insert" "mroads" '(23 -17) 1 1 0 )
(command "insert" "mroads" '(70 -32) 1 1 0 )
(command "insert" "mroads" '(35 -30) 1 1 0 )
(command "insert" "mroads" '(98 -32) 1 1 0 )
(command "insert" "mroads" '(36 -25) 1 1 0 )
(command "insert" "mroads" '(10 -20) 1 1 0 )
(command "insert" "mroads" '(25 -20) 1 1 0 )
(command "insert" "mroads" '(82 -31) 1 1 0 )
(command "insert" "mroads" '(106 -32) 1 1 0 )
(command "insert" "mroads" '(37 -28) 1 1 0 )
(command "insert" "mroads" '(26 -19) 1 1 0 )
(command "insert" "mroads" '(38 -19) 1 1 0 )
(command "insert" "mroads" '(3 -15) 1 1 0 )
(command "insert" "mroads" '(39 -26) 1 1 0 )
(command "insert" "mroads" '(51 -31) 1 1 0 )
(command "insert" "mroads" '(3 -21) 1 1 0 )
(command "insert" "mroads" '(25 -32) 1 1 0 )
(command "insert" "mroads" '(90 -30) 1 1 0 )
(command "insert" "mroads" '(30 -31) 1 1 0 )
(command "insert" "mroads" '(4 -22) 1 1 0 )
(command "insert" "mroads" '(91 -31) 1 1 0 )
(command "insert" "mroads" '(31 -30) 1 1 0 )
(command "insert" "mroads" '(5 -23) 1 1 0 )
(command "insert" "mroads" '(20 -17) 1 1 0 )
(command "insert" "mroads" '(16 -17) 1 1 0 )
(command "insert" "mroads" '(21 -20) 1 1 0 )
(command "insert" "mroads" '(32 -20) 1 1 0 )
(command "insert" "mroads" '(33 -17) 1 1 0 )
(command "insert" "mroads" '(34 -22) 1 1 0 )
(command "insert" "mroads" '(8 -29) 1 1 0 )
(command "insert" "mroads" '(61 -31) 1 1 0 )
(command "insert" "mroads" '(86 -30) 1 1 0 )
(command "insert" "mroads" '(10 -31) 1 1 0 )
(command "insert" "mroads" '(40 -25) 1 1 0 )
(command "insert" "mroads" '(87 -31) 1 1 0 )
(command "insert" "mroads" '(11 -30) 1 1 0 )
(command "insert" "mroads" '(76 -32) 1 1 0 )
(command "insert" "mroads" '(27 -19) 1 1 0 )
(command "insert" "mroads" '(39 -19) 1 1 0 )
(command "insert" "mroads" '(28 -20) 1 1 0 )
(command "insert" "mroads" '(3 -26) 1 1 0 )
(command "insert" "mroads" '(40 -15) 1 1 0 )
(command "insert" "mroads" '(4 -29) 1 1 0 )
(command "insert" "mroads" '(19 -31) 1 1 0 )
(command "insert" "mroads" '(41 -20) 1 1 0 )
(command "insert" "mroads" '(5 -16) 1 1 0 )
(command "insert" "mroads" '(3 -32) 1 1 0 )
(command "insert" "mroads" '(66 -30) 1 1 0 )
(command "insert" "mroads" '(40 -21) 1 1 0 )
(command "insert" "mroads" '(67 -31) 1 1 0 )
(command "insert" "mroads" '(7 -30) 1 1 0 )
(command "insert" "mroads" '(22 -18) 1 1 0 )
(command "insert" "mroads" '(55 -32) 1 1 0 )
(command "insert" "mroads" '(18 -18) 1 1 0 )
(command "insert" "mroads" '(83 -32) 1 1 0 )
(command "insert" "mroads" '(114 -30) 1 1 0 )
(command "insert" "mroads" '(34 -17) 1 1 0 )
(command "insert" "mroads" '(91 -32) 1 1 0 )
(command "insert" "mroads" '(14 -30) 1 1 0 )
(command "insert" "mroads" '(36 -15) 1 1 0 )
(command "insert" "mroads" '(15 -31) 1 1 0 )
(command "insert" "mroads" '(35 -18) 1 1 0 )
(command "insert" "mroads" '(12 -16) 1 1 0 )
(command "insert" "mroads" '(36 -21) 1 1 0 )
(command "insert" "mroads" '(1 -29) 1 1 0 )
(command "insert" "mroads" '(63 -31) 1 1 0 )
(command "insert" "mroads" '(28 -19) 1 1 0 )
(command "insert" "mroads" '(2 -26) 1 1 0 )
(command "insert" "mroads" '(26 -15) 1 1 0 )
(command "insert" "mroads" '(29 -18) 1 1 0 )
(command "insert" "mroads" '(5 -25) 1 1 0 )
(command "insert" "mroads" '(16 -15) 1 1 0 )
(command "insert" "mroads" '(6 -22) 1 1 0 )
(command "insert" "mroads" '(30 -19) 1 1 0 )
(command "insert" "mroads" '(7 -23) 1 1 0 )
(command "insert" "mroads" '(56 -31) 1 1 0 )
(command "insert" "mroads" '(9 -32) 1 1 0 )
(command "insert" "mroads" '(42 -30) 1 1 0 )
(command "insert" "mroads" '(23 -16) 1 1 0 )
(command "insert" "mroads" '(43 -31) 1 1 0 )
(command "insert" "mroads" '(17 -32) 1 1 0 )
(command "insert" "mroads" '(22 -15) 1 1 0 )
(command "insert" "mroads" '(61 -32) 1 1 0 )
(command "insert" "mroads" '(52 -30) 1 1 0 )
(command "insert" "mroads" '(105 -30) 1 1 0 )
(command "insert" "mroads" '(69 -32) 1 1 0 )
(command "insert" "mroads" '(34 -24) 1 1 0 )
(command "insert" "mroads" '(8 -17) 1 1 0 )
(command "insert" "mroads" '(97 -32) 1 1 0 )
(command "insert" "mroads" '(35 -27) 1 1 0 )
(command "insert" "mroads" '(24 -20) 1 1 0 )
(command "insert" "mroads" '(12 -15) 1 1 0 )
(command "insert" "mroads" '(36 -28) 1 1 0 )
(command "insert" "mroads" '(1 -22) 1 1 0 )
(command "insert" "mroads" '(25 -17) 1 1 0 )
(command "insert" "mroads" '(37 -17) 1 1 0 )
(command "insert" "mroads" '(2 -21) 1 1 0 )
(command "insert" "mroads" '(38 -30) 1 1 0 )
(command "insert" "mroads" '(53 -30) 1 1 0 )
(command "insert" "mroads" '(112 -32) 1 1 0 )
(command "insert" "mroads" '(39 -31) 1 1 0 )
(command "insert" "mroads" '(100 -31) 1 1 0 )
(command "insert" "mroads" '(24 -32) 1 1 0 )
(command "insert" "mroads" '(101 -30) 1 1 0 )
(command "insert" "mroads" '(32 -32) 1 1 0 )
(command "insert" "mroads" '(19 -19) 1 1 0 )
(command "insert" "mroads" '(31 -19) 1 1 0 )
(command "insert" "mroads" '(20 -20) 1 1 0 )
(command "insert" "mroads" '(6 -32) 1 1 0 )
(command "insert" "mroads" '(32 -31) 1 1 0 )
(command "insert" "mroads" '(18 -30) 1 1 0 )
(command "insert" "mroads" '(33 -30) 1 1 0 )
(command "insert" "mroads" '(34 -29) 1 1 0 )
(command "insert" "mroads" '(8 -24) 1 1 0 )
(command "insert" "mroads" '(39 -32) 1 1 0 )
(command "insert" "mroads" '(80 -31) 1 1 0 )
(command "insert" "mroads" '(81 -30) 1 1 0 )
(command "insert" "mroads" '(113 -31) 1 1 0 )
(command "insert" "mroads" '(36 -27) 1 1 0 )
(command "insert" "mroads" '(10 -18) 1 1 0 )
(command "insert" "mroads" '(75 -32) 1 1 0 )
(command "insert" "mroads" '(37 -26) 1 1 0 )
(command "insert" "mroads" '(26 -17) 1 1 0 )
(command "insert" "mroads" '(38 -17) 1 1 0 )
(command "insert" "mroads" '(39 -20) 1 1 0 )
(command "insert" "mroads" '(88 -30) 1 1 0 )
(command "insert" "mroads" '(28 -31) 1 1 0 )
(command "insert" "mroads" '(89 -31) 1 1 0 )
(command "insert" "mroads" '(29 -30) 1 1 0 )
(command "insert" "mroads" '(3 -23) 1 1 0 )
(command "insert" "mroads" '(4 -16) 1 1 0 )
(command "insert" "mroads" '(2 -32) 1 1 0 )
(command "insert" "mroads" '(76 -31) 1 1 0 )
(command "insert" "mroads" '(5 -21) 1 1 0 )
(command "insert" "mroads" '(20 -19) 1 1 0 )
(command "insert" "mroads" '(33 -29) 1 1 0 )
(command "insert" "mroads" '(77 -30) 1 1 0 )
(command "insert" "mroads" '(6 -26) 1 1 0 )
(command "insert" "mroads" '(21 -18) 1 1 0 )
(command "insert" "mroads" '(54 -32) 1 1 0 )
(command "insert" "mroads" '(33 -23) 1 1 0 )
(command "insert" "mroads" '(90 -32) 1 1 0 )
(command "insert" "mroads" '(84 -30) 1 1 0 )
(command "insert" "mroads" '(8 -31) 1 1 0 )
(command "insert" "mroads" '(95 -31) 1 1 0 )
(command "insert" "mroads" '(85 -31) 1 1 0 )
(command "insert" "mroads" '(9 -30) 1 1 0 )
(command "insert" "mroads" '(15 -16) 1 1 0 )
(command "insert" "mroads" '(11 -16) 1 1 0 )
(command "insert" "mroads" '(28 -16) 1 1 0 )
(command "insert" "mroads" '(1 -26) 1 1 0 )
(command "insert" "mroads" '(6 -31) 1 1 0 )
(command "insert" "mroads" '(73 -31) 1 1 0 )
(command "insert" "mroads" '(3 -28) 1 1 0 )
(command "insert" "mroads" '(64 -30) 1 1 0 )
(command "insert" "mroads" '(4 -31) 1 1 0 )
(command "insert" "mroads" '(65 -31) 1 1 0 )
(command "insert" "mroads" '(5 -30) 1 1 0 )
(command "insert" "mroads" '(6 -29) 1 1 0 )
(command "insert" "mroads" '(112 -30) 1 1 0 )
(command "insert" "mroads" '(8 -32) 1 1 0 )
(command "insert" "mroads" '(41 -22) 1 1 0 )
(command "insert" "mroads" '(22 -16) 1 1 0 )
(command "insert" "mroads" '(34 -20) 1 1 0 )
(command "insert" "mroads" '(18 -16) 1 1 0 )
(command "insert" "mroads" '(16 -32) 1 1 0 )
(command "insert" "mroads" '(60 -32) 1 1 0 )
(command "insert" "mroads" '(68 -32) 1 1 0 )
(command "insert" "mroads" '(96 -32) 1 1 0 )
(command "insert" "mroads" '(60 -30) 1 1 0 )
(command "insert" "mroads" '(104 -32) 1 1 0 )
(command "insert" "mroads" '(35 -20) 1 1 0 )
(command "insert" "mroads" '(24 -15) 1 1 0 )
(command "insert" "mroads" '(36 -23) 1 1 0 )
(command "insert" "mroads" '(108 -30) 1 1 0 )
(command "insert" "mroads" '(37 -22) 1 1 0 )
(command "insert" "mroads" '(2 -24) 1 1 0 )
(command "insert" "mroads" '(109 -31) 1 1 0 )
(command "insert" "mroads" '(29 -16) 1 1 0 )
(command "insert" "mroads" '(30 -15) 1 1 0 )
(command "insert" "mroads" '(25 -18) 1 1 0 )
(command "insert" "mroads" '(40 -30) 1 1 0 )
(command "insert" "mroads" '(30 -17) 1 1 0 )
(command "insert" "mroads" '(7 -17) 1 1 0 )
(command "insert" "mroads" '(31 -20) 1 1 0 )
(command "insert" "mroads" '(20 -15) 1 1 0 )
(command "insert" "mroads" '(33 -31) 1 1 0 )
(command "insert" "mroads" '(23 -18) 1 1 0 )
(command "insert" "mroads" '(47 -32) 1 1 0 )
(command "insert" "mroads" '(33 -27) 1 1 0 )
(command "insert" "mroads" '(38 -32) 1 1 0 )
(command "insert" "mroads" '(10 -15) 1 1 0 )
(command "insert" "mroads" '(8 -19) 1 1 0 )
(command "insert" "mroads" '(35 -29) 1 1 0 )
(command "insert" "mroads" '(9 -18) 1 1 0 )
(command "insert" "mroads" '(74 -32) 1 1 0 )
(command "insert" "mroads" '(102 -30) 1 1 0 )
(command "insert" "mroads" '(36 -30) 1 1 0 )
(command "insert" "mroads" '(51 -30) 1 1 0 )
(command "insert" "mroads" '(82 -32) 1 1 0 )
(command "insert" "mroads" '(37 -31) 1 1 0 )
(command "insert" "mroads" '(26 -20) 1 1 0 )
(command "insert" "mroads" '(41 -29) 1 1 0 )
(command "insert" "mroads" '(98 -31) 1 1 0 )
(command "insert" "mroads" '(38 -28) 1 1 0 )
(command "insert" "mroads" '(6 -25) 1 1 0 )
(command "insert" "mroads" '(99 -30) 1 1 0 )
(command "insert" "mroads" '(39 -25) 1 1 0 )
(command "insert" "mroads" '(3 -16) 1 1 0 )
(command "insert" "mroads" '(1 -32) 1 1 0 )
(command "insert" "mroads" '(6 -15) 1 1 0 )
(command "insert" "mroads" '(46 -31) 1 1 0 )
(command "insert" "mroads" '(53 -32) 1 1 0 )
(command "insert" "mroads" '(16 -30) 1 1 0 )
(command "insert" "mroads" '(47 -30) 1 1 0 )
(command "insert" "mroads" '(17 -31) 1 1 0 )
(command "insert" "mroads" '(32 -17) 1 1 0 )
(command "insert" "mroads" '(7 -28) 1 1 0 )
(command "insert" "mroads" '(89 -32) 1 1 0 )
(command "insert" "mroads" '(7 -24) 1 1 0 )
(command "insert" "mroads" '(94 -31) 1 1 0 )
(command "insert" "mroads" '(33 -28) 1 1 0 )
(command "insert" "mroads" '(95 -30) 1 1 0 )
(command "insert" "mroads" '(34 -27) 1 1 0 )
(command "insert" "mroads" '(8 -26) 1 1 0 )
(command "insert" "mroads" '(14 -16) 1 1 0 )
(command "insert" "mroads" '(10 -16) 1 1 0 )
(command "insert" "mroads" '(37 -24) 1 1 0 )
(command "insert" "mroads" '(68 -30) 1 1 0 )
(command "insert" "mroads" '(26 -31) 1 1 0 )
(command "insert" "mroads" '(38 -23) 1 1 0 )
(command "insert" "mroads" '(83 -30) 1 1 0 )
(command "insert" "mroads" '(27 -30) 1 1 0 )
(command "insert" "mroads" '(31 -31) 1 1 0 )
(command "insert" "mroads" '(39 -22) 1 1 0 )
(command "insert" "mroads" '(13 -31) 1 1 0 )
(command "insert" "mroads" '(74 -31) 1 1 0 )
(command "insert" "mroads" '(3 -25) 1 1 0 )
(command "insert" "mroads" '(75 -30) 1 1 0 )
(command "insert" "mroads" '(4 -18) 1 1 0 )
(command "insert" "mroads" '(62 -30) 1 1 0 )
(command "insert" "mroads" '(5 -19) 1 1 0 )
(command "insert" "mroads" '(23 -32) 1 1 0 )
(command "insert" "mroads" '(6 -24) 1 1 0 )
(command "insert" "mroads" '(21 -16) 1 1 0 )
(command "insert" "mroads" '(17 -16) 1 1 0 )
(command "insert" "mroads" '(7 -29) 1 1 0 )
(command "insert" "mroads" '(22 -31) 1 1 0 )
(command "insert" "mroads" '(40 -23) 1 1 0 )
(command "insert" "mroads" '(59 -32) 1 1 0 )
(command "insert" "mroads" '(83 -31) 1 1 0 )
(command "insert" "mroads" '(23 -30) 1 1 0 )
(command "insert" "mroads" '(34 -18) 1 1 0 )
(command "insert" "mroads" '(67 -32) 1 1 0 )
(command "insert" "mroads" '(6 -20) 1 1 0 )
(command "insert" "mroads" '(70 -31) 1 1 0 )
(command "insert" "mroads" '(33 -15) 1 1 0 )
(command "insert" "mroads" '(71 -30) 1 1 0 )
(command "insert" "mroads" '(11 -18) 1 1 0 )
(command "insert" "mroads" '(35 -17) 1 1 0 )
(command "insert" "mroads" '(1 -24) 1 1 0 )
(command "insert" "mroads" '(39 -15) 1 1 0 )
(command "insert" "mroads" '(78 -30) 1 1 0 )
(command "insert" "mroads" '(2 -31) 1 1 0 )
(command "insert" "mroads" '(12 -30) 1 1 0 )
(command "insert" "mroads" '(41 -31) 1 1 0 )
(command "insert" "mroads" '(79 -31) 1 1 0 )
(command "insert" "mroads" '(3 -30) 1 1 0 )
(command "insert" "mroads" '(40 -17) 1 1 0 )
(command "insert" "mroads" '(4 -25) 1 1 0 )
(command "insert" "mroads" '(50 -31) 1 1 0 )
(command "insert" "mroads" '(5 -28) 1 1 0 )
(command "insert" "mroads" '(29 -15) 1 1 0 )
(command "insert" "mroads" '(6 -19) 1 1 0 )
(command "insert" "mroads" '(7 -26) 1 1 0 )
(command "insert" "mroads" '(58 -30) 1 1 0 )
(command "insert" "mroads" '(37 -32) 1 1 0 )
(command "insert" "mroads" '(59 -31) 1 1 0 )
(command "insert" "mroads" '(41 -16) 1 1 0 )
(command "insert" "mroads" '(45 -32) 1 1 0 )
(command "insert" "mroads" '(73 -32) 1 1 0 )
(command "insert" "mroads" '(106 -30) 1 1 0 )
(command "insert" "mroads" '(35 -22) 1 1 0 )
(command "insert" "mroads" '(24 -17) 1 1 0 )
(command "insert" "mroads" '(107 -31) 1 1 0 )
(command "insert" "mroads" '(81 -32) 1 1 0 )
(command "insert" "mroads" '(36 -17) 1 1 0 )
(command "insert" "mroads" '(13 -17) 1 1 0 )
(command "insert" "mroads" '(37 -20) 1 1 0 )
(command "insert" "mroads" '(2 -22) 1 1 0 )
(command "insert" "mroads" '(72 -30) 1 1 0 )
(command "insert" "mroads" '(38 -27) 1 1 0 )
(command "insert" "mroads" '(54 -30) 1 1 0 )
(command "insert" "mroads" '(34 -23) 1 1 0 )
(command "insert" "mroads" '(55 -31) 1 1 0 )
(command "insert" "mroads" '(116 -31) 1 1 0 )
(command "insert" "mroads" '(52 -32) 1 1 0 )
(command "insert" "mroads" '(7 -19) 1 1 0 )
(command "insert" "mroads" '(103 -31) 1 1 0 )
(command "insert" "mroads" '(88 -32) 1 1 0 )
(command "insert" "mroads" '(84 -31) 1 1 0 )
(command "insert" "mroads" '(8 -15) 1 1 0 )
(command "insert" "mroads" '(79 -30) 1 1 0 )
(command "insert" "mroads" '(34 -30) 1 1 0 )
(command "insert" "mroads" '(8 -21) 1 1 0 )
(command "insert" "mroads" '(35 -31) 1 1 0 )
(command "insert" "mroads" '(9 -16) 1 1 0 )
(command "insert" "mroads" '(14 -15) 1 1 0 )
(command "insert" "mroads" '(40 -28) 1 1 0 )
(command "insert" "mroads" '(96 -31) 1 1 0 )
(command "insert" "mroads" '(36 -24) 1 1 0 )
(command "insert" "mroads" '(78 -31) 1 1 0 )
(command "insert" "mroads" '(82 -30) 1 1 0 )
(command "insert" "mroads" '(97 -30) 1 1 0 )
(command "insert" "mroads" '(37 -29) 1 1 0 )
(command "insert" "mroads" '(26 -18) 1 1 0 )
(command "insert" "mroads" '(38 -18) 1 1 0 )
(command "insert" "mroads" '(103 -32) 1 1 0 )
(command "insert" "mroads" '(39 -27) 1 1 0 )
(command "insert" "mroads" '(4 -15) 1 1 0 )
(command "insert" "mroads" '(41 -25) 1 1 0 )
(command "insert" "mroads" '(3 -18) 1 1 0 )
(command "insert" "mroads" '(30 -30) 1 1 0 )
(command "insert" "mroads" '(4 -21) 1 1 0 )
(command "insert" "mroads" '(22 -32) 1 1 0 )
(command "insert" "mroads" '(20 -16) 1 1 0 )
(command "insert" "mroads" '(92 -31) 1 1 0 )
(command "insert" "mroads" '(16 -16) 1 1 0 )
(command "insert" "mroads" '(30 -32) 1 1 0 )
(command "insert" "mroads" '(93 -30) 1 1 0 )
(command "insert" "mroads" '(58 -32) 1 1 0 )
(command "insert" "mroads" '(32 -19) 1 1 0 )
(command "insert" "mroads" '(33 -18) 1 1 0 )
(command "insert" "mroads" '(66 -32) 1 1 0 )
(command "insert" "mroads" '(110 -32) 1 1 0 )
(command "insert" "mroads" '(34 -25) 1 1 0 )
(command "insert" "mroads" '(8 -28) 1 1 0 )
(command "insert" "mroads" '(57 -30) 1 1 0 )
(command "insert" "mroads" '(24 -31) 1 1 0 )
(command "insert" "mroads" '(10 -30) 1 1 0 )
(command "insert" "mroads" '(25 -30) 1 1 0 )
(command "insert" "mroads" '(11 -31) 1 1 0 )
(command "insert" "mroads" '(72 -31) 1 1 0 )
(command "insert" "mroads" '(27 -16) 1 1 0 )
(command "insert" "mroads" '(49 -32) 1 1 0 )
(command "insert" "mroads" '(73 -30) 1 1 0 )
(command "insert" "mroads" '(3 -27) 1 1 0 )
(command "insert" "mroads" '(4 -28) 1 1 0 )
(command "insert" "mroads" '(41 -15) 1 1 0 )
(command "insert" "mroads" '(5 -17) 1 1 0 )
(command "insert" "mroads" '(20 -31) 1 1 0 )
(command "insert" "mroads" '(40 -20) 1 1 0 )
(command "insert" "mroads" '(21 -30) 1 1 0 )
(command "insert" "mroads" '(7 -31) 1 1 0 )
(command "insert" "mroads" '(68 -31) 1 1 0 )
(command "insert" "mroads" '(36 -32) 1 1 0 )
(command "insert" "mroads" '(69 -30) 1 1 0 )
(command "insert" "mroads" '(34 -16) 1 1 0 )
(command "insert" "mroads" '(44 -32) 1 1 0 )
(command "insert" "mroads" '(72 -32) 1 1 0 )
(command "insert" "mroads" '(6 -16) 1 1 0 )
(command "insert" "mroads" '(80 -32) 1 1 0 )
(command "insert" "mroads" '(11 -20) 1 1 0 )
(command "insert" "mroads" '(35 -19) 1 1 0 )
(command "insert" "mroads" '(36 -20) 1 1 0 )
(command "insert" "mroads" '(1 -30) 1 1 0 )
(command "insert" "mroads" '(28 -18) 1 1 0 )
(command "insert" "mroads" '(2 -29) 1 1 0 )
(command "insert" "mroads" '(48 -31) 1 1 0 )
(command "insert" "mroads" '(29 -19) 1 1 0 )
(command "insert" "mroads" '(27 -15) 1 1 0 )
(command "insert" "mroads" '(49 -30) 1 1 0 )
(command "insert" "mroads" '(4 -27) 1 1 0 )
(command "insert" "mroads" '(41 -27) 1 1 0 )
(command "insert" "mroads" '(5 -26) 1 1 0 )
(command "insert" "mroads" '(51 -32) 1 1 0 )
(command "insert" "mroads" '(6 -17) 1 1 0 )
(command "insert" "mroads" '(30 -18) 1 1 0 )
(command "insert" "mroads" '(17 -15) 1 1 0 )
(command "insert" "mroads" '(41 -26) 1 1 0 )
(command "insert" "mroads" '(56 -30) 1 1 0 )
(command "insert" "mroads" '(57 -31) 1 1 0 )
(command "insert" "mroads" '(86 -31) 1 1 0 )
(command "insert" "mroads" '(104 -30) 1 1 0 )
(command "insert" "mroads" '(44 -31) 1 1 0 )
(command "insert" "mroads" '(23 -15) 1 1 0 )
(command "insert" "mroads" '(105 -31) 1 1 0 )
(command "insert" "mroads" '(45 -30) 1 1 0 )
(command "insert" "mroads" '(8 -16) 1 1 0 )
(command "insert" "mroads" '(35 -24) 1 1 0 )
(command "insert" "mroads" '(50 -32) 1 1 0 )
(command "insert" "mroads" '(24 -19) 1 1 0 )
(command "insert" "mroads" '(36 -19) 1 1 0 )
(command "insert" "mroads" '(1 -23) 1 1 0 )
(command "insert" "mroads" '(104 -31) 1 1 0 )
(command "insert" "mroads" '(13 -15) 1 1 0 )
(command "insert" "mroads" '(37 -18) 1 1 0 )
(command "insert" "mroads" '(102 -32) 1 1 0 )
(command "insert" "mroads" '(38 -25) 1 1 0 )
(command "insert" "mroads" '(53 -31) 1 1 0 )
(command "insert" "mroads" '(33 -25) 1 1 0 )
(command "insert" "mroads" '(39 -28) 1 1 0 )
(command "insert" "mroads" '(100 -30) 1 1 0 )
(command "insert" "mroads" '(115 -30) 1 1 0 )
(command "insert" "mroads" '(101 -31) 1 1 0 )
(command "insert" "mroads" '(21 -32) 1 1 0 )
(command "insert" "mroads" '(19 -16) 1 1 0 )
(command "insert" "mroads" '(31 -16) 1 1 0 )
(command "insert" "mroads" '(29 -32) 1 1 0 )
(command "insert" "mroads" '(41 -17) 1 1 0 )
(command "insert" "mroads" '(32 -30) 1 1 0 )
(command "insert" "mroads" '(65 -32) 1 1 0 )
(command "insert" "mroads" '(52 -31) 1 1 0 )
(command "insert" "mroads" '(7 -20) 1 1 0 )
(command "insert" "mroads" '(110 -31) 1 1 0 )
(command "insert" "mroads" '(34 -28) 1 1 0 )
(command "insert" "mroads" '(8 -23) 1 1 0 )
(command "insert" "mroads" '(80 -30) 1 1 0 )
(command "insert" "mroads" '(111 -30) 1 1 0 )
(command "insert" "mroads" '(57 -32) 1 1 0 )
(command "insert" "mroads" '(81 -31) 1 1 0 )
(command "insert" "mroads" '(36 -26) 1 1 0 )
(command "insert" "mroads" '(40 -24) 1 1 0 )
(command "insert" "mroads" '(37 -27) 1 1 0 )
(command "insert" "mroads" '(26 -16) 1 1 0 )
(command "insert" "mroads" '(38 -16) 1 1 0 )
(command "insert" "mroads" '(39 -21) 1 1 0 )
(command "insert" "mroads" '(28 -30) 1 1 0 )
(command "insert" "mroads" '(29 -31) 1 1 0 )
(command "insert" "mroads" '(3 -20) 1 1 0 )
(command "insert" "mroads" '(90 -31) 1 1 0 )
(command "insert" "mroads" '(4 -23) 1 1 0 )
(command "insert" "mroads" '(76 -30) 1 1 0 )
(command "insert" "mroads" '(91 -30) 1 1 0 )
(command "insert" "mroads" '(7 -27) 1 1 0 )
(command "insert" "mroads" '(5 -22) 1 1 0 )
(command "insert" "mroads" '(20 -18) 1 1 0 )
(command "insert" "mroads" '(77 -31) 1 1 0 )
(command "insert" "mroads" '(21 -19) 1 1 0 )
(command "insert" "mroads" '(7 -32) 1 1 0 )
(command "insert" "mroads" '(35 -32) 1 1 0 )
(command "insert" "mroads" '(113 -30) 1 1 0 )
(command "insert" "mroads" '(33 -16) 1 1 0 )
(command "insert" "mroads" '(43 -32) 1 1 0 )
(command "insert" "mroads" '(8 -30) 1 1 0 )
(command "insert" "mroads" '(40 -16) 1 1 0 )
(command "insert" "mroads" '(87 -32) 1 1 0 )
(command "insert" "mroads" '(9 -31) 1 1 0 )
(command "insert" "mroads" '(95 -32) 1 1 0 )
(command "insert" "mroads" '(15 -17) 1 1 0 )
(command "insert" "mroads" '(87 -30) 1 1 0 )
(command "insert" "mroads" '(11 -17) 1 1 0 )
(command "insert" "mroads" '(27 -18) 1 1 0 )
(command "insert" "mroads" '(1 -27) 1 1 0 )
(command "insert" "mroads" '(39 -18) 1 1 0 )
(command "insert" "mroads" '(14 -32) 1 1 0 )
(command "insert" "mroads" '(3 -29) 1 1 0 )
(command "insert" "mroads" '(4 -30) 1 1 0 )
(command "insert" "mroads" '(19 -30) 1 1 0 )
(command "layer" "m" "Commmer" "" )
(command "insert" "Commmer" '(32 -1) 1 1 0 )
(command "insert" "Commmer" '(23 -1) 1 1 0 )
(command "insert" "Commmer" '(21 -2) 1 1 0 )
(command "insert" "Commmer" '(16 -2) 1 1 0 )
(command "insert" "Commmer" '(15 -1) 1 1 0 )
(command "insert" "Commmer" '(28 -1) 1 1 0 )
(command "insert" "Commmer" '(25 -1) 1 1 0 )
(command "insert" "Commmer" '(27 -2) 1 1 0 )
(command "insert" "Commmer" '(32 -2) 1 1 0 )
(command "insert" "Commmer" '(18 -1) 1 1 0 )
(command "insert" "Commmer" '(31 -1) 1 1 0 )
(command "insert" "Commmer" '(22 -2) 1 1 0 )
(command "insert" "Commmer" '(21 -1) 1 1 0 )
(command "insert" "Commmer" '(23 -2) 1 1 0 )
(command "insert" "Commmer" '(17 -2) 1 1 0 )
(command "insert" "Commmer" '(28 -2) 1 1 0 )
(command "insert" "Commmer" '(34 -1) 1 1 0 )
(command "insert" "Commmer" '(24 -1) 1 1 0 )
(command "insert" "Commmer" '(33 -2) 1 1 0 )
(command "insert" "Commmer" '(30 -1) 1 1 0 )
(command "insert" "Commmer" '(27 -1) 1 1 0 )
(command "insert" "Commmer" '(18 -2) 1 1 0 )
(command "insert" "Commmer" '(20 -1) 1 1 0 )
(command "insert" "Commmer" '(17 -1) 1 1 0 )
(command "insert" "Commmer" '(19 -2) 1 1 0 )
(command "insert" "Commmer" '(29 -2) 1 1 0 )
(command "insert" "Commmer" '(24 -2) 1 1 0 )
(command "insert" "Commmer" '(34 -2) 1 1 0 )
(command "insert" "Commmer" '(35 -1) 1 1 0 )
(command "insert" "Commmer" '(26 -2) 1 1 0 )
(command "insert" "Commmer" '(33 -1) 1 1 0 )
(command "insert" "Commmer" '(35 -2) 1 1 0 )
(command "insert" "Commmer" '(26 -1) 1 1 0 )
(command "insert" "Commmer" '(15 -2) 1 1 0 )
(command "insert" "Commmer" '(20 -2) 1 1 0 )
(command "insert" "Commmer" '(30 -2) 1 1 0 )
(command "insert" "Commmer" '(16 -1) 1 1 0 )
(command "insert" "Commmer" '(29 -1) 1 1 0 )
(command "insert" "Commmer" '(31 -2) 1 1 0 )
(command "insert" "Commmer" '(25 -2) 1 1 0 )
(command "insert" "Commmer" '(22 -1) 1 1 0 )
(command "insert" "Commmer" '(19 -1) 1 1 0 )
(command "layer" "m" "ped" "" )
(command "insert" "ped" '(1 -3) 1 1 0 )
(command "insert" "ped" '(2 -18) 1 1 0 )
(command "insert" "ped" '(2 -8) 1 1 0 )
(command "insert" "ped" '(1 -17) 1 1 0 )
(command "insert" "ped" '(2 -1) 1 1 0 )
(command "insert" "ped" '(1 -15) 1 1 0 )
(command "insert" "ped" '(6 -2) 1 1 0 )
(command "insert" "ped" '(1 -6) 1 1 0 )
(command "insert" "ped" '(2 -12) 1 1 0 )
(command "insert" "ped" '(5 -1) 1 1 0 )
(command "insert" "ped" '(2 -5) 1 1 0 )
(command "insert" "ped" '(1 -11) 1 1 0 )
(command "insert" "ped" '(1 -20) 1 1 0 )
(command "insert" "ped" '(1 -2) 1 1 0 )
(command "insert" "ped" '(2 -19) 1 1 0 )
(command "insert" "ped" '(2 -9) 1 1 0 )
(command "insert" "ped" '(8 -1) 1 1 0 )
(command "insert" "ped" '(1 -16) 1 1 0 )
(command "insert" "ped" '(1 -14) 1 1 0 )
(command "insert" "ped" '(1 -5) 1 1 0 )
(command "insert" "ped" '(2 -13) 1 1 0 )
(command "insert" "ped" '(7 -2) 1 1 0 )
(command "insert" "ped" '(2 -2) 1 1 0 )
(command "insert" "ped" '(1 -10) 1 1 0 )
(command "insert" "ped" '(4 -1) 1 1 0 )
(command "insert" "ped" '(1 -1) 1 1 0 )
(command "insert" "ped" '(2 -16) 1 1 0 )
(command "insert" "ped" '(3 -2) 1 1 0 )
(command "insert" "ped" '(2 -6) 1 1 0 )
(command "insert" "ped" '(8 -2) 1 1 0 )
(command "insert" "ped" '(7 -1) 1 1 0 )
(command "insert" "ped" '(1 -13) 1 1 0 )
(command "insert" "ped" '(2 -20) 1 1 0 )
(command "insert" "ped" '(1 -4) 1 1 0 )
(command "insert" "ped" '(2 -10) 1 1 0 )
(command "insert" "ped" '(1 -19) 1 1 0 )
(command "insert" "ped" '(2 -3) 1 1 0 )
(command "insert" "ped" '(1 -9) 1 1 0 )
(command "insert" "ped" '(4 -2) 1 1 0 )
(command "insert" "ped" '(2 -14) 1 1 0 )
(command "insert" "ped" '(2 -17) 1 1 0 )
(command "insert" "ped" '(2 -7) 1 1 0 )
(command "insert" "ped" '(1 -12) 1 1 0 )
(command "insert" "ped" '(6 -1) 1 1 0 )
(command "insert" "ped" '(3 -1) 1 1 0 )
(command "insert" "ped" '(2 -11) 1 1 0 )
(command "insert" "ped" '(1 -18) 1 1 0 )
(command "insert" "ped" '(1 -8) 1 1 0 )
(command "insert" "ped" '(1 -7) 1 1 0 )
(command "insert" "ped" '(2 -15) 1 1 0 )
(command "insert" "ped" '(5 -2) 1 1 0 )
(command "insert" "ped" '(2 -4) 1 1 0 )
(command "layer" "m" "edge" "" )
(command "insert" "edge" '(45 -1) 1 1 0 )
(command "insert" "edge" '(47 -2) 1 1 0 )
(command "insert" "edge" '(44 -2) 1 1 0 )
(command "insert" "edge" '(41 -2) 1 1 0 )
(command "insert" "edge" '(38 -1) 1 1 0 )
(command "insert" "edge" '(46 -1) 1 1 0 )
(command "insert" "edge" '(43 -1) 1 1 0 )
(command "insert" "edge" '(36 -2) 1 1 0 )
(command "insert" "edge" '(45 -2) 1 1 0 )
(command "insert" "edge" '(37 -2) 1 1 0 )
(command "insert" "edge" '(42 -2) 1 1 0 )
(command "insert" "edge" '(41 -1) 1 1 0 )
(command "insert" "edge" '(44 -1) 1 1 0 )
(command "insert" "edge" '(40 -2) 1 1 0 )
(command "insert" "edge" '(39 -1) 1 1 0 )
(command "insert" "edge" '(36 -1) 1 1 0 )
(command "insert" "edge" '(43 -2) 1 1 0 )
(command "insert" "edge" '(47 -1) 1 1 0 )
(command "insert" "edge" '(40 -1) 1 1 0 )
(command "insert" "edge" '(38 -2) 1 1 0 )
(command "insert" "edge" '(42 -1) 1 1 0 )
(command "insert" "edge" '(37 -1) 1 1 0 )
(command "insert" "edge" '(46 -2) 1 1 0 )
(command "insert" "edge" '(39 -2) 1 1 0 )
(command "layer" "m" "Commmer" "" )
(command "insert" "Commmer" '(32 -1) 1 1 0 )
(command "insert" "Commmer" '(35 -1) 1 1 0 )
(command "insert" "Commmer" '(21 -2) 1 1 0 )
(command "insert" "Commmer" '(16 -2) 1 1 0 )
(command "insert" "Commmer" '(26 -2) 1 1 0 )
(command "insert" "Commmer" '(28 -1) 1 1 0 )
(command "insert" "Commmer" '(25 -1) 1 1 0 )
(command "insert" "Commmer" '(34 -2) 1 1 0 )
(command "insert" "Commmer" '(27 -2) 1 1 0 )
(command "insert" "Commmer" '(32 -2) 1 1 0 )
(command "insert" "Commmer" '(18 -1) 1 1 0 )
(command "insert" "Commmer" '(31 -1) 1 1 0 )
(command "insert" "Commmer" '(22 -2) 1 1 0 )
(command "insert" "Commmer" '(21 -1) 1 1 0 )
(command "insert" "Commmer" '(23 -2) 1 1 0 )
(command "insert" "Commmer" '(17 -2) 1 1 0 )
(command "insert" "Commmer" '(28 -2) 1 1 0 )
(command "insert" "Commmer" '(34 -1) 1 1 0 )
(command "insert" "Commmer" '(24 -1) 1 1 0 )
(command "insert" "Commmer" '(33 -2) 1 1 0 )
(command "insert" "Commmer" '(30 -1) 1 1 0 )
(command "insert" "Commmer" '(27 -1) 1 1 0 )
(command "insert" "Commmer" '(18 -2) 1 1 0 )
(command "insert" "Commmer" '(20 -1) 1 1 0 )
(command "insert" "Commmer" '(17 -1) 1 1 0 )
(command "insert" "Commmer" '(19 -2) 1 1 0 )
(command "insert" "Commmer" '(29 -2) 1 1 0 )
(command "insert" "Commmer" '(24 -2) 1 1 0 )
(command "insert" "Commmer" '(23 -1) 1 1 0 )
(command "insert" "Commmer" '(15 -1) 1 1 0 )
(command "insert" "Commmer" '(33 -1) 1 1 0 )
(command "insert" "Commmer" '(35 -2) 1 1 0 )
(command "insert" "Commmer" '(26 -1) 1 1 0 )
(command "insert" "Commmer" '(15 -2) 1 1 0 )
(command "insert" "Commmer" '(20 -2) 1 1 0 )
(command "insert" "Commmer" '(30 -2) 1 1 0 )
(command "insert" "Commmer" '(16 -1) 1 1 0 )
(command "insert" "Commmer" '(29 -1) 1 1 0 )
(command "insert" "Commmer" '(31 -2) 1 1 0 )
(command "insert" "Commmer" '(25 -2) 1 1 0 )
(command "insert" "Commmer" '(22 -1) 1 1 0 )
(command "insert" "Commmer" '(19 -1) 1 1 0 )
(command "layer" "m" "ped" "" )
(command "insert" "ped" '(1 -1) 1 1 0 )
(command "layer" "m" "ped" "" )
(command "insert" "ped" '(1 -3) 1 1 0 )
(command "insert" "ped" '(2 -18) 1 1 0 )
(command "insert" "ped" '(2 -8) 1 1 0 )
(command "insert" "ped" '(1 -17) 1 1 0 )
(command "insert" "ped" '(2 -1) 1 1 0 )
(command "insert" "ped" '(1 -15) 1 1 0 )
(command "insert" "ped" '(6 -2) 1 1 0 )
(command "insert" "ped" '(1 -6) 1 1 0 )
(command "insert" "ped" '(2 -12) 1 1 0 )
(command "insert" "ped" '(5 -1) 1 1 0 )
(command "insert" "ped" '(2 -5) 1 1 0 )
(command "insert" "ped" '(1 -11) 1 1 0 )
(command "insert" "ped" '(1 -20) 1 1 0 )
(command "insert" "ped" '(1 -2) 1 1 0 )
(command "insert" "ped" '(2 -19) 1 1 0 )
(command "insert" "ped" '(2 -9) 1 1 0 )
(command "insert" "ped" '(8 -1) 1 1 0 )
(command "insert" "ped" '(1 -16) 1 1 0 )
(command "insert" "ped" '(1 -14) 1 1 0 )
(command "insert" "ped" '(1 -5) 1 1 0 )
(command "insert" "ped" '(2 -13) 1 1 0 )
(command "insert" "ped" '(7 -2) 1 1 0 )
(command "insert" "ped" '(2 -2) 1 1 0 )
(command "insert" "ped" '(1 -10) 1 1 0 )
(command "insert" "ped" '(4 -1) 1 1 0 )
(command "insert" "ped" '(1 -1) 1 1 0 )
(command "insert" "ped" '(2 -16) 1 1 0 )
(command "insert" "ped" '(3 -2) 1 1 0 )
(command "insert" "ped" '(2 -6) 1 1 0 )
(command "insert" "ped" '(8 -2) 1 1 0 )
(command "insert" "ped" '(7 -1) 1 1 0 )
(command "insert" "ped" '(1 -13) 1 1 0 )
(command "insert" "ped" '(2 -20) 1 1 0 )
(command "insert" "ped" '(1 -4) 1 1 0 )
(command "insert" "ped" '(2 -10) 1 1 0 )
(command "insert" "ped" '(1 -19) 1 1 0 )
(command "insert" "ped" '(2 -3) 1 1 0 )
(command "insert" "ped" '(1 -9) 1 1 0 )
(command "insert" "ped" '(4 -2) 1 1 0 )
(command "insert" "ped" '(2 -14) 1 1 0 )
(command "insert" "ped" '(2 -17) 1 1 0 )
(command "insert" "ped" '(2 -7) 1 1 0 )
(command "insert" "ped" '(1 -12) 1 1 0 )
(command "insert" "ped" '(6 -1) 1 1 0 )
(command "insert" "ped" '(3 -1) 1 1 0 )
(command "insert" "ped" '(2 -11) 1 1 0 )
(command "insert" "ped" '(1 -18) 1 1 0 )
(command "insert" "ped" '(1 -8) 1 1 0 )
(command "insert" "ped" '(1 -7) 1 1 0 )
(command "insert" "ped" '(2 -15) 1 1 0 )
(command "insert" "ped" '(5 -2) 1 1 0 )
(command "insert" "ped" '(2 -4) 1 1 0 )
(command "layer" "m" "Res" "" )
(command "insert" "Res" '(13 -1) 1 1 0 )
(command "insert" "Res" '(12 -1) 1 1 0 )
(command "insert" "Res" '(9 -1) 1 1 0 )
(command "insert" "Res" '(12 -2) 1 1 0 )
(command "insert" "Res" '(9 -2) 1 1 0 )
(command "insert" "Res" '(11 -2) 1 1 0 )
(command "insert" "Res" '(14 -1) 1 1 0 )
(command "insert" "Res" '(11 -1) 1 1 0 )
(command "insert" "Res" '(10 -1) 1 1 0 )
(command "insert" "Res" '(13 -2) 1 1 0 )
(command "insert" "Res" '(14 -2) 1 1 0 )
(command "insert" "Res" '(10 -2) 1 1 0 )
(command "layer" "m" "Commmer" "" )
(command "insert" "Commmer" '(32 -1) 1 1 0 )
(command "insert" "Commmer" '(34 -2) 1 1 0 )
(command "insert" "Commmer" '(21 -2) 1 1 0 )
(command "insert" "Commmer" '(16 -2) 1 1 0 )
(command "insert" "Commmer" '(26 -2) 1 1 0 )
(command "insert" "Commmer" '(28 -1) 1 1 0 )
(command "insert" "Commmer" '(25 -1) 1 1 0 )
(command "insert" "Commmer" '(27 -2) 1 1 0 )
(command "insert" "Commmer" '(32 -2) 1 1 0 )
(command "insert" "Commmer" '(18 -1) 1 1 0 )
(command "insert" "Commmer" '(31 -1) 1 1 0 )
(command "insert" "Commmer" '(22 -2) 1 1 0 )
(command "insert" "Commmer" '(21 -1) 1 1 0 )
(command "insert" "Commmer" '(23 -2) 1 1 0 )
(command "insert" "Commmer" '(17 -2) 1 1 0 )
(command "insert" "Commmer" '(28 -2) 1 1 0 )
(command "insert" "Commmer" '(34 -1) 1 1 0 )
(command "insert" "Commmer" '(24 -1) 1 1 0 )
(command "insert" "Commmer" '(33 -2) 1 1 0 )
(command "insert" "Commmer" '(30 -1) 1 1 0 )
(command "insert" "Commmer" '(27 -1) 1 1 0 )
(command "insert" "Commmer" '(18 -2) 1 1 0 )
(command "insert" "Commmer" '(20 -1) 1 1 0 )
(command "insert" "Commmer" '(17 -1) 1 1 0 )
(command "insert" "Commmer" '(19 -2) 1 1 0 )
(command "insert" "Commmer" '(29 -2) 1 1 0 )
(command "insert" "Commmer" '(24 -2) 1 1 0 )
(command "insert" "Commmer" '(23 -1) 1 1 0 )
(command "insert" "Commmer" '(35 -1) 1 1 0 )
(command "insert" "Commmer" '(15 -1) 1 1 0 )
(command "insert" "Commmer" '(33 -1) 1 1 0 )
(command "insert" "Commmer" '(35 -2) 1 1 0 )
(command "insert" "Commmer" '(26 -1) 1 1 0 )
(command "insert" "Commmer" '(15 -2) 1 1 0 )
(command "insert" "Commmer" '(20 -2) 1 1 0 )
(command "insert" "Commmer" '(30 -2) 1 1 0 )
(command "insert" "Commmer" '(16 -1) 1 1 0 )
(command "insert" "Commmer" '(29 -1) 1 1 0 )
(command "insert" "Commmer" '(31 -2) 1 1 0 )
(command "insert" "Commmer" '(25 -2) 1 1 0 )
(command "insert" "Commmer" '(22 -1) 1 1 0 )
(command "insert" "Commmer" '(19 -1) 1 1 0 )
(command "layer" "m" "edge" "" )
(command "insert" "edge" '(54 -2) 1 1 0 )
(command "insert" "edge" '(55 -2) 1 1 0 )
(command "insert" "edge" '(56 -2) 1 1 0 )
(command "insert" "edge" '(55 -1) 1 1 0 )
(command "insert" "edge" '(56 -1) 1 1 0 )
(command "insert" "edge" '(54 -1) 1 1 0 )
(command "layer" "m" "Res" "" )
(command "insert" "Res" '(1 -34) 1 1 0 )
(command "insert" "Res" '(1 -35) 1 1 0 )
(command "insert" "Res" '(2 -35) 1 1 0 )
(command "insert" "Res" '(2 -34) 1 1 0 )
(command "insert" "Res" '(1 -33) 1 1 0 )
(command "insert" "Res" '(2 -33) 1 1 0 )
(command "layer" "m" "Commmer" "" )
(command "insert" "Commmer" '(218 -97) 1 1 0 )
(command "insert" "Commmer" '(218 -96) 1 1 0 )
(command "insert" "Commmer" '(218 -98) 1 1 0 )
(command "insert" "Commmer" '(216 -97) 1 1 0 )
(command "insert" "Commmer" '(217 -96) 1 1 0 )
(command "insert" "Commmer" '(217 -97) 1 1 0 )
(command "insert" "Commmer" '(217 -98) 1 1 0 )
(command "insert" "Commmer" '(216 -96) 1 1 0 )
(command "insert" "Commmer" '(216 -98) 1 1 0 )
(command "layer" "m" "Commmer" "" )
(command "insert" "Commmer" '(32 -1) 1 1 0 )
(command "insert" "Commmer" '(23 -1) 1 1 0 )
(command "insert" "Commmer" '(21 -2) 1 1 0 )
(command "insert" "Commmer" '(16 -2) 1 1 0 )
(command "insert" "Commmer" '(26 -2) 1 1 0 )
(command "insert" "Commmer" '(28 -1) 1 1 0 )
(command "insert" "Commmer" '(25 -1) 1 1 0 )
(command "insert" "Commmer" '(27 -2) 1 1 0 )
(command "insert" "Commmer" '(32 -2) 1 1 0 )
(command "insert" "Commmer" '(18 -1) 1 1 0 )
(command "insert" "Commmer" '(31 -1) 1 1 0 )
(command "insert" "Commmer" '(22 -2) 1 1 0 )
(command "insert" "Commmer" '(21 -1) 1 1 0 )
(command "insert" "Commmer" '(23 -2) 1 1 0 )
(command "insert" "Commmer" '(17 -2) 1 1 0 )
(command "insert" "Commmer" '(28 -2) 1 1 0 )
(command "insert" "Commmer" '(34 -1) 1 1 0 )
(command "insert" "Commmer" '(24 -1) 1 1 0 )
(command "insert" "Commmer" '(33 -2) 1 1 0 )
(command "insert" "Commmer" '(30 -1) 1 1 0 )
(command "insert" "Commmer" '(27 -1) 1 1 0 )
(command "insert" "Commmer" '(18 -2) 1 1 0 )
(command "insert" "Commmer" '(20 -1) 1 1 0 )
(command "insert" "Commmer" '(17 -1) 1 1 0 )
(command "insert" "Commmer" '(19 -2) 1 1 0 )
(command "insert" "Commmer" '(29 -2) 1 1 0 )
(command "insert" "Commmer" '(24 -2) 1 1 0 )
(command "insert" "Commmer" '(34 -2) 1 1 0 )
(command "insert" "Commmer" '(35 -1) 1 1 0 )
(command "insert" "Commmer" '(15 -1) 1 1 0 )
(command "insert" "Commmer" '(33 -1) 1 1 0 )
(command "insert" "Commmer" '(35 -2) 1 1 0 )
(command "insert" "Commmer" '(15 -2) 1 1 0 )
(command "insert" "Commmer" '(26 -1) 1 1 0 )
(command "insert" "Commmer" '(20 -2) 1 1 0 )
(command "insert" "Commmer" '(30 -2) 1 1 0 )
(command "insert" "Commmer" '(16 -1) 1 1 0 )
(command "insert" "Commmer" '(29 -1) 1 1 0 )
(command "insert" "Commmer" '(31 -2) 1 1 0 )
(command "insert" "Commmer" '(25 -2) 1 1 0 )
(command "insert" "Commmer" '(22 -1) 1 1 0 )
(command "insert" "Commmer" '(19 -1) 1 1 0 )
(command "layer" "m" "Res" "" )
(command "insert" "Res" '(1 -34) 1 1 0 )
(command "insert" "Res" '(1 -35) 1 1 0 )
(command "insert" "Res" '(2 -35) 1 1 0 )
(command "insert" "Res" '(2 -34) 1 1 0 )
(command "insert" "Res" '(1 -33) 1 1 0 )
(command "insert" "Res" '(2 -33) 1 1 0 )
(command "layer" "m" "Commmer" "" )
(command "insert" "Commmer" '(32 -1) 1 1 0 )
(command "insert" "Commmer" '(35 -1) 1 1 0 )
(command "insert" "Commmer" '(21 -2) 1 1 0 )
(command "insert" "Commmer" '(16 -2) 1 1 0 )
(command "insert" "Commmer" '(26 -2) 1 1 0 )
(command "insert" "Commmer" '(28 -1) 1 1 0 )
(command "insert" "Commmer" '(25 -1) 1 1 0 )
(command "insert" "Commmer" '(34 -2) 1 1 0 )
(command "insert" "Commmer" '(27 -2) 1 1 0 )
(command "insert" "Commmer" '(32 -2) 1 1 0 )
(command "insert" "Commmer" '(18 -1) 1 1 0 )
(command "insert" "Commmer" '(31 -1) 1 1 0 )
(command "insert" "Commmer" '(22 -2) 1 1 0 )
(command "insert" "Commmer" '(21 -1) 1 1 0 )
(command "insert" "Commmer" '(23 -2) 1 1 0 )
(command "insert" "Commmer" '(17 -2) 1 1 0 )
(command "insert" "Commmer" '(28 -2) 1 1 0 )
(command "insert" "Commmer" '(34 -1) 1 1 0 )
(command "insert" "Commmer" '(24 -1) 1 1 0 )
(command "insert" "Commmer" '(33 -2) 1 1 0 )
(command "insert" "Commmer" '(30 -1) 1 1 0 )
(command "insert" "Commmer" '(27 -1) 1 1 0 )
(command "insert" "Commmer" '(18 -2) 1 1 0 )
(command "insert" "Commmer" '(20 -1) 1 1 0 )
(command "insert" "Commmer" '(17 -1) 1 1 0 )
(command "insert" "Commmer" '(19 -2) 1 1 0 )
(command "insert" "Commmer" '(29 -2) 1 1 0 )
(command "insert" "Commmer" '(24 -2) 1 1 0 )
(command "insert" "Commmer" '(23 -1) 1 1 0 )
(command "insert" "Commmer" '(15 -1) 1 1 0 )
(command "insert" "Commmer" '(33 -1) 1 1 0 )
(command "insert" "Commmer" '(35 -2) 1 1 0 )
(command "insert" "Commmer" '(26 -1) 1 1 0 )
(command "insert" "Commmer" '(15 -2) 1 1 0 )
(command "insert" "Commmer" '(20 -2) 1 1 0 )
(command "insert" "Commmer" '(30 -2) 1 1 0 )
(command "insert" "Commmer" '(16 -1) 1 1 0 )
(command "insert" "Commmer" '(29 -1) 1 1 0 )
(command "insert" "Commmer" '(31 -2) 1 1 0 )
(command "insert" "Commmer" '(25 -2) 1 1 0 )
(command "insert" "Commmer" '(22 -1) 1 1 0 )
(command "insert" "Commmer" '(19 -1) 1 1 0 )
(command "layer" "m" "edge" "" )
(command "insert" "edge" '(44 -2) 1 1 0 )
(command "insert" "edge" '(47 -2) 1 1 0 )
(command "insert" "edge" '(45 -1) 1 1 0 )
(command "insert" "edge" '(40 -1) 1 1 0 )
(command "insert" "edge" '(38 -1) 1 1 0 )
(command "insert" "edge" '(46 -1) 1 1 0 )
(command "insert" "edge" '(43 -1) 1 1 0 )
(command "insert" "edge" '(40 -2) 1 1 0 )
(command "insert" "edge" '(45 -2) 1 1 0 )
(command "insert" "edge" '(37 -2) 1 1 0 )
(command "insert" "edge" '(42 -2) 1 1 0 )
(command "insert" "edge" '(37 -1) 1 1 0 )
(command "insert" "edge" '(44 -1) 1 1 0 )
(command "insert" "edge" '(41 -1) 1 1 0 )
(command "insert" "edge" '(39 -1) 1 1 0 )
(command "insert" "edge" '(36 -1) 1 1 0 )
(command "insert" "edge" '(43 -2) 1 1 0 )
(command "insert" "edge" '(47 -1) 1 1 0 )
(command "insert" "edge" '(41 -2) 1 1 0 )
(command "insert" "edge" '(38 -2) 1 1 0 )
(command "insert" "edge" '(42 -1) 1 1 0 )
(command "insert" "edge" '(36 -2) 1 1 0 )
(command "insert" "edge" '(46 -2) 1 1 0 )
(command "insert" "edge" '(39 -2) 1 1 0 )
(command "layer" "m" "ped" "" )
(command "insert" "ped" '(4 -41) 1 1 0 )
(command "insert" "ped" '(30 -41) 1 1 0 )
(command "insert" "ped" '(4 -36) 1 1 0 )
(command "insert" "ped" '(28 -41) 1 1 0 )
(command "insert" "ped" '(9 -41) 1 1 0 )
(command "insert" "ped" '(33 -36) 1 1 0 )
(command "insert" "ped" '(23 -41) 1 1 0 )
(command "insert" "ped" '(6 -35) 1 1 0 )
(command "insert" "ped" '(1 -36) 1 1 0 )
(command "insert" "ped" '(12 -40) 1 1 0 )
(command "insert" "ped" '(19 -40) 1 1 0 )
(command "insert" "ped" '(8 -41) 1 1 0 )
(command "insert" "ped" '(32 -38) 1 1 0 )
(command "insert" "ped" '(22 -41) 1 1 0 )
(command "insert" "ped" '(9 -36) 1 1 0 )
(command "insert" "ped" '(32 -41) 1 1 0 )
(command "insert" "ped" '(35 -36) 1 1 0 )
(command "insert" "ped" '(34 -36) 1 1 0 )
(command "insert" "ped" '(17 -36) 1 1 0 )
(command "insert" "ped" '(7 -41) 1 1 0 )
(command "insert" "ped" '(17 -41) 1 1 0 )
(command "insert" "ped" '(15 -34) 1 1 0 )
(command "insert" "ped" '(16 -38) 1 1 0 )
(command "insert" "ped" '(19 -39) 1 1 0 )
(command "insert" "ped" '(25 -38) 1 1 0 )
(command "insert" "ped" '(6 -41) 1 1 0 )
(command "insert" "ped" '(21 -40) 1 1 0 )
(command "insert" "ped" '(3 -40) 1 1 0 )
(command "insert" "ped" '(27 -39) 1 1 0 )
(command "insert" "ped" '(26 -37) 1 1 0 )
(command "insert" "ped" '(22 -39) 1 1 0 )
(command "insert" "ped" '(21 -37) 1 1 0 )
(command "insert" "ped" '(27 -40) 1 1 0 )
(command "insert" "ped" '(8 -38) 1 1 0 )
(command "insert" "ped" '(23 -38) 1 1 0 )
(command "insert" "ped" '(30 -39) 1 1 0 )
(command "insert" "ped" '(10 -41) 1 1 0 )
(command "insert" "ped" '(9 -39) 1 1 0 )
(command "insert" "ped" '(7 -35) 1 1 0 )
(command "insert" "ped" '(31 -38) 1 1 0 )
(command "insert" "ped" '(11 -36) 1 1 0 )
(command "insert" "ped" '(10 -36) 1 1 0 )
(command "insert" "ped" '(17 -39) 1 1 0 )
(command "insert" "ped" '(16 -41) 1 1 0 )
(command "insert" "ped" '(12 -39) 1 1 0 )
(command "insert" "ped" '(11 -41) 1 1 0 )
(command "insert" "ped" '(18 -36) 1 1 0 )
(command "insert" "ped" '(15 -33) 1 1 0 )
(command "insert" "ped" '(1 -38) 1 1 0 )
(command "insert" "ped" '(20 -37) 1 1 0 )
(command "insert" "ped" '(3 -39) 1 1 0 )
(command "insert" "ped" '(2 -37) 1 1 0 )
(command "insert" "ped" '(26 -38) 1 1 0 )
(command "insert" "ped" '(5 -40) 1 1 0 )
(command "insert" "ped" '(8 -35) 1 1 0 )
(command "insert" "ped" '(23 -37) 1 1 0 )
(command "insert" "ped" '(6 -39) 1 1 0 )
(command "insert" "ped" '(5 -37) 1 1 0 )
(command "insert" "ped" '(29 -40) 1 1 0 )
(command "insert" "ped" '(7 -38) 1 1 0 )
(command "insert" "ped" '(31 -37) 1 1 0 )
(command "insert" "ped" '(17 -34) 1 1 0 )
(command "insert" "ped" '(18 -41) 1 1 0 )
(command "insert" "ped" '(15 -36) 1 1 0 )
(command "insert" "ped" '(13 -41) 1 1 0 )
(command "insert" "ped" '(24 -36) 1 1 0 )
(command "insert" "ped" '(6 -40) 1 1 0 )
(command "insert" "ped" '(2 -38) 1 1 0 )
(command "insert" "ped" '(4 -37) 1 1 0 )
(command "insert" "ped" '(9 -40) 1 1 0 )
(command "insert" "ped" '(23 -40) 1 1 0 )
(command "insert" "ped" '(7 -37) 1 1 0 )
(command "insert" "ped" '(12 -41) 1 1 0 )
(command "insert" "ped" '(32 -39) 1 1 0 )
(command "insert" "ped" '(33 -38) 1 1 0 )
(command "insert" "ped" '(34 -37) 1 1 0 )
(command "insert" "ped" '(7 -40) 1 1 0 )
(command "insert" "ped" '(14 -40) 1 1 0 )
(command "insert" "ped" '(17 -40) 1 1 0 )
(command "insert" "ped" '(24 -40) 1 1 0 )
(command "insert" "ped" '(19 -38) 1 1 0 )
(command "insert" "ped" '(25 -37) 1 1 0 )
(command "insert" "ped" '(7 -33) 1 1 0 )
(command "insert" "ped" '(22 -36) 1 1 0 )
(command "insert" "ped" '(21 -36) 1 1 0 )
(command "insert" "ped" '(8 -39) 1 1 0 )
(command "insert" "ped" '(32 -36) 1 1 0 )
(command "insert" "ped" '(30 -36) 1 1 0 )
(command "insert" "ped" '(9 -38) 1 1 0 )
(command "insert" "ped" '(16 -39) 1 1 0 )
(command "insert" "ped" '(11 -39) 1 1 0 )
(command "insert" "ped" '(10 -37) 1 1 0 )
(command "insert" "ped" '(34 -38) 1 1 0 )
(command "insert" "ped" '(17 -38) 1 1 0 )
(command "insert" "ped" '(11 -40) 1 1 0 )
(command "insert" "ped" '(18 -37) 1 1 0 )
(command "insert" "ped" '(24 -37) 1 1 0 )
(command "insert" "ped" '(19 -37) 1 1 0 )
(command "insert" "ped" '(26 -40) 1 1 0 )
(command "insert" "ped" '(20 -38) 1 1 0 )
(command "insert" "ped" '(3 -38) 1 1 0 )
(command "insert" "ped" '(26 -39) 1 1 0 )
(command "insert" "ped" '(31 -40) 1 1 0 )
(command "insert" "ped" '(21 -39) 1 1 0 )
(command "insert" "ped" '(8 -36) 1 1 0 )
(command "insert" "ped" '(23 -36) 1 1 0 )
(command "insert" "ped" '(6 -36) 1 1 0 )
(command "insert" "ped" '(5 -36) 1 1 0 )
(command "insert" "ped" '(29 -39) 1 1 0 )
(command "insert" "ped" '(16 -36) 1 1 0 )
(command "insert" "ped" '(31 -36) 1 1 0 )
(command "insert" "ped" '(10 -38) 1 1 0 )
(command "insert" "ped" '(17 -33) 1 1 0 )
(command "insert" "ped" '(18 -38) 1 1 0 )
(command "insert" "ped" '(15 -39) 1 1 0 )
(command "insert" "ped" '(13 -40) 1 1 0 )
(command "insert" "ped" '(20 -40) 1 1 0 )
(command "insert" "ped" '(16 -35) 1 1 0 )
(command "insert" "ped" '(3 -37) 1 1 0 )
(command "insert" "ped" '(4 -38) 1 1 0 )
(command "insert" "ped" '(8 -33) 1 1 0 )
(command "insert" "ped" '(6 -33) 1 1 0 )
(command "insert" "ped" '(5 -39) 1 1 0 )
(command "insert" "ped" '(7 -36) 1 1 0 )
(command "insert" "ped" '(15 -41) 1 1 0 )
(command "insert" "ped" '(25 -41) 1 1 0 )
(command "insert" "ped" '(4 -40) 1 1 0 )
(command "insert" "ped" '(6 -38) 1 1 0 )
(command "insert" "ped" '(30 -40) 1 1 0 )
(command "insert" "ped" '(28 -40) 1 1 0 )
(command "insert" "ped" '(33 -37) 1 1 0 )
(command "insert" "ped" '(6 -34) 1 1 0 )
(command "insert" "ped" '(35 -38) 1 1 0 )
(command "insert" "ped" '(14 -41) 1 1 0 )
(command "insert" "ped" '(24 -41) 1 1 0 )
(command "insert" "ped" '(19 -41) 1 1 0 )
(command "insert" "ped" '(25 -36) 1 1 0 )
(command "insert" "ped" '(22 -37) 1 1 0 )
(command "insert" "ped" '(7 -39) 1 1 0 )
(command "insert" "ped" '(8 -40) 1 1 0 )
(command "insert" "ped" '(32 -37) 1 1 0 )
(command "insert" "ped" '(22 -40) 1 1 0 )
(command "insert" "ped" '(30 -37) 1 1 0 )
(command "insert" "ped" '(9 -37) 1 1 0 )
(command "insert" "ped" '(32 -40) 1 1 0 )
(command "insert" "ped" '(1 -37) 1 1 0 )
(command "insert" "ped" '(11 -38) 1 1 0 )
(command "insert" "ped" '(35 -37) 1 1 0 )
(command "insert" "ped" '(17 -37) 1 1 0 )
(command "insert" "ped" '(24 -39) 1 1 0 )
(command "insert" "ped" '(15 -35) 1 1 0 )
(command "insert" "ped" '(19 -36) 1 1 0 )
(command "insert" "ped" '(26 -41) 1 1 0 )
(command "insert" "ped" '(25 -39) 1 1 0 )
(command "insert" "ped" '(16 -33) 1 1 0 )
(command "insert" "ped" '(21 -41) 1 1 0 )
(command "insert" "ped" '(20 -39) 1 1 0 )
(command "insert" "ped" '(3 -41) 1 1 0 )
(command "insert" "ped" '(26 -36) 1 1 0 )
(command "insert" "ped" '(22 -38) 1 1 0 )
(command "insert" "ped" '(21 -38) 1 1 0 )
(command "insert" "ped" '(28 -39) 1 1 0 )
(command "insert" "ped" '(27 -41) 1 1 0 )
(command "insert" "ped" '(8 -37) 1 1 0 )
(command "insert" "ped" '(23 -39) 1 1 0 )
(command "insert" "ped" '(6 -37) 1 1 0 )
(command "insert" "ped" '(30 -38) 1 1 0 )
(command "insert" "ped" '(10 -40) 1 1 0 )
(command "insert" "ped" '(16 -37) 1 1 0 )
(command "insert" "ped" '(31 -39) 1 1 0 )
(command "insert" "ped" '(11 -37) 1 1 0 )
(command "insert" "ped" '(10 -39) 1 1 0 )
(command "insert" "ped" '(16 -40) 1 1 0 )
(command "insert" "ped" '(14 -39) 1 1 0 )
(command "insert" "ped" '(18 -39) 1 1 0 )
(command "insert" "ped" '(15 -38) 1 1 0 )
(command "insert" "ped" '(13 -39) 1 1 0 )
(command "insert" "ped" '(20 -41) 1 1 0 )
(command "insert" "ped" '(20 -36) 1 1 0 )
(command "insert" "ped" '(3 -36) 1 1 0 )
(command "insert" "ped" '(2 -36) 1 1 0 )
(command "insert" "ped" '(5 -41) 1 1 0 )
(command "insert" "ped" '(4 -39) 1 1 0 )
(command "insert" "ped" '(8 -34) 1 1 0 )
(command "insert" "ped" '(31 -41) 1 1 0 )
(command "insert" "ped" '(5 -38) 1 1 0 )
(command "insert" "ped" '(29 -41) 1 1 0 )
(command "insert" "ped" '(16 -34) 1 1 0 )
(command "insert" "ped" '(17 -35) 1 1 0 )
(command "insert" "ped" '(15 -40) 1 1 0 )
(command "insert" "ped" '(7 -34) 1 1 0 )
(command "insert" "ped" '(24 -38) 1 1 0 )
(command "insert" "ped" '(18 -40) 1 1 0 )
(command "insert" "ped" '(25 -40) 1 1 0 )
(command "insert" "ped" '(15 -37) 1 1 0 )
(command "layer" "m" "ped" "" )
(command "insert" "ped" '(1 -3) 1 1 0 )
(command "insert" "ped" '(2 -18) 1 1 0 )
(command "insert" "ped" '(2 -8) 1 1 0 )
(command "insert" "ped" '(1 -17) 1 1 0 )
(command "insert" "ped" '(2 -1) 1 1 0 )
(command "insert" "ped" '(1 -15) 1 1 0 )
(command "insert" "ped" '(6 -2) 1 1 0 )
(command "insert" "ped" '(1 -6) 1 1 0 )
(command "insert" "ped" '(2 -12) 1 1 0 )
(command "insert" "ped" '(5 -1) 1 1 0 )
(command "insert" "ped" '(2 -5) 1 1 0 )
(command "insert" "ped" '(1 -11) 1 1 0 )
(command "insert" "ped" '(7 -2) 1 1 0 )
(command "insert" "ped" '(1 -2) 1 1 0 )
(command "insert" "ped" '(2 -19) 1 1 0 )
(command "insert" "ped" '(2 -9) 1 1 0 )
(command "insert" "ped" '(8 -1) 1 1 0 )
(command "insert" "ped" '(1 -16) 1 1 0 )
(command "insert" "ped" '(1 -14) 1 1 0 )
(command "insert" "ped" '(1 -5) 1 1 0 )
(command "insert" "ped" '(2 -13) 1 1 0 )
(command "insert" "ped" '(1 -20) 1 1 0 )
(command "insert" "ped" '(2 -2) 1 1 0 )
(command "insert" "ped" '(1 -10) 1 1 0 )
(command "insert" "ped" '(4 -1) 1 1 0 )
(command "insert" "ped" '(1 -1) 1 1 0 )
(command "insert" "ped" '(2 -16) 1 1 0 )
(command "insert" "ped" '(3 -2) 1 1 0 )
(command "insert" "ped" '(2 -6) 1 1 0 )
(command "insert" "ped" '(8 -2) 1 1 0 )
(command "insert" "ped" '(7 -1) 1 1 0 )
(command "insert" "ped" '(1 -13) 1 1 0 )
(command "insert" "ped" '(2 -20) 1 1 0 )
(command "insert" "ped" '(1 -4) 1 1 0 )
(command "insert" "ped" '(2 -10) 1 1 0 )
(command "insert" "ped" '(1 -19) 1 1 0 )
(command "insert" "ped" '(2 -3) 1 1 0 )
(command "insert" "ped" '(1 -9) 1 1 0 )
(command "insert" "ped" '(4 -2) 1 1 0 )
(command "insert" "ped" '(2 -14) 1 1 0 )
(command "insert" "ped" '(2 -17) 1 1 0 )
(command "insert" "ped" '(2 -7) 1 1 0 )
(command "insert" "ped" '(1 -12) 1 1 0 )
(command "insert" "ped" '(6 -1) 1 1 0 )
(command "insert" "ped" '(3 -1) 1 1 0 )
(command "insert" "ped" '(2 -11) 1 1 0 )
(command "insert" "ped" '(1 -18) 1 1 0 )
(command "insert" "ped" '(1 -8) 1 1 0 )
(command "insert" "ped" '(1 -7) 1 1 0 )
(command "insert" "ped" '(2 -15) 1 1 0 )
(command "insert" "ped" '(5 -2) 1 1 0 )
(command "insert" "ped" '(2 -4) 1 1 0 )
(command "layer" "m" "Res" "" )
(command "insert" "Res" '(12 -2) 1 1 0 )
(command "insert" "Res" '(12 -1) 1 1 0 )
(command "insert" "Res" '(9 -1) 1 1 0 )
(command "insert" "Res" '(13 -1) 1 1 0 )
(command "insert" "Res" '(9 -2) 1 1 0 )
(command "insert" "Res" '(11 -2) 1 1 0 )
(command "insert" "Res" '(14 -1) 1 1 0 )
(command "insert" "Res" '(11 -1) 1 1 0 )
(command "insert" "Res" '(10 -1) 1 1 0 )
(command "insert" "Res" '(13 -2) 1 1 0 )
(command "insert" "Res" '(14 -2) 1 1 0 )
(command "insert" "Res" '(10 -2) 1 1 0 )
(command "layer" "m" "Commmer" "" )
(command "insert" "Commmer" '(51 -2) 1 1 0 )
(command "insert" "Commmer" '(53 -1) 1 1 0 )
(command "insert" "Commmer" '(52 -2) 1 1 0 )
(command "insert" "Commmer" '(51 -1) 1 1 0 )
(command "insert" "Commmer" '(52 -1) 1 1 0 )
(command "insert" "Commmer" '(53 -2) 1 1 0 )
(command "layer" "m" "Commmer" "" )
(command "insert" "Commmer" '(183 -68) 1 1 0 )
(command "insert" "Commmer" '(185 -68) 1 1 0 )
(command "insert" "Commmer" '(183 -66) 1 1 0 )
(command "insert" "Commmer" '(184 -68) 1 1 0 )
(command "insert" "Commmer" '(183 -67) 1 1 0 )
(command "insert" "Commmer" '(184 -67) 1 1 0 )
(command "insert" "Commmer" '(184 -66) 1 1 0 )
(command "insert" "Commmer" '(185 -66) 1 1 0 )
(command "insert" "Commmer" '(185 -67) 1 1 0 )
(command "layer" "m" "Commmer" "" )
(command "insert" "Commmer" '(32 -1) 1 1 0 )
(command "insert" "Commmer" '(23 -1) 1 1 0 )
(command "insert" "Commmer" '(21 -2) 1 1 0 )
(command "insert" "Commmer" '(16 -2) 1 1 0 )
(command "insert" "Commmer" '(15 -1) 1 1 0 )
(command "insert" "Commmer" '(28 -1) 1 1 0 )
(command "insert" "Commmer" '(25 -1) 1 1 0 )
(command "insert" "Commmer" '(27 -2) 1 1 0 )
(command "insert" "Commmer" '(32 -2) 1 1 0 )
(command "insert" "Commmer" '(18 -1) 1 1 0 )
(command "insert" "Commmer" '(31 -1) 1 1 0 )
(command "insert" "Commmer" '(22 -2) 1 1 0 )
(command "insert" "Commmer" '(21 -1) 1 1 0 )
(command "insert" "Commmer" '(23 -2) 1 1 0 )
(command "insert" "Commmer" '(17 -2) 1 1 0 )
(command "insert" "Commmer" '(28 -2) 1 1 0 )
(command "insert" "Commmer" '(34 -1) 1 1 0 )
(command "insert" "Commmer" '(24 -1) 1 1 0 )
(command "insert" "Commmer" '(33 -2) 1 1 0 )
(command "insert" "Commmer" '(30 -1) 1 1 0 )
(command "insert" "Commmer" '(27 -1) 1 1 0 )
(command "insert" "Commmer" '(18 -2) 1 1 0 )
(command "insert" "Commmer" '(20 -1) 1 1 0 )
(command "insert" "Commmer" '(17 -1) 1 1 0 )
(command "insert" "Commmer" '(19 -2) 1 1 0 )
(command "insert" "Commmer" '(29 -2) 1 1 0 )
(command "insert" "Commmer" '(24 -2) 1 1 0 )
(command "insert" "Commmer" '(34 -2) 1 1 0 )
(command "insert" "Commmer" '(35 -1) 1 1 0 )
(command "insert" "Commmer" '(26 -2) 1 1 0 )
(command "insert" "Commmer" '(33 -1) 1 1 0 )
(command "insert" "Commmer" '(35 -2) 1 1 0 )
(command "insert" "Commmer" '(26 -1) 1 1 0 )
(command "insert" "Commmer" '(15 -2) 1 1 0 )
(command "insert" "Commmer" '(20 -2) 1 1 0 )
(command "insert" "Commmer" '(30 -2) 1 1 0 )
(command "insert" "Commmer" '(16 -1) 1 1 0 )
(command "insert" "Commmer" '(29 -1) 1 1 0 )
(command "insert" "Commmer" '(31 -2) 1 1 0 )
(command "insert" "Commmer" '(25 -2) 1 1 0 )
(command "insert" "Commmer" '(22 -1) 1 1 0 )
(command "insert" "Commmer" '(19 -1) 1 1 0 )
(command "layer" "m" "Commmer" "" )
(command "insert" "Commmer" '(32 -1) 1 1 0 )
(command "insert" "Commmer" '(35 -1) 1 1 0 )
(command "insert" "Commmer" '(21 -2) 1 1 0 )
(command "insert" "Commmer" '(16 -2) 1 1 0 )
(command "insert" "Commmer" '(26 -2) 1 1 0 )
(command "insert" "Commmer" '(28 -1) 1 1 0 )
(command "insert" "Commmer" '(25 -1) 1 1 0 )
(command "insert" "Commmer" '(34 -2) 1 1 0 )
(command "insert" "Commmer" '(27 -2) 1 1 0 )
(command "insert" "Commmer" '(32 -2) 1 1 0 )
(command "insert" "Commmer" '(18 -1) 1 1 0 )
(command "insert" "Commmer" '(31 -1) 1 1 0 )
(command "insert" "Commmer" '(22 -2) 1 1 0 )
(command "insert" "Commmer" '(21 -1) 1 1 0 )
(command "insert" "Commmer" '(23 -2) 1 1 0 )
(command "insert" "Commmer" '(17 -2) 1 1 0 )
(command "insert" "Commmer" '(28 -2) 1 1 0 )
(command "insert" "Commmer" '(34 -1) 1 1 0 )
(command "insert" "Commmer" '(24 -1) 1 1 0 )
(command "insert" "Commmer" '(33 -2) 1 1 0 )
(command "insert" "Commmer" '(30 -1) 1 1 0 )
(command "insert" "Commmer" '(27 -1) 1 1 0 )
(command "insert" "Commmer" '(18 -2) 1 1 0 )
(command "insert" "Commmer" '(20 -1) 1 1 0 )
(command "insert" "Commmer" '(17 -1) 1 1 0 )
(command "insert" "Commmer" '(19 -2) 1 1 0 )
(command "insert" "Commmer" '(29 -2) 1 1 0 )
(command "insert" "Commmer" '(24 -2) 1 1 0 )
(command "insert" "Commmer" '(23 -1) 1 1 0 )
(command "insert" "Commmer" '(15 -1) 1 1 0 )
(command "insert" "Commmer" '(33 -1) 1 1 0 )
(command "insert" "Commmer" '(35 -2) 1 1 0 )
(command "insert" "Commmer" '(26 -1) 1 1 0 )
(command "insert" "Commmer" '(15 -2) 1 1 0 )
(command "insert" "Commmer" '(20 -2) 1 1 0 )
(command "insert" "Commmer" '(30 -2) 1 1 0 )
(command "insert" "Commmer" '(16 -1) 1 1 0 )
(command "insert" "Commmer" '(29 -1) 1 1 0 )
(command "insert" "Commmer" '(31 -2) 1 1 0 )
(command "insert" "Commmer" '(25 -2) 1 1 0 )
(command "insert" "Commmer" '(22 -1) 1 1 0 )
(command "insert" "Commmer" '(19 -1) 1 1 0 )
(command "layer" "m" "ped" "" )
(command "insert" "ped" '(1 -3) 1 1 0 )
(command "insert" "ped" '(2 -18) 1 1 0 )
(command "insert" "ped" '(2 -8) 1 1 0 )
(command "insert" "ped" '(1 -17) 1 1 0 )
(command "insert" "ped" '(2 -1) 1 1 0 )
(command "insert" "ped" '(1 -15) 1 1 0 )
(command "insert" "ped" '(6 -2) 1 1 0 )
(command "insert" "ped" '(1 -6) 1 1 0 )
(command "insert" "ped" '(2 -12) 1 1 0 )
(command "insert" "ped" '(5 -1) 1 1 0 )
(command "insert" "ped" '(2 -5) 1 1 0 )
(command "insert" "ped" '(1 -11) 1 1 0 )
(command "insert" "ped" '(7 -2) 1 1 0 )
(command "insert" "ped" '(1 -2) 1 1 0 )
(command "insert" "ped" '(2 -19) 1 1 0 )
(command "insert" "ped" '(2 -9) 1 1 0 )
(command "insert" "ped" '(8 -1) 1 1 0 )
(command "insert" "ped" '(1 -16) 1 1 0 )
(command "insert" "ped" '(1 -14) 1 1 0 )
(command "insert" "ped" '(1 -5) 1 1 0 )
(command "insert" "ped" '(2 -13) 1 1 0 )
(command "insert" "ped" '(1 -20) 1 1 0 )
(command "insert" "ped" '(2 -2) 1 1 0 )
(command "insert" "ped" '(1 -10) 1 1 0 )
(command "insert" "ped" '(4 -1) 1 1 0 )
(command "insert" "ped" '(1 -1) 1 1 0 )
(command "insert" "ped" '(2 -16) 1 1 0 )
(command "insert" "ped" '(3 -2) 1 1 0 )
(command "insert" "ped" '(2 -6) 1 1 0 )
(command "insert" "ped" '(8 -2) 1 1 0 )
(command "insert" "ped" '(7 -1) 1 1 0 )
(command "insert" "ped" '(1 -13) 1 1 0 )
(command "insert" "ped" '(2 -20) 1 1 0 )
(command "insert" "ped" '(1 -4) 1 1 0 )
(command "insert" "ped" '(2 -10) 1 1 0 )
(command "insert" "ped" '(1 -19) 1 1 0 )
(command "insert" "ped" '(2 -3) 1 1 0 )
(command "insert" "ped" '(1 -9) 1 1 0 )
(command "insert" "ped" '(4 -2) 1 1 0 )
(command "insert" "ped" '(2 -14) 1 1 0 )
(command "insert" "ped" '(2 -17) 1 1 0 )
(command "insert" "ped" '(2 -7) 1 1 0 )
(command "insert" "ped" '(1 -12) 1 1 0 )
(command "insert" "ped" '(6 -1) 1 1 0 )
(command "insert" "ped" '(3 -1) 1 1 0 )
(command "insert" "ped" '(2 -11) 1 1 0 )
(command "insert" "ped" '(1 -18) 1 1 0 )
(command "insert" "ped" '(1 -8) 1 1 0 )
(command "insert" "ped" '(1 -7) 1 1 0 )
(command "insert" "ped" '(2 -15) 1 1 0 )
(command "insert" "ped" '(5 -2) 1 1 0 )
(command "insert" "ped" '(2 -4) 1 1 0 )
(command "layer" "m" "Commmer" "" )
(command "insert" "Commmer" '(32 -1) 1 1 0 )
(command "insert" "Commmer" '(34 -2) 1 1 0 )
(command "insert" "Commmer" '(21 -2) 1 1 0 )
(command "insert" "Commmer" '(16 -2) 1 1 0 )
(command "insert" "Commmer" '(26 -2) 1 1 0 )
(command "insert" "Commmer" '(28 -1) 1 1 0 )
(command "insert" "Commmer" '(25 -1) 1 1 0 )
(command "insert" "Commmer" '(27 -2) 1 1 0 )
(command "insert" "Commmer" '(32 -2) 1 1 0 )
(command "insert" "Commmer" '(18 -1) 1 1 0 )
(command "insert" "Commmer" '(31 -1) 1 1 0 )
(command "insert" "Commmer" '(22 -2) 1 1 0 )
(command "insert" "Commmer" '(21 -1) 1 1 0 )
(command "insert" "Commmer" '(23 -2) 1 1 0 )
(command "insert" "Commmer" '(17 -2) 1 1 0 )
(command "insert" "Commmer" '(28 -2) 1 1 0 )
(command "insert" "Commmer" '(34 -1) 1 1 0 )
(command "insert" "Commmer" '(24 -1) 1 1 0 )
(command "insert" "Commmer" '(33 -2) 1 1 0 )
(command "insert" "Commmer" '(30 -1) 1 1 0 )
(command "insert" "Commmer" '(27 -1) 1 1 0 )
(command "insert" "Commmer" '(18 -2) 1 1 0 )
(command "insert" "Commmer" '(20 -1) 1 1 0 )
(command "insert" "Commmer" '(17 -1) 1 1 0 )
(command "insert" "Commmer" '(19 -2) 1 1 0 )
(command "insert" "Commmer" '(29 -2) 1 1 0 )
(command "insert" "Commmer" '(24 -2) 1 1 0 )
(command "insert" "Commmer" '(23 -1) 1 1 0 )
(command "insert" "Commmer" '(35 -1) 1 1 0 )
(command "insert" "Commmer" '(15 -1) 1 1 0 )
(command "insert" "Commmer" '(33 -1) 1 1 0 )
(command "insert" "Commmer" '(35 -2) 1 1 0 )
(command "insert" "Commmer" '(26 -1) 1 1 0 )
(command "insert" "Commmer" '(15 -2) 1 1 0 )
(command "insert" "Commmer" '(20 -2) 1 1 0 )
(command "insert" "Commmer" '(30 -2) 1 1 0 )
(command "insert" "Commmer" '(16 -1) 1 1 0 )
(command "insert" "Commmer" '(29 -1) 1 1 0 )
(command "insert" "Commmer" '(31 -2) 1 1 0 )
(command "insert" "Commmer" '(25 -2) 1 1 0 )
(command "insert" "Commmer" '(22 -1) 1 1 0 )
(command "insert" "Commmer" '(19 -1) 1 1 0 )
(command "layer" "m" "edge" "" )
(command "insert" "edge" '(44 -2) 1 1 0 )
(command "insert" "edge" '(47 -2) 1 1 0 )
(command "insert" "edge" '(45 -1) 1 1 0 )
(command "insert" "edge" '(40 -1) 1 1 0 )
(command "insert" "edge" '(38 -1) 1 1 0 )
(command "insert" "edge" '(46 -1) 1 1 0 )
(command "insert" "edge" '(43 -1) 1 1 0 )
(command "insert" "edge" '(40 -2) 1 1 0 )
(command "insert" "edge" '(45 -2) 1 1 0 )
(command "insert" "edge" '(36 -1) 1 1 0 )
(command "insert" "edge" '(42 -2) 1 1 0 )
(command "insert" "edge" '(37 -1) 1 1 0 )
(command "insert" "edge" '(44 -1) 1 1 0 )
(command "insert" "edge" '(41 -1) 1 1 0 )
(command "insert" "edge" '(39 -1) 1 1 0 )
(command "insert" "edge" '(37 -2) 1 1 0 )
(command "insert" "edge" '(43 -2) 1 1 0 )
(command "insert" "edge" '(47 -1) 1 1 0 )
(command "insert" "edge" '(41 -2) 1 1 0 )
(command "insert" "edge" '(38 -2) 1 1 0 )
(command "insert" "edge" '(42 -1) 1 1 0 )
(command "insert" "edge" '(36 -2) 1 1 0 )
(command "insert" "edge" '(46 -2) 1 1 0 )
(command "insert" "edge" '(39 -2) 1 1 0 )
(command "layer" "m" "edge" "" )
(command "insert" "edge" '(44 -2) 1 1 0 )
(command "insert" "edge" '(47 -2) 1 1 0 )
(command "insert" "edge" '(45 -1) 1 1 0 )
(command "insert" "edge" '(41 -2) 1 1 0 )
(command "insert" "edge" '(38 -1) 1 1 0 )
(command "insert" "edge" '(46 -1) 1 1 0 )
(command "insert" "edge" '(43 -1) 1 1 0 )
(command "insert" "edge" '(40 -2) 1 1 0 )
(command "insert" "edge" '(45 -2) 1 1 0 )
(command "insert" "edge" '(37 -2) 1 1 0 )
(command "insert" "edge" '(42 -2) 1 1 0 )
(command "insert" "edge" '(37 -1) 1 1 0 )
(command "insert" "edge" '(44 -1) 1 1 0 )
(command "insert" "edge" '(41 -1) 1 1 0 )
(command "insert" "edge" '(39 -1) 1 1 0 )
(command "insert" "edge" '(36 -1) 1 1 0 )
(command "insert" "edge" '(43 -2) 1 1 0 )
(command "insert" "edge" '(47 -1) 1 1 0 )
(command "insert" "edge" '(40 -1) 1 1 0 )
(command "insert" "edge" '(38 -2) 1 1 0 )
(command "insert" "edge" '(42 -1) 1 1 0 )
(command "insert" "edge" '(36 -2) 1 1 0 )
(command "insert" "edge" '(46 -2) 1 1 0 )
(command "insert" "edge" '(39 -2) 1 1 0 )
(command "layer" "m" "mroads" "" )
(command "insert" "mroads" '(5 -31) 1 1 0 )
(command "insert" "mroads" '(66 -31) 1 1 0 )
(command "insert" "mroads" '(6 -28) 1 1 0 )
(command "insert" "mroads" '(67 -30) 1 1 0 )
(command "insert" "mroads" '(7 -25) 1 1 0 )
(command "insert" "mroads" '(22 -19) 1 1 0 )
(command "insert" "mroads" '(18 -19) 1 1 0 )
(command "insert" "mroads" '(38 -21) 1 1 0 )
(command "insert" "mroads" '(114 -31) 1 1 0 )
(command "insert" "mroads" '(13 -32) 1 1 0 )
(command "insert" "mroads" '(35 -15) 1 1 0 )
(command "insert" "mroads" '(14 -31) 1 1 0 )
(command "insert" "mroads" '(15 -30) 1 1 0 )
(command "insert" "mroads" '(35 -21) 1 1 0 )
(command "insert" "mroads" '(12 -17) 1 1 0 )
(command "insert" "mroads" '(36 -22) 1 1 0 )
(command "insert" "mroads" '(1 -28) 1 1 0 )
(command "insert" "mroads" '(25 -15) 1 1 0 )
(command "insert" "mroads" '(39 -16) 1 1 0 )
(command "insert" "mroads" '(63 -30) 1 1 0 )
(command "insert" "mroads" '(37 -23) 1 1 0 )
(command "insert" "mroads" '(2 -27) 1 1 0 )
(command "insert" "mroads" '(109 -32) 1 1 0 )
(command "insert" "mroads" '(29 -17) 1 1 0 )
(command "insert" "mroads" '(31 -15) 1 1 0 )
(command "insert" "mroads" '(5 -24) 1 1 0 )
(command "insert" "mroads" '(20 -32) 1 1 0 )
(command "insert" "mroads" '(6 -23) 1 1 0 )
(command "insert" "mroads" '(30 -16) 1 1 0 )
(command "insert" "mroads" '(28 -32) 1 1 0 )
(command "insert" "mroads" '(7 -22) 1 1 0 )
(command "insert" "mroads" '(41 -23) 1 1 0 )
(command "insert" "mroads" '(42 -31) 1 1 0 )
(command "insert" "mroads" '(23 -19) 1 1 0 )
(command "insert" "mroads" '(21 -15) 1 1 0 )
(command "insert" "mroads" '(43 -30) 1 1 0 )
(command "insert" "mroads" '(116 -32) 1 1 0 )
(command "insert" "mroads" '(8 -18) 1 1 0 )
(command "insert" "mroads" '(11 -15) 1 1 0 )
(command "insert" "mroads" '(35 -26) 1 1 0 )
(command "insert" "mroads" '(9 -19) 1 1 0 )
(command "insert" "mroads" '(36 -29) 1 1 0 )
(command "insert" "mroads" '(1 -21) 1 1 0 )
(command "insert" "mroads" '(25 -16) 1 1 0 )
(command "insert" "mroads" '(29 -20) 1 1 0 )
(command "insert" "mroads" '(37 -16) 1 1 0 )
(command "insert" "mroads" '(98 -30) 1 1 0 )
(command "insert" "mroads" '(38 -31) 1 1 0 )
(command "insert" "mroads" '(99 -31) 1 1 0 )
(command "insert" "mroads" '(39 -30) 1 1 0 )
(command "insert" "mroads" '(3 -17) 1 1 0 )
(command "insert" "mroads" '(19 -18) 1 1 0 )
(command "insert" "mroads" '(7 -15) 1 1 0 )
(command "insert" "mroads" '(31 -18) 1 1 0 )
(command "insert" "mroads" '(46 -30) 1 1 0 )
(command "insert" "mroads" '(6 -32) 1 1 0 )
(command "insert" "mroads" '(34 -32) 1 1 0 )
(command "insert" "mroads" '(32 -16) 1 1 0 )
(command "insert" "mroads" '(94 -30) 1 1 0 )
(command "insert" "mroads" '(18 -31) 1 1 0 )
(command "insert" "mroads" '(42 -32) 1 1 0 )
(command "insert" "mroads" '(86 -32) 1 1 0 )
(command "insert" "mroads" '(34 -26) 1 1 0 )
(command "insert" "mroads" '(8 -25) 1 1 0 )
(command "insert" "mroads" '(94 -32) 1 1 0 )
(command "insert" "mroads" '(9 -20) 1 1 0 )
(command "insert" "mroads" '(10 -19) 1 1 0 )
(command "insert" "mroads" '(37 -25) 1 1 0 )
(command "insert" "mroads" '(26 -30) 1 1 0 )
(command "insert" "mroads" '(7 -18) 1 1 0 )
(command "insert" "mroads" '(38 -22) 1 1 0 )
(command "insert" "mroads" '(27 -31) 1 1 0 )
(command "insert" "mroads" '(40 -20) 1 1 0 )
(command "insert" "mroads" '(39 -23) 1 1 0 )
(command "insert" "mroads" '(88 -31) 1 1 0 )
(command "insert" "mroads" '(74 -30) 1 1 0 )
(command "insert" "mroads" '(89 -30) 1 1 0 )
(command "insert" "mroads" '(3 -22) 1 1 0 )
(command "insert" "mroads" '(75 -31) 1 1 0 )
(command "insert" "mroads" '(4 -17) 1 1 0 )
(command "insert" "mroads" '(5 -20) 1 1 0 )
(command "insert" "mroads" '(6 -27) 1 1 0 )
(command "insert" "mroads" '(21 -17) 1 1 0 )
(command "insert" "mroads" '(17 -17) 1 1 0 )
(command "insert" "mroads" '(22 -30) 1 1 0 )
(command "insert" "mroads" '(33 -22) 1 1 0 )
(command "insert" "mroads" '(23 -31) 1 1 0 )
(command "insert" "mroads" '(12 -32) 1 1 0 )
(command "insert" "mroads" '(34 -21) 1 1 0 )
(command "insert" "mroads" '(70 -30) 1 1 0 )
(command "insert" "mroads" '(85 -30) 1 1 0 )
(command "insert" "mroads" '(48 -32) 1 1 0 )
(command "insert" "mroads" '(71 -31) 1 1 0 )
(command "insert" "mroads" '(34 -15) 1 1 0 )
(command "insert" "mroads" '(11 -19) 1 1 0 )
(command "insert" "mroads" '(100 -32) 1 1 0 )
(command "insert" "mroads" '(27 -20) 1 1 0 )
(command "insert" "mroads" '(1 -25) 1 1 0 )
(command "insert" "mroads" '(108 -32) 1 1 0 )
(command "insert" "mroads" '(2 -30) 1 1 0 )
(command "insert" "mroads" '(3 -31) 1 1 0 )
(command "insert" "mroads" '(64 -31) 1 1 0 )
(command "insert" "mroads" '(4 -24) 1 1 0 )
(command "insert" "mroads" '(19 -32) 1 1 0 )
(command "insert" "mroads" '(62 -31) 1 1 0 )
(command "insert" "mroads" '(50 -30) 1 1 0 )
(command "insert" "mroads" '(65 -30) 1 1 0 )
(command "insert" "mroads" '(5 -29) 1 1 0 )
(command "insert" "mroads" '(27 -32) 1 1 0 )
(command "insert" "mroads" '(6 -18) 1 1 0 )
(command "insert" "mroads" '(101 -32) 1 1 0 )
(command "insert" "mroads" '(112 -31) 1 1 0 )
(command "insert" "mroads" '(41 -21) 1 1 0 )
(command "insert" "mroads" '(22 -17) 1 1 0 )
(command "insert" "mroads" '(79 -32) 1 1 0 )
(command "insert" "mroads" '(18 -17) 1 1 0 )
(command "insert" "mroads" '(23 -20) 1 1 0 )
(command "insert" "mroads" '(40 -31) 1 1 0 )
(command "insert" "mroads" '(115 -32) 1 1 0 )
(command "insert" "mroads" '(60 -31) 1 1 0 )
(command "insert" "mroads" '(61 -30) 1 1 0 )
(command "insert" "mroads" '(35 -23) 1 1 0 )
(command "insert" "mroads" '(24 -16) 1 1 0 )
(command "insert" "mroads" '(36 -16) 1 1 0 )
(command "insert" "mroads" '(108 -31) 1 1 0 )
(command "insert" "mroads" '(37 -21) 1 1 0 )
(command "insert" "mroads" '(2 -25) 1 1 0 )
(command "insert" "mroads" '(109 -30) 1 1 0 )
(command "insert" "mroads" '(7 -16) 1 1 0 )
(command "insert" "mroads" '(38 -26) 1 1 0 )
(command "insert" "mroads" '(40 -18) 1 1 0 )
(command "insert" "mroads" '(114 -32) 1 1 0 )
(command "insert" "mroads" '(116 -30) 1 1 0 )
(command "insert" "mroads" '(6 -21) 1 1 0 )
(command "insert" "mroads" '(111 -31) 1 1 0 )
(command "insert" "mroads" '(19 -15) 1 1 0 )
(command "insert" "mroads" '(41 -30) 1 1 0 )
(command "insert" "mroads" '(5 -32) 1 1 0 )
(command "insert" "mroads" '(33 -32) 1 1 0 )
(command "insert" "mroads" '(41 -32) 1 1 0 )
(command "insert" "mroads" '(7 -29) 1 1 0 )
(command "insert" "mroads" '(85 -32) 1 1 0 )
(command "insert" "mroads" '(9 -15) 1 1 0 )
(command "insert" "mroads" '(33 -26) 1 1 0 )
(command "insert" "mroads" '(22 -31) 1 1 0 )
(command "insert" "mroads" '(93 -32) 1 1 0 )
(command "insert" "mroads" '(8 -20) 1 1 0 )
(command "insert" "mroads" '(37 -15) 1 1 0 )
(command "insert" "mroads" '(35 -28) 1 1 0 )
(command "insert" "mroads" '(9 -17) 1 1 0 )
(command "insert" "mroads" '(96 -30) 1 1 0 )
(command "insert" "mroads" '(36 -31) 1 1 0 )
(command "insert" "mroads" '(15 -15) 1 1 0 )
(command "insert" "mroads" '(97 -31) 1 1 0 )
(command "insert" "mroads" '(37 -30) 1 1 0 )
(command "insert" "mroads" '(38 -29) 1 1 0 )
(command "insert" "mroads" '(83 -31) 1 1 0 )
(command "insert" "mroads" '(39 -24) 1 1 0 )
(command "insert" "mroads" '(5 -15) 1 1 0 )
(command "insert" "mroads" '(3 -19) 1 1 0 )
(command "insert" "mroads" '(4 -20) 1 1 0 )
(command "insert" "mroads" '(19 -20) 1 1 0 )
(command "insert" "mroads" '(92 -30) 1 1 0 )
(command "insert" "mroads" '(16 -31) 1 1 0 )
(command "insert" "mroads" '(93 -31) 1 1 0 )
(command "insert" "mroads" '(17 -30) 1 1 0 )
(command "insert" "mroads" '(32 -18) 1 1 0 )
(command "insert" "mroads" '(11 -32) 1 1 0 )
(command "insert" "mroads" '(33 -19) 1 1 0 )
(command "insert" "mroads" '(40 -29) 1 1 0 )
(command "insert" "mroads" '(8 -27) 1 1 0 )
(command "insert" "mroads" '(63 -32) 1 1 0 )
(command "insert" "mroads" '(5 -21) 1 1 0 )
(command "insert" "mroads" '(24 -30) 1 1 0 )
(command "insert" "mroads" '(14 -17) 1 1 0 )
(command "insert" "mroads" '(71 -32) 1 1 0 )
(command "insert" "mroads" '(10 -17) 1 1 0 )
(command "insert" "mroads" '(25 -31) 1 1 0 )
(command "insert" "mroads" '(99 -32) 1 1 0 )
(command "insert" "mroads" '(111 -32) 1 1 0 )
(command "insert" "mroads" '(107 -32) 1 1 0 )
(command "insert" "mroads" '(38 -20) 1 1 0 )
(command "insert" "mroads" '(12 -31) 1 1 0 )
(command "insert" "mroads" '(27 -17) 1 1 0 )
(command "insert" "mroads" '(39 -17) 1 1 0 )
(command "insert" "mroads" '(13 -30) 1 1 0 )
(command "insert" "mroads" '(41 -24) 1 1 0 )
(command "insert" "mroads" '(3 -24) 1 1 0 )
(command "insert" "mroads" '(56 -32) 1 1 0 )
(command "insert" "mroads" '(4 -19) 1 1 0 )
(command "insert" "mroads" '(26 -32) 1 1 0 )
(command "insert" "mroads" '(5 -18) 1 1 0 )
(command "insert" "mroads" '(20 -30) 1 1 0 )
(command "insert" "mroads" '(6 -25) 1 1 0 )
(command "insert" "mroads" '(21 -31) 1 1 0 )
(command "insert" "mroads" '(40 -22) 1 1 0 )
(command "insert" "mroads" '(78 -32) 1 1 0 )
(command "insert" "mroads" '(41 -18) 1 1 0 )
(command "insert" "mroads" '(18 -20) 1 1 0 )
(command "insert" "mroads" '(33 -20) 1 1 0 )
(command "insert" "mroads" '(69 -31) 1 1 0 )
(command "insert" "mroads" '(34 -19) 1 1 0 )
(command "insert" "mroads" '(32 -15) 1 1 0 )
(command "insert" "mroads" '(15 -32) 1 1 0 )
(command "insert" "mroads" '(64 -32) 1 1 0 )
(command "insert" "mroads" '(35 -16) 1 1 0 )
(command "insert" "mroads" '(38 -15) 1 1 0 )
(command "insert" "mroads" '(77 -32) 1 1 0 )
(command "insert" "mroads" '(1 -31) 1 1 0 )
(command "insert" "mroads" '(28 -17) 1 1 0 )
(command "insert" "mroads" '(2 -28) 1 1 0 )
(command "insert" "mroads" '(48 -30) 1 1 0 )
(command "insert" "mroads" '(113 -32) 1 1 0 )
(command "insert" "mroads" '(49 -31) 1 1 0 )
(command "insert" "mroads" '(4 -26) 1 1 0 )
(command "insert" "mroads" '(28 -15) 1 1 0 )
(command "insert" "mroads" '(5 -27) 1 1 0 )
(command "insert" "mroads" '(40 -26) 1 1 0 )
(command "insert" "mroads" '(4 -32) 1 1 0 )
(command "insert" "mroads" '(7 -21) 1 1 0 )
(command "insert" "mroads" '(18 -15) 1 1 0 )
(command "insert" "mroads" '(40 -32) 1 1 0 )
(command "insert" "mroads" '(34 -20) 1 1 0 )
(command "insert" "mroads" '(58 -31) 1 1 0 )
(command "insert" "mroads" '(44 -30) 1 1 0 )
(command "insert" "mroads" '(59 -30) 1 1 0 )
(command "insert" "mroads" '(92 -32) 1 1 0 )
(command "insert" "mroads" '(45 -31) 1 1 0 )
(command "insert" "mroads" '(6 -17) 1 1 0 )
(command "insert" "mroads" '(106 -31) 1 1 0 )
(command "insert" "mroads" '(35 -25) 1 1 0 )
(command "insert" "mroads" '(24 -18) 1 1 0 )
(command "insert" "mroads" '(107 -30) 1 1 0 )
(command "insert" "mroads" '(36 -18) 1 1 0 )
(command "insert" "mroads" '(25 -19) 1 1 0 )
(command "insert" "mroads" '(13 -16) 1 1 0 )
(command "insert" "mroads" '(37 -19) 1 1 0 )
(command "insert" "mroads" '(2 -23) 1 1 0 )
(command "insert" "mroads" '(38 -24) 1 1 0 )
(command "insert" "mroads" '(39 -29) 1 1 0 )
(command "insert" "mroads" '(54 -31) 1 1 0 )
(command "insert" "mroads" '(115 -31) 1 1 0 )
(command "insert" "mroads" '(55 -30) 1 1 0 )
(command "insert" "mroads" '(22 -20) 1 1 0 )
(command "insert" "mroads" '(30 -20) 1 1 0 )
(command "insert" "mroads" '(19 -17) 1 1 0 )
(command "insert" "mroads" '(102 -31) 1 1 0 )
(command "insert" "mroads" '(41 -28) 1 1 0 )
(command "insert" "mroads" '(31 -17) 1 1 0 )
(command "insert" "mroads" '(103 -30) 1 1 0 )
(command "insert" "mroads" '(10 -32) 1 1 0 )
(command "insert" "mroads" '(22 -32) 1 1 0 )
(command "insert" "mroads" '(18 -32) 1 1 0 )
(command "insert" "mroads" '(33 -24) 1 1 0 )
(command "insert" "mroads" '(62 -32) 1 1 0 )
(command "insert" "mroads" '(110 -30) 1 1 0 )
(command "insert" "mroads" '(34 -31) 1 1 0 )
(command "insert" "mroads" '(8 -22) 1 1 0 )
(command "insert" "mroads" '(23 -17) 1 1 0 )
(command "insert" "mroads" '(70 -32) 1 1 0 )
(command "insert" "mroads" '(35 -30) 1 1 0 )
(command "insert" "mroads" '(98 -32) 1 1 0 )
(command "insert" "mroads" '(36 -25) 1 1 0 )
(command "insert" "mroads" '(10 -20) 1 1 0 )
(command "insert" "mroads" '(25 -20) 1 1 0 )
(command "insert" "mroads" '(82 -31) 1 1 0 )
(command "insert" "mroads" '(106 -32) 1 1 0 )
(command "insert" "mroads" '(37 -28) 1 1 0 )
(command "insert" "mroads" '(26 -19) 1 1 0 )
(command "insert" "mroads" '(38 -19) 1 1 0 )
(command "insert" "mroads" '(3 -15) 1 1 0 )
(command "insert" "mroads" '(39 -26) 1 1 0 )
(command "insert" "mroads" '(51 -31) 1 1 0 )
(command "insert" "mroads" '(3 -21) 1 1 0 )
(command "insert" "mroads" '(25 -32) 1 1 0 )
(command "insert" "mroads" '(90 -30) 1 1 0 )
(command "insert" "mroads" '(30 -31) 1 1 0 )
(command "insert" "mroads" '(4 -22) 1 1 0 )
(command "insert" "mroads" '(91 -31) 1 1 0 )
(command "insert" "mroads" '(31 -30) 1 1 0 )
(command "insert" "mroads" '(5 -23) 1 1 0 )
(command "insert" "mroads" '(20 -17) 1 1 0 )
(command "insert" "mroads" '(16 -17) 1 1 0 )
(command "insert" "mroads" '(21 -20) 1 1 0 )
(command "insert" "mroads" '(32 -20) 1 1 0 )
(command "insert" "mroads" '(33 -17) 1 1 0 )
(command "insert" "mroads" '(34 -22) 1 1 0 )
(command "insert" "mroads" '(8 -29) 1 1 0 )
(command "insert" "mroads" '(61 -31) 1 1 0 )
(command "insert" "mroads" '(86 -30) 1 1 0 )
(command "insert" "mroads" '(10 -31) 1 1 0 )
(command "insert" "mroads" '(6 -19) 1 1 0 )
(command "insert" "mroads" '(87 -31) 1 1 0 )
(command "insert" "mroads" '(11 -30) 1 1 0 )
(command "insert" "mroads" '(76 -32) 1 1 0 )
(command "insert" "mroads" '(27 -19) 1 1 0 )
(command "insert" "mroads" '(39 -19) 1 1 0 )
(command "insert" "mroads" '(28 -20) 1 1 0 )
(command "insert" "mroads" '(3 -26) 1 1 0 )
(command "insert" "mroads" '(40 -15) 1 1 0 )
(command "insert" "mroads" '(4 -29) 1 1 0 )
(command "insert" "mroads" '(19 -31) 1 1 0 )
(command "insert" "mroads" '(7 -26) 1 1 0 )
(command "insert" "mroads" '(5 -16) 1 1 0 )
(command "insert" "mroads" '(3 -32) 1 1 0 )
(command "insert" "mroads" '(66 -30) 1 1 0 )
(command "insert" "mroads" '(6 -31) 1 1 0 )
(command "insert" "mroads" '(67 -31) 1 1 0 )
(command "insert" "mroads" '(7 -30) 1 1 0 )
(command "insert" "mroads" '(22 -18) 1 1 0 )
(command "insert" "mroads" '(55 -32) 1 1 0 )
(command "insert" "mroads" '(18 -18) 1 1 0 )
(command "insert" "mroads" '(83 -32) 1 1 0 )
(command "insert" "mroads" '(114 -30) 1 1 0 )
(command "insert" "mroads" '(34 -17) 1 1 0 )
(command "insert" "mroads" '(91 -32) 1 1 0 )
(command "insert" "mroads" '(14 -30) 1 1 0 )
(command "insert" "mroads" '(36 -15) 1 1 0 )
(command "insert" "mroads" '(15 -31) 1 1 0 )
(command "insert" "mroads" '(35 -18) 1 1 0 )
(command "insert" "mroads" '(12 -16) 1 1 0 )
(command "insert" "mroads" '(36 -21) 1 1 0 )
(command "insert" "mroads" '(1 -29) 1 1 0 )
(command "insert" "mroads" '(63 -31) 1 1 0 )
(command "insert" "mroads" '(28 -19) 1 1 0 )
(command "insert" "mroads" '(2 -26) 1 1 0 )
(command "insert" "mroads" '(26 -15) 1 1 0 )
(command "insert" "mroads" '(12 -15) 1 1 0 )
(command "insert" "mroads" '(29 -18) 1 1 0 )
(command "insert" "mroads" '(5 -25) 1 1 0 )
(command "insert" "mroads" '(16 -15) 1 1 0 )
(command "insert" "mroads" '(6 -22) 1 1 0 )
(command "insert" "mroads" '(30 -19) 1 1 0 )
(command "insert" "mroads" '(41 -25) 1 1 0 )
(command "insert" "mroads" '(56 -31) 1 1 0 )
(command "insert" "mroads" '(9 -32) 1 1 0 )
(command "insert" "mroads" '(42 -30) 1 1 0 )
(command "insert" "mroads" '(23 -16) 1 1 0 )
(command "insert" "mroads" '(43 -31) 1 1 0 )
(command "insert" "mroads" '(17 -32) 1 1 0 )
(command "insert" "mroads" '(22 -15) 1 1 0 )
(command "insert" "mroads" '(61 -32) 1 1 0 )
(command "insert" "mroads" '(52 -30) 1 1 0 )
(command "insert" "mroads" '(105 -30) 1 1 0 )
(command "insert" "mroads" '(69 -32) 1 1 0 )
(command "insert" "mroads" '(34 -24) 1 1 0 )
(command "insert" "mroads" '(8 -17) 1 1 0 )
(command "insert" "mroads" '(97 -32) 1 1 0 )
(command "insert" "mroads" '(35 -27) 1 1 0 )
(command "insert" "mroads" '(24 -20) 1 1 0 )
(command "insert" "mroads" '(105 -32) 1 1 0 )
(command "insert" "mroads" '(36 -28) 1 1 0 )
(command "insert" "mroads" '(1 -22) 1 1 0 )
(command "insert" "mroads" '(6 -29) 1 1 0 )
(command "insert" "mroads" '(37 -17) 1 1 0 )
(command "insert" "mroads" '(2 -21) 1 1 0 )
(command "insert" "mroads" '(38 -30) 1 1 0 )
(command "insert" "mroads" '(53 -30) 1 1 0 )
(command "insert" "mroads" '(112 -32) 1 1 0 )
(command "insert" "mroads" '(39 -31) 1 1 0 )
(command "insert" "mroads" '(100 -31) 1 1 0 )
(command "insert" "mroads" '(24 -32) 1 1 0 )
(command "insert" "mroads" '(101 -30) 1 1 0 )
(command "insert" "mroads" '(19 -19) 1 1 0 )
(command "insert" "mroads" '(31 -19) 1 1 0 )
(command "insert" "mroads" '(20 -20) 1 1 0 )
(command "insert" "mroads" '(47 -31) 1 1 0 )
(command "insert" "mroads" '(32 -31) 1 1 0 )
(command "insert" "mroads" '(18 -30) 1 1 0 )
(command "insert" "mroads" '(33 -30) 1 1 0 )
(command "insert" "mroads" '(34 -29) 1 1 0 )
(command "insert" "mroads" '(8 -24) 1 1 0 )
(command "insert" "mroads" '(39 -32) 1 1 0 )
(command "insert" "mroads" '(80 -31) 1 1 0 )
(command "insert" "mroads" '(81 -30) 1 1 0 )
(command "insert" "mroads" '(36 -27) 1 1 0 )
(command "insert" "mroads" '(10 -18) 1 1 0 )
(command "insert" "mroads" '(75 -32) 1 1 0 )
(command "insert" "mroads" '(37 -26) 1 1 0 )
(command "insert" "mroads" '(26 -17) 1 1 0 )
(command "insert" "mroads" '(38 -17) 1 1 0 )
(command "insert" "mroads" '(39 -20) 1 1 0 )
(command "insert" "mroads" '(88 -30) 1 1 0 )
(command "insert" "mroads" '(28 -31) 1 1 0 )
(command "insert" "mroads" '(89 -31) 1 1 0 )
(command "insert" "mroads" '(29 -30) 1 1 0 )
(command "insert" "mroads" '(3 -23) 1 1 0 )
(command "insert" "mroads" '(4 -16) 1 1 0 )
(command "insert" "mroads" '(2 -32) 1 1 0 )
(command "insert" "mroads" '(76 -31) 1 1 0 )
(command "insert" "mroads" '(46 -32) 1 1 0 )
(command "insert" "mroads" '(20 -19) 1 1 0 )
(command "insert" "mroads" '(33 -29) 1 1 0 )
(command "insert" "mroads" '(77 -30) 1 1 0 )
(command "insert" "mroads" '(6 -26) 1 1 0 )
(command "insert" "mroads" '(21 -18) 1 1 0 )
(command "insert" "mroads" '(54 -32) 1 1 0 )
(command "insert" "mroads" '(33 -23) 1 1 0 )
(command "insert" "mroads" '(90 -32) 1 1 0 )
(command "insert" "mroads" '(84 -30) 1 1 0 )
(command "insert" "mroads" '(8 -31) 1 1 0 )
(command "insert" "mroads" '(95 -31) 1 1 0 )
(command "insert" "mroads" '(85 -31) 1 1 0 )
(command "insert" "mroads" '(9 -30) 1 1 0 )
(command "insert" "mroads" '(15 -16) 1 1 0 )
(command "insert" "mroads" '(11 -16) 1 1 0 )
(command "insert" "mroads" '(1 -26) 1 1 0 )
(command "insert" "mroads" '(40 -21) 1 1 0 )
(command "insert" "mroads" '(73 -31) 1 1 0 )
(command "insert" "mroads" '(3 -28) 1 1 0 )
(command "insert" "mroads" '(64 -30) 1 1 0 )
(command "insert" "mroads" '(4 -31) 1 1 0 )
(command "insert" "mroads" '(65 -31) 1 1 0 )
(command "insert" "mroads" '(5 -30) 1 1 0 )
(command "insert" "mroads" '(40 -23) 1 1 0 )
(command "insert" "mroads" '(112 -30) 1 1 0 )
(command "insert" "mroads" '(8 -32) 1 1 0 )
(command "insert" "mroads" '(41 -22) 1 1 0 )
(command "insert" "mroads" '(22 -16) 1 1 0 )
(command "insert" "mroads" '(113 -31) 1 1 0 )
(command "insert" "mroads" '(18 -16) 1 1 0 )
(command "insert" "mroads" '(16 -32) 1 1 0 )
(command "insert" "mroads" '(60 -32) 1 1 0 )
(command "insert" "mroads" '(68 -32) 1 1 0 )
(command "insert" "mroads" '(96 -32) 1 1 0 )
(command "insert" "mroads" '(60 -30) 1 1 0 )
(command "insert" "mroads" '(104 -32) 1 1 0 )
(command "insert" "mroads" '(35 -20) 1 1 0 )
(command "insert" "mroads" '(24 -15) 1 1 0 )
(command "insert" "mroads" '(36 -23) 1 1 0 )
(command "insert" "mroads" '(108 -30) 1 1 0 )
(command "insert" "mroads" '(37 -22) 1 1 0 )
(command "insert" "mroads" '(2 -24) 1 1 0 )
(command "insert" "mroads" '(109 -31) 1 1 0 )
(command "insert" "mroads" '(29 -16) 1 1 0 )
(command "insert" "mroads" '(30 -15) 1 1 0 )
(command "insert" "mroads" '(25 -18) 1 1 0 )
(command "insert" "mroads" '(40 -30) 1 1 0 )
(command "insert" "mroads" '(30 -17) 1 1 0 )
(command "insert" "mroads" '(7 -17) 1 1 0 )
(command "insert" "mroads" '(31 -20) 1 1 0 )
(command "insert" "mroads" '(20 -15) 1 1 0 )
(command "insert" "mroads" '(33 -31) 1 1 0 )
(command "insert" "mroads" '(23 -18) 1 1 0 )
(command "insert" "mroads" '(47 -32) 1 1 0 )
(command "insert" "mroads" '(33 -27) 1 1 0 )
(command "insert" "mroads" '(38 -32) 1 1 0 )
(command "insert" "mroads" '(10 -15) 1 1 0 )
(command "insert" "mroads" '(8 -19) 1 1 0 )
(command "insert" "mroads" '(35 -29) 1 1 0 )
(command "insert" "mroads" '(9 -18) 1 1 0 )
(command "insert" "mroads" '(74 -32) 1 1 0 )
(command "insert" "mroads" '(52 -32) 1 1 0 )
(command "insert" "mroads" '(36 -30) 1 1 0 )
(command "insert" "mroads" '(51 -30) 1 1 0 )
(command "insert" "mroads" '(41 -27) 1 1 0 )
(command "insert" "mroads" '(82 -32) 1 1 0 )
(command "insert" "mroads" '(37 -31) 1 1 0 )
(command "insert" "mroads" '(26 -20) 1 1 0 )
(command "insert" "mroads" '(7 -19) 1 1 0 )
(command "insert" "mroads" '(98 -31) 1 1 0 )
(command "insert" "mroads" '(38 -28) 1 1 0 )
(command "insert" "mroads" '(40 -19) 1 1 0 )
(command "insert" "mroads" '(99 -30) 1 1 0 )
(command "insert" "mroads" '(39 -25) 1 1 0 )
(command "insert" "mroads" '(3 -16) 1 1 0 )
(command "insert" "mroads" '(1 -32) 1 1 0 )
(command "insert" "mroads" '(6 -15) 1 1 0 )
(command "insert" "mroads" '(46 -31) 1 1 0 )
(command "insert" "mroads" '(53 -32) 1 1 0 )
(command "insert" "mroads" '(16 -30) 1 1 0 )
(command "insert" "mroads" '(47 -30) 1 1 0 )
(command "insert" "mroads" '(17 -31) 1 1 0 )
(command "insert" "mroads" '(32 -17) 1 1 0 )
(command "insert" "mroads" '(7 -28) 1 1 0 )
(command "insert" "mroads" '(89 -32) 1 1 0 )
(command "insert" "mroads" '(7 -24) 1 1 0 )
(command "insert" "mroads" '(94 -31) 1 1 0 )
(command "insert" "mroads" '(33 -28) 1 1 0 )
(command "insert" "mroads" '(95 -30) 1 1 0 )
(command "insert" "mroads" '(34 -27) 1 1 0 )
(command "insert" "mroads" '(8 -26) 1 1 0 )
(command "insert" "mroads" '(14 -16) 1 1 0 )
(command "insert" "mroads" '(10 -16) 1 1 0 )
(command "insert" "mroads" '(37 -24) 1 1 0 )
(command "insert" "mroads" '(68 -30) 1 1 0 )
(command "insert" "mroads" '(26 -31) 1 1 0 )
(command "insert" "mroads" '(26 -18) 1 1 0 )
(command "insert" "mroads" '(38 -23) 1 1 0 )
(command "insert" "mroads" '(83 -30) 1 1 0 )
(command "insert" "mroads" '(27 -30) 1 1 0 )
(command "insert" "mroads" '(39 -22) 1 1 0 )
(command "insert" "mroads" '(13 -31) 1 1 0 )
(command "insert" "mroads" '(74 -31) 1 1 0 )
(command "insert" "mroads" '(3 -25) 1 1 0 )
(command "insert" "mroads" '(75 -30) 1 1 0 )
(command "insert" "mroads" '(4 -18) 1 1 0 )
(command "insert" "mroads" '(62 -30) 1 1 0 )
(command "insert" "mroads" '(5 -19) 1 1 0 )
(command "insert" "mroads" '(23 -32) 1 1 0 )
(command "insert" "mroads" '(6 -24) 1 1 0 )
(command "insert" "mroads" '(21 -16) 1 1 0 )
(command "insert" "mroads" '(17 -16) 1 1 0 )
(command "insert" "mroads" '(41 -19) 1 1 0 )
(command "insert" "mroads" '(31 -32) 1 1 0 )
(command "insert" "mroads" '(59 -32) 1 1 0 )
(command "insert" "mroads" '(33 -21) 1 1 0 )
(command "insert" "mroads" '(23 -30) 1 1 0 )
(command "insert" "mroads" '(34 -18) 1 1 0 )
(command "insert" "mroads" '(67 -32) 1 1 0 )
(command "insert" "mroads" '(6 -20) 1 1 0 )
(command "insert" "mroads" '(70 -31) 1 1 0 )
(command "insert" "mroads" '(33 -15) 1 1 0 )
(command "insert" "mroads" '(71 -30) 1 1 0 )
(command "insert" "mroads" '(11 -18) 1 1 0 )
(command "insert" "mroads" '(35 -17) 1 1 0 )
(command "insert" "mroads" '(1 -24) 1 1 0 )
(command "insert" "mroads" '(39 -15) 1 1 0 )
(command "insert" "mroads" '(28 -16) 1 1 0 )
(command "insert" "mroads" '(2 -31) 1 1 0 )
(command "insert" "mroads" '(12 -30) 1 1 0 )
(command "insert" "mroads" '(41 -31) 1 1 0 )
(command "insert" "mroads" '(79 -31) 1 1 0 )
(command "insert" "mroads" '(3 -30) 1 1 0 )
(command "insert" "mroads" '(40 -17) 1 1 0 )
(command "insert" "mroads" '(4 -25) 1 1 0 )
(command "insert" "mroads" '(50 -31) 1 1 0 )
(command "insert" "mroads" '(5 -28) 1 1 0 )
(command "insert" "mroads" '(29 -15) 1 1 0 )
(command "insert" "mroads" '(40 -25) 1 1 0 )
(command "insert" "mroads" '(41 -20) 1 1 0 )
(command "insert" "mroads" '(58 -30) 1 1 0 )
(command "insert" "mroads" '(37 -32) 1 1 0 )
(command "insert" "mroads" '(59 -31) 1 1 0 )
(command "insert" "mroads" '(41 -16) 1 1 0 )
(command "insert" "mroads" '(45 -32) 1 1 0 )
(command "insert" "mroads" '(73 -32) 1 1 0 )
(command "insert" "mroads" '(106 -30) 1 1 0 )
(command "insert" "mroads" '(35 -22) 1 1 0 )
(command "insert" "mroads" '(24 -17) 1 1 0 )
(command "insert" "mroads" '(107 -31) 1 1 0 )
(command "insert" "mroads" '(81 -32) 1 1 0 )
(command "insert" "mroads" '(36 -17) 1 1 0 )
(command "insert" "mroads" '(13 -17) 1 1 0 )
(command "insert" "mroads" '(37 -20) 1 1 0 )
(command "insert" "mroads" '(2 -22) 1 1 0 )
(command "insert" "mroads" '(72 -30) 1 1 0 )
(command "insert" "mroads" '(38 -27) 1 1 0 )
(command "insert" "mroads" '(54 -30) 1 1 0 )
(command "insert" "mroads" '(34 -23) 1 1 0 )
(command "insert" "mroads" '(55 -31) 1 1 0 )
(command "insert" "mroads" '(116 -31) 1 1 0 )
(command "insert" "mroads" '(102 -30) 1 1 0 )
(command "insert" "mroads" '(41 -29) 1 1 0 )
(command "insert" "mroads" '(103 -31) 1 1 0 )
(command "insert" "mroads" '(88 -32) 1 1 0 )
(command "insert" "mroads" '(84 -31) 1 1 0 )
(command "insert" "mroads" '(8 -15) 1 1 0 )
(command "insert" "mroads" '(33 -25) 1 1 0 )
(command "insert" "mroads" '(34 -30) 1 1 0 )
(command "insert" "mroads" '(8 -21) 1 1 0 )
(command "insert" "mroads" '(35 -31) 1 1 0 )
(command "insert" "mroads" '(9 -16) 1 1 0 )
(command "insert" "mroads" '(14 -15) 1 1 0 )
(command "insert" "mroads" '(40 -28) 1 1 0 )
(command "insert" "mroads" '(96 -31) 1 1 0 )
(command "insert" "mroads" '(36 -24) 1 1 0 )
(command "insert" "mroads" '(78 -31) 1 1 0 )
(command "insert" "mroads" '(82 -30) 1 1 0 )
(command "insert" "mroads" '(97 -30) 1 1 0 )
(command "insert" "mroads" '(37 -29) 1 1 0 )
(command "insert" "mroads" '(31 -31) 1 1 0 )
(command "insert" "mroads" '(38 -18) 1 1 0 )
(command "insert" "mroads" '(103 -32) 1 1 0 )
(command "insert" "mroads" '(39 -27) 1 1 0 )
(command "insert" "mroads" '(4 -15) 1 1 0 )
(command "insert" "mroads" '(7 -23) 1 1 0 )
(command "insert" "mroads" '(3 -18) 1 1 0 )
(command "insert" "mroads" '(30 -30) 1 1 0 )
(command "insert" "mroads" '(4 -21) 1 1 0 )
(command "insert" "mroads" '(79 -30) 1 1 0 )
(command "insert" "mroads" '(20 -16) 1 1 0 )
(command "insert" "mroads" '(92 -31) 1 1 0 )
(command "insert" "mroads" '(16 -16) 1 1 0 )
(command "insert" "mroads" '(30 -32) 1 1 0 )
(command "insert" "mroads" '(93 -30) 1 1 0 )
(command "insert" "mroads" '(58 -32) 1 1 0 )
(command "insert" "mroads" '(32 -19) 1 1 0 )
(command "insert" "mroads" '(33 -18) 1 1 0 )
(command "insert" "mroads" '(66 -32) 1 1 0 )
(command "insert" "mroads" '(110 -32) 1 1 0 )
(command "insert" "mroads" '(34 -25) 1 1 0 )
(command "insert" "mroads" '(8 -28) 1 1 0 )
(command "insert" "mroads" '(57 -30) 1 1 0 )
(command "insert" "mroads" '(24 -31) 1 1 0 )
(command "insert" "mroads" '(10 -30) 1 1 0 )
(command "insert" "mroads" '(25 -30) 1 1 0 )
(command "insert" "mroads" '(11 -31) 1 1 0 )
(command "insert" "mroads" '(72 -31) 1 1 0 )
(command "insert" "mroads" '(27 -16) 1 1 0 )
(command "insert" "mroads" '(49 -32) 1 1 0 )
(command "insert" "mroads" '(73 -30) 1 1 0 )
(command "insert" "mroads" '(3 -27) 1 1 0 )
(command "insert" "mroads" '(4 -28) 1 1 0 )
(command "insert" "mroads" '(41 -15) 1 1 0 )
(command "insert" "mroads" '(5 -17) 1 1 0 )
(command "insert" "mroads" '(20 -31) 1 1 0 )
(command "insert" "mroads" '(6 -30) 1 1 0 )
(command "insert" "mroads" '(21 -30) 1 1 0 )
(command "insert" "mroads" '(7 -31) 1 1 0 )
(command "insert" "mroads" '(68 -31) 1 1 0 )
(command "insert" "mroads" '(36 -32) 1 1 0 )
(command "insert" "mroads" '(69 -30) 1 1 0 )
(command "insert" "mroads" '(34 -16) 1 1 0 )
(command "insert" "mroads" '(44 -32) 1 1 0 )
(command "insert" "mroads" '(72 -32) 1 1 0 )
(command "insert" "mroads" '(6 -16) 1 1 0 )
(command "insert" "mroads" '(80 -32) 1 1 0 )
(command "insert" "mroads" '(11 -20) 1 1 0 )
(command "insert" "mroads" '(35 -19) 1 1 0 )
(command "insert" "mroads" '(36 -20) 1 1 0 )
(command "insert" "mroads" '(1 -30) 1 1 0 )
(command "insert" "mroads" '(28 -18) 1 1 0 )
(command "insert" "mroads" '(2 -29) 1 1 0 )
(command "insert" "mroads" '(48 -31) 1 1 0 )
(command "insert" "mroads" '(29 -19) 1 1 0 )
(command "insert" "mroads" '(27 -15) 1 1 0 )
(command "insert" "mroads" '(49 -30) 1 1 0 )
(command "insert" "mroads" '(4 -27) 1 1 0 )
(command "insert" "mroads" '(32 -32) 1 1 0 )
(command "insert" "mroads" '(5 -26) 1 1 0 )
(command "insert" "mroads" '(51 -32) 1 1 0 )
(command "insert" "mroads" '(40 -27) 1 1 0 )
(command "insert" "mroads" '(30 -18) 1 1 0 )
(command "insert" "mroads" '(17 -15) 1 1 0 )
(command "insert" "mroads" '(41 -26) 1 1 0 )
(command "insert" "mroads" '(56 -30) 1 1 0 )
(command "insert" "mroads" '(57 -31) 1 1 0 )
(command "insert" "mroads" '(86 -31) 1 1 0 )
(command "insert" "mroads" '(104 -30) 1 1 0 )
(command "insert" "mroads" '(44 -31) 1 1 0 )
(command "insert" "mroads" '(23 -15) 1 1 0 )
(command "insert" "mroads" '(105 -31) 1 1 0 )
(command "insert" "mroads" '(45 -30) 1 1 0 )
(command "insert" "mroads" '(8 -16) 1 1 0 )
(command "insert" "mroads" '(35 -24) 1 1 0 )
(command "insert" "mroads" '(50 -32) 1 1 0 )
(command "insert" "mroads" '(24 -19) 1 1 0 )
(command "insert" "mroads" '(36 -19) 1 1 0 )
(command "insert" "mroads" '(1 -23) 1 1 0 )
(command "insert" "mroads" '(104 -31) 1 1 0 )
(command "insert" "mroads" '(13 -15) 1 1 0 )
(command "insert" "mroads" '(37 -18) 1 1 0 )
(command "insert" "mroads" '(102 -32) 1 1 0 )
(command "insert" "mroads" '(38 -25) 1 1 0 )
(command "insert" "mroads" '(53 -31) 1 1 0 )
(command "insert" "mroads" '(78 -30) 1 1 0 )
(command "insert" "mroads" '(39 -28) 1 1 0 )
(command "insert" "mroads" '(84 -32) 1 1 0 )
(command "insert" "mroads" '(100 -30) 1 1 0 )
(command "insert" "mroads" '(115 -30) 1 1 0 )
(command "insert" "mroads" '(25 -17) 1 1 0 )
(command "insert" "mroads" '(101 -31) 1 1 0 )
(command "insert" "mroads" '(21 -32) 1 1 0 )
(command "insert" "mroads" '(19 -16) 1 1 0 )
(command "insert" "mroads" '(31 -16) 1 1 0 )
(command "insert" "mroads" '(29 -32) 1 1 0 )
(command "insert" "mroads" '(41 -17) 1 1 0 )
(command "insert" "mroads" '(32 -30) 1 1 0 )
(command "insert" "mroads" '(65 -32) 1 1 0 )
(command "insert" "mroads" '(52 -31) 1 1 0 )
(command "insert" "mroads" '(7 -20) 1 1 0 )
(command "insert" "mroads" '(110 -31) 1 1 0 )
(command "insert" "mroads" '(34 -28) 1 1 0 )
(command "insert" "mroads" '(8 -23) 1 1 0 )
(command "insert" "mroads" '(80 -30) 1 1 0 )
(command "insert" "mroads" '(111 -30) 1 1 0 )
(command "insert" "mroads" '(57 -32) 1 1 0 )
(command "insert" "mroads" '(81 -31) 1 1 0 )
(command "insert" "mroads" '(36 -26) 1 1 0 )
(command "insert" "mroads" '(40 -24) 1 1 0 )
(command "insert" "mroads" '(37 -27) 1 1 0 )
(command "insert" "mroads" '(26 -16) 1 1 0 )
(command "insert" "mroads" '(38 -16) 1 1 0 )
(command "insert" "mroads" '(39 -21) 1 1 0 )
(command "insert" "mroads" '(28 -30) 1 1 0 )
(command "insert" "mroads" '(29 -31) 1 1 0 )
(command "insert" "mroads" '(3 -20) 1 1 0 )
(command "insert" "mroads" '(90 -31) 1 1 0 )
(command "insert" "mroads" '(4 -23) 1 1 0 )
(command "insert" "mroads" '(76 -30) 1 1 0 )
(command "insert" "mroads" '(91 -30) 1 1 0 )
(command "insert" "mroads" '(7 -27) 1 1 0 )
(command "insert" "mroads" '(5 -22) 1 1 0 )
(command "insert" "mroads" '(20 -18) 1 1 0 )
(command "insert" "mroads" '(77 -31) 1 1 0 )
(command "insert" "mroads" '(21 -19) 1 1 0 )
(command "insert" "mroads" '(7 -32) 1 1 0 )
(command "insert" "mroads" '(35 -32) 1 1 0 )
(command "insert" "mroads" '(113 -30) 1 1 0 )
(command "insert" "mroads" '(33 -16) 1 1 0 )
(command "insert" "mroads" '(43 -32) 1 1 0 )
(command "insert" "mroads" '(8 -30) 1 1 0 )
(command "insert" "mroads" '(40 -16) 1 1 0 )
(command "insert" "mroads" '(87 -32) 1 1 0 )
(command "insert" "mroads" '(9 -31) 1 1 0 )
(command "insert" "mroads" '(95 -32) 1 1 0 )
(command "insert" "mroads" '(15 -17) 1 1 0 )
(command "insert" "mroads" '(87 -30) 1 1 0 )
(command "insert" "mroads" '(11 -17) 1 1 0 )
(command "insert" "mroads" '(27 -18) 1 1 0 )
(command "insert" "mroads" '(1 -27) 1 1 0 )
(command "insert" "mroads" '(39 -18) 1 1 0 )
(command "insert" "mroads" '(14 -32) 1 1 0 )
(command "insert" "mroads" '(3 -29) 1 1 0 )
(command "insert" "mroads" '(4 -30) 1 1 0 )
(command "insert" "mroads" '(19 -30) 1 1 0 )
(command "layer" "m" "ped" "" )
(command "insert" "ped" '(1 -3) 1 1 0 )
(command "insert" "ped" '(2 -18) 1 1 0 )
(command "insert" "ped" '(2 -8) 1 1 0 )
(command "insert" "ped" '(1 -17) 1 1 0 )
(command "insert" "ped" '(2 -1) 1 1 0 )
(command "insert" "ped" '(1 -15) 1 1 0 )
(command "insert" "ped" '(6 -2) 1 1 0 )
(command "insert" "ped" '(1 -6) 1 1 0 )
(command "insert" "ped" '(2 -12) 1 1 0 )
(command "insert" "ped" '(5 -1) 1 1 0 )
(command "insert" "ped" '(2 -5) 1 1 0 )
(command "insert" "ped" '(1 -11) 1 1 0 )
(command "insert" "ped" '(7 -2) 1 1 0 )
(command "insert" "ped" '(1 -2) 1 1 0 )
(command "insert" "ped" '(2 -19) 1 1 0 )
(command "insert" "ped" '(2 -9) 1 1 0 )
(command "insert" "ped" '(8 -1) 1 1 0 )
(command "insert" "ped" '(1 -16) 1 1 0 )
(command "insert" "ped" '(1 -14) 1 1 0 )
(command "insert" "ped" '(1 -5) 1 1 0 )
(command "insert" "ped" '(2 -13) 1 1 0 )
(command "insert" "ped" '(1 -20) 1 1 0 )
(command "insert" "ped" '(2 -2) 1 1 0 )
(command "insert" "ped" '(1 -10) 1 1 0 )
(command "insert" "ped" '(4 -1) 1 1 0 )
(command "insert" "ped" '(1 -1) 1 1 0 )
(command "insert" "ped" '(2 -16) 1 1 0 )
(command "insert" "ped" '(3 -2) 1 1 0 )
(command "insert" "ped" '(2 -6) 1 1 0 )
(command "insert" "ped" '(8 -2) 1 1 0 )
(command "insert" "ped" '(7 -1) 1 1 0 )
(command "insert" "ped" '(1 -13) 1 1 0 )
(command "insert" "ped" '(2 -20) 1 1 0 )
(command "insert" "ped" '(1 -4) 1 1 0 )
(command "insert" "ped" '(2 -10) 1 1 0 )
(command "insert" "ped" '(1 -19) 1 1 0 )
(command "insert" "ped" '(2 -3) 1 1 0 )
(command "insert" "ped" '(1 -9) 1 1 0 )
(command "insert" "ped" '(4 -2) 1 1 0 )
(command "insert" "ped" '(2 -14) 1 1 0 )
(command "insert" "ped" '(2 -17) 1 1 0 )
(command "insert" "ped" '(2 -7) 1 1 0 )
(command "insert" "ped" '(1 -12) 1 1 0 )
(command "insert" "ped" '(6 -1) 1 1 0 )
(command "insert" "ped" '(3 -1) 1 1 0 )
(command "insert" "ped" '(2 -11) 1 1 0 )
(command "insert" "ped" '(1 -18) 1 1 0 )
(command "insert" "ped" '(1 -8) 1 1 0 )
(command "insert" "ped" '(1 -7) 1 1 0 )
(command "insert" "ped" '(2 -15) 1 1 0 )
(command "insert" "ped" '(5 -2) 1 1 0 )
(command "insert" "ped" '(2 -4) 1 1 0 )
(command "layer" "m" "ped" "" )
(command "insert" "ped" '(4 -41) 1 1 0 )
(command "insert" "ped" '(30 -41) 1 1 0 )
(command "insert" "ped" '(4 -36) 1 1 0 )
(command "insert" "ped" '(28 -41) 1 1 0 )
(command "insert" "ped" '(9 -41) 1 1 0 )
(command "insert" "ped" '(33 -36) 1 1 0 )
(command "insert" "ped" '(23 -41) 1 1 0 )
(command "insert" "ped" '(6 -35) 1 1 0 )
(command "insert" "ped" '(1 -36) 1 1 0 )
(command "insert" "ped" '(12 -40) 1 1 0 )
(command "insert" "ped" '(19 -40) 1 1 0 )
(command "insert" "ped" '(8 -41) 1 1 0 )
(command "insert" "ped" '(32 -38) 1 1 0 )
(command "insert" "ped" '(22 -41) 1 1 0 )
(command "insert" "ped" '(9 -36) 1 1 0 )
(command "insert" "ped" '(32 -41) 1 1 0 )
(command "insert" "ped" '(35 -36) 1 1 0 )
(command "insert" "ped" '(34 -36) 1 1 0 )
(command "insert" "ped" '(17 -36) 1 1 0 )
(command "insert" "ped" '(7 -41) 1 1 0 )
(command "insert" "ped" '(17 -41) 1 1 0 )
(command "insert" "ped" '(15 -34) 1 1 0 )
(command "insert" "ped" '(16 -38) 1 1 0 )
(command "insert" "ped" '(19 -39) 1 1 0 )
(command "insert" "ped" '(25 -38) 1 1 0 )
(command "insert" "ped" '(6 -41) 1 1 0 )
(command "insert" "ped" '(21 -40) 1 1 0 )
(command "insert" "ped" '(3 -40) 1 1 0 )
(command "insert" "ped" '(27 -39) 1 1 0 )
(command "insert" "ped" '(26 -37) 1 1 0 )
(command "insert" "ped" '(22 -39) 1 1 0 )
(command "insert" "ped" '(21 -37) 1 1 0 )
(command "insert" "ped" '(27 -40) 1 1 0 )
(command "insert" "ped" '(8 -38) 1 1 0 )
(command "insert" "ped" '(23 -38) 1 1 0 )
(command "insert" "ped" '(30 -39) 1 1 0 )
(command "insert" "ped" '(10 -41) 1 1 0 )
(command "insert" "ped" '(9 -39) 1 1 0 )
(command "insert" "ped" '(7 -35) 1 1 0 )
(command "insert" "ped" '(31 -38) 1 1 0 )
(command "insert" "ped" '(11 -36) 1 1 0 )
(command "insert" "ped" '(10 -36) 1 1 0 )
(command "insert" "ped" '(17 -39) 1 1 0 )
(command "insert" "ped" '(16 -41) 1 1 0 )
(command "insert" "ped" '(12 -39) 1 1 0 )
(command "insert" "ped" '(11 -41) 1 1 0 )
(command "insert" "ped" '(18 -36) 1 1 0 )
(command "insert" "ped" '(15 -33) 1 1 0 )
(command "insert" "ped" '(1 -38) 1 1 0 )
(command "insert" "ped" '(20 -37) 1 1 0 )
(command "insert" "ped" '(3 -39) 1 1 0 )
(command "insert" "ped" '(2 -37) 1 1 0 )
(command "insert" "ped" '(26 -38) 1 1 0 )
(command "insert" "ped" '(5 -40) 1 1 0 )
(command "insert" "ped" '(8 -35) 1 1 0 )
(command "insert" "ped" '(23 -37) 1 1 0 )
(command "insert" "ped" '(6 -39) 1 1 0 )
(command "insert" "ped" '(5 -37) 1 1 0 )
(command "insert" "ped" '(29 -40) 1 1 0 )
(command "insert" "ped" '(7 -38) 1 1 0 )
(command "insert" "ped" '(31 -37) 1 1 0 )
(command "insert" "ped" '(17 -34) 1 1 0 )
(command "insert" "ped" '(18 -41) 1 1 0 )
(command "insert" "ped" '(15 -36) 1 1 0 )
(command "insert" "ped" '(13 -41) 1 1 0 )
(command "insert" "ped" '(24 -36) 1 1 0 )
(command "insert" "ped" '(6 -40) 1 1 0 )
(command "insert" "ped" '(2 -38) 1 1 0 )
(command "insert" "ped" '(4 -37) 1 1 0 )
(command "insert" "ped" '(9 -40) 1 1 0 )
(command "insert" "ped" '(23 -40) 1 1 0 )
(command "insert" "ped" '(7 -37) 1 1 0 )
(command "insert" "ped" '(12 -41) 1 1 0 )
(command "insert" "ped" '(32 -39) 1 1 0 )
(command "insert" "ped" '(33 -38) 1 1 0 )
(command "insert" "ped" '(34 -37) 1 1 0 )
(command "insert" "ped" '(7 -40) 1 1 0 )
(command "insert" "ped" '(14 -40) 1 1 0 )
(command "insert" "ped" '(17 -40) 1 1 0 )
(command "insert" "ped" '(24 -40) 1 1 0 )
(command "insert" "ped" '(19 -38) 1 1 0 )
(command "insert" "ped" '(25 -37) 1 1 0 )
(command "insert" "ped" '(7 -33) 1 1 0 )
(command "insert" "ped" '(22 -36) 1 1 0 )
(command "insert" "ped" '(21 -36) 1 1 0 )
(command "insert" "ped" '(8 -39) 1 1 0 )
(command "insert" "ped" '(32 -36) 1 1 0 )
(command "insert" "ped" '(30 -36) 1 1 0 )
(command "insert" "ped" '(9 -38) 1 1 0 )
(command "insert" "ped" '(16 -39) 1 1 0 )
(command "insert" "ped" '(11 -39) 1 1 0 )
(command "insert" "ped" '(10 -37) 1 1 0 )
(command "insert" "ped" '(34 -38) 1 1 0 )
(command "insert" "ped" '(17 -38) 1 1 0 )
(command "insert" "ped" '(11 -40) 1 1 0 )
(command "insert" "ped" '(18 -37) 1 1 0 )
(command "insert" "ped" '(24 -37) 1 1 0 )
(command "insert" "ped" '(19 -37) 1 1 0 )
(command "insert" "ped" '(26 -40) 1 1 0 )
(command "insert" "ped" '(20 -38) 1 1 0 )
(command "insert" "ped" '(3 -38) 1 1 0 )
(command "insert" "ped" '(26 -39) 1 1 0 )
(command "insert" "ped" '(31 -40) 1 1 0 )
(command "insert" "ped" '(21 -39) 1 1 0 )
(command "insert" "ped" '(8 -36) 1 1 0 )
(command "insert" "ped" '(23 -36) 1 1 0 )
(command "insert" "ped" '(6 -36) 1 1 0 )
(command "insert" "ped" '(5 -36) 1 1 0 )
(command "insert" "ped" '(29 -39) 1 1 0 )
(command "insert" "ped" '(16 -36) 1 1 0 )
(command "insert" "ped" '(31 -36) 1 1 0 )
(command "insert" "ped" '(10 -38) 1 1 0 )
(command "insert" "ped" '(17 -33) 1 1 0 )
(command "insert" "ped" '(18 -38) 1 1 0 )
(command "insert" "ped" '(15 -39) 1 1 0 )
(command "insert" "ped" '(13 -40) 1 1 0 )
(command "insert" "ped" '(20 -40) 1 1 0 )
(command "insert" "ped" '(16 -35) 1 1 0 )
(command "insert" "ped" '(3 -37) 1 1 0 )
(command "insert" "ped" '(4 -38) 1 1 0 )
(command "insert" "ped" '(8 -33) 1 1 0 )
(command "insert" "ped" '(6 -33) 1 1 0 )
(command "insert" "ped" '(5 -39) 1 1 0 )
(command "insert" "ped" '(7 -36) 1 1 0 )
(command "insert" "ped" '(15 -41) 1 1 0 )
(command "insert" "ped" '(25 -41) 1 1 0 )
(command "insert" "ped" '(4 -40) 1 1 0 )
(command "insert" "ped" '(6 -38) 1 1 0 )
(command "insert" "ped" '(30 -40) 1 1 0 )
(command "insert" "ped" '(28 -40) 1 1 0 )
(command "insert" "ped" '(33 -37) 1 1 0 )
(command "insert" "ped" '(6 -34) 1 1 0 )
(command "insert" "ped" '(35 -38) 1 1 0 )
(command "insert" "ped" '(14 -41) 1 1 0 )
(command "insert" "ped" '(24 -41) 1 1 0 )
(command "insert" "ped" '(19 -41) 1 1 0 )
(command "insert" "ped" '(25 -36) 1 1 0 )
(command "insert" "ped" '(22 -37) 1 1 0 )
(command "insert" "ped" '(7 -39) 1 1 0 )
(command "insert" "ped" '(8 -40) 1 1 0 )
(command "insert" "ped" '(32 -37) 1 1 0 )
(command "insert" "ped" '(22 -40) 1 1 0 )
(command "insert" "ped" '(30 -37) 1 1 0 )
(command "insert" "ped" '(9 -37) 1 1 0 )
(command "insert" "ped" '(32 -40) 1 1 0 )
(command "insert" "ped" '(1 -37) 1 1 0 )
(command "insert" "ped" '(11 -38) 1 1 0 )
(command "insert" "ped" '(35 -37) 1 1 0 )
(command "insert" "ped" '(17 -37) 1 1 0 )
(command "insert" "ped" '(24 -39) 1 1 0 )
(command "insert" "ped" '(15 -35) 1 1 0 )
(command "insert" "ped" '(19 -36) 1 1 0 )
(command "insert" "ped" '(26 -41) 1 1 0 )
(command "insert" "ped" '(25 -39) 1 1 0 )
(command "insert" "ped" '(16 -33) 1 1 0 )
(command "insert" "ped" '(21 -41) 1 1 0 )
(command "insert" "ped" '(20 -39) 1 1 0 )
(command "insert" "ped" '(3 -41) 1 1 0 )
(command "insert" "ped" '(26 -36) 1 1 0 )
(command "insert" "ped" '(22 -38) 1 1 0 )
(command "insert" "ped" '(21 -38) 1 1 0 )
(command "insert" "ped" '(28 -39) 1 1 0 )
(command "insert" "ped" '(27 -41) 1 1 0 )
(command "insert" "ped" '(8 -37) 1 1 0 )
(command "insert" "ped" '(23 -39) 1 1 0 )
(command "insert" "ped" '(6 -37) 1 1 0 )
(command "insert" "ped" '(30 -38) 1 1 0 )
(command "insert" "ped" '(10 -40) 1 1 0 )
(command "insert" "ped" '(16 -37) 1 1 0 )
(command "insert" "ped" '(31 -39) 1 1 0 )
(command "insert" "ped" '(11 -37) 1 1 0 )
(command "insert" "ped" '(10 -39) 1 1 0 )
(command "insert" "ped" '(16 -40) 1 1 0 )
(command "insert" "ped" '(14 -39) 1 1 0 )
(command "insert" "ped" '(18 -39) 1 1 0 )
(command "insert" "ped" '(15 -38) 1 1 0 )
(command "insert" "ped" '(13 -39) 1 1 0 )
(command "insert" "ped" '(20 -41) 1 1 0 )
(command "insert" "ped" '(20 -36) 1 1 0 )
(command "insert" "ped" '(3 -36) 1 1 0 )
(command "insert" "ped" '(2 -36) 1 1 0 )
(command "insert" "ped" '(5 -41) 1 1 0 )
(command "insert" "ped" '(4 -39) 1 1 0 )
(command "insert" "ped" '(8 -34) 1 1 0 )
(command "insert" "ped" '(31 -41) 1 1 0 )
(command "insert" "ped" '(5 -38) 1 1 0 )
(command "insert" "ped" '(29 -41) 1 1 0 )
(command "insert" "ped" '(16 -34) 1 1 0 )
(command "insert" "ped" '(17 -35) 1 1 0 )
(command "insert" "ped" '(15 -40) 1 1 0 )
(command "insert" "ped" '(7 -34) 1 1 0 )
(command "insert" "ped" '(24 -38) 1 1 0 )
(command "insert" "ped" '(18 -40) 1 1 0 )
(command "insert" "ped" '(25 -40) 1 1 0 )
(command "insert" "ped" '(15 -37) 1 1 0 )
(command "layer" "m" "Commmer" "" )
(command "insert" "Commmer" '(32 -1) 1 1 0 )
(command "insert" "Commmer" '(23 -1) 1 1 0 )
(command "insert" "Commmer" '(21 -2) 1 1 0 )
(command "insert" "Commmer" '(16 -2) 1 1 0 )
(command "insert" "Commmer" '(26 -2) 1 1 0 )
(command "insert" "Commmer" '(28 -1) 1 1 0 )
(command "insert" "Commmer" '(25 -1) 1 1 0 )
(command "insert" "Commmer" '(27 -2) 1 1 0 )
(command "insert" "Commmer" '(32 -2) 1 1 0 )
(command "insert" "Commmer" '(18 -1) 1 1 0 )
(command "insert" "Commmer" '(31 -1) 1 1 0 )
(command "insert" "Commmer" '(22 -2) 1 1 0 )
(command "insert" "Commmer" '(21 -1) 1 1 0 )
(command "insert" "Commmer" '(23 -2) 1 1 0 )
(command "insert" "Commmer" '(17 -2) 1 1 0 )
(command "insert" "Commmer" '(28 -2) 1 1 0 )
(command "insert" "Commmer" '(34 -1) 1 1 0 )
(command "insert" "Commmer" '(24 -1) 1 1 0 )
(command "insert" "Commmer" '(33 -2) 1 1 0 )
(command "insert" "Commmer" '(30 -1) 1 1 0 )
(command "insert" "Commmer" '(27 -1) 1 1 0 )
(command "insert" "Commmer" '(18 -2) 1 1 0 )
(command "insert" "Commmer" '(20 -1) 1 1 0 )
(command "insert" "Commmer" '(17 -1) 1 1 0 )
(command "insert" "Commmer" '(19 -2) 1 1 0 )
(command "insert" "Commmer" '(29 -2) 1 1 0 )
(command "insert" "Commmer" '(24 -2) 1 1 0 )
(command "insert" "Commmer" '(34 -2) 1 1 0 )
(command "insert" "Commmer" '(35 -1) 1 1 0 )
(command "insert" "Commmer" '(15 -1) 1 1 0 )
(command "insert" "Commmer" '(33 -1) 1 1 0 )
(command "insert" "Commmer" '(35 -2) 1 1 0 )
(command "insert" "Commmer" '(26 -1) 1 1 0 )
(command "insert" "Commmer" '(15 -2) 1 1 0 )
(command "insert" "Commmer" '(20 -2) 1 1 0 )
(command "insert" "Commmer" '(30 -2) 1 1 0 )
(command "insert" "Commmer" '(16 -1) 1 1 0 )
(command "insert" "Commmer" '(29 -1) 1 1 0 )
(command "insert" "Commmer" '(31 -2) 1 1 0 )
(command "insert" "Commmer" '(25 -2) 1 1 0 )
(command "insert" "Commmer" '(22 -1) 1 1 0 )
(command "insert" "Commmer" '(19 -1) 1 1 0 )
(command "layer" "m" "ped" "" )
(command "insert" "ped" '(1 -3) 1 1 0 )
(command "insert" "ped" '(2 -18) 1 1 0 )
(command "insert" "ped" '(2 -8) 1 1 0 )
(command "insert" "ped" '(1 -17) 1 1 0 )
(command "insert" "ped" '(2 -1) 1 1 0 )
(command "insert" "ped" '(1 -15) 1 1 0 )
(command "insert" "ped" '(6 -2) 1 1 0 )
(command "insert" "ped" '(1 -6) 1 1 0 )
(command "insert" "ped" '(2 -12) 1 1 0 )
(command "insert" "ped" '(5 -1) 1 1 0 )
(command "insert" "ped" '(2 -5) 1 1 0 )
(command "insert" "ped" '(1 -11) 1 1 0 )
(command "insert" "ped" '(7 -2) 1 1 0 )
(command "insert" "ped" '(1 -2) 1 1 0 )
(command "insert" "ped" '(2 -19) 1 1 0 )
(command "insert" "ped" '(2 -9) 1 1 0 )
(command "insert" "ped" '(8 -1) 1 1 0 )
(command "insert" "ped" '(1 -16) 1 1 0 )
(command "insert" "ped" '(1 -14) 1 1 0 )
(command "insert" "ped" '(1 -5) 1 1 0 )
(command "insert" "ped" '(2 -13) 1 1 0 )
(command "insert" "ped" '(1 -20) 1 1 0 )
(command "insert" "ped" '(2 -2) 1 1 0 )
(command "insert" "ped" '(1 -10) 1 1 0 )
(command "insert" "ped" '(4 -1) 1 1 0 )
(command "insert" "ped" '(1 -1) 1 1 0 )
(command "insert" "ped" '(2 -16) 1 1 0 )
(command "insert" "ped" '(3 -2) 1 1 0 )
(command "insert" "ped" '(2 -6) 1 1 0 )
(command "insert" "ped" '(8 -2) 1 1 0 )
(command "insert" "ped" '(7 -1) 1 1 0 )
(command "insert" "ped" '(1 -13) 1 1 0 )
(command "insert" "ped" '(2 -20) 1 1 0 )
(command "insert" "ped" '(1 -4) 1 1 0 )
(command "insert" "ped" '(2 -10) 1 1 0 )
(command "insert" "ped" '(1 -19) 1 1 0 )
(command "insert" "ped" '(2 -3) 1 1 0 )
(command "insert" "ped" '(1 -9) 1 1 0 )
(command "insert" "ped" '(4 -2) 1 1 0 )
(command "insert" "ped" '(2 -14) 1 1 0 )
(command "insert" "ped" '(2 -17) 1 1 0 )
(command "insert" "ped" '(2 -7) 1 1 0 )
(command "insert" "ped" '(1 -12) 1 1 0 )
(command "insert" "ped" '(6 -1) 1 1 0 )
(command "insert" "ped" '(3 -1) 1 1 0 )
(command "insert" "ped" '(2 -11) 1 1 0 )
(command "insert" "ped" '(1 -18) 1 1 0 )
(command "insert" "ped" '(1 -8) 1 1 0 )
(command "insert" "ped" '(1 -7) 1 1 0 )
(command "insert" "ped" '(2 -15) 1 1 0 )
(command "insert" "ped" '(5 -2) 1 1 0 )
(command "insert" "ped" '(2 -4) 1 1 0 )
(command "layer" "m" "Res" "" )
(command "insert" "Res" '(48 -1) 1 1 0 )
(command "insert" "Res" '(49 -2) 1 1 0 )
(command "insert" "Res" '(50 -2) 1 1 0 )
(command "insert" "Res" '(49 -1) 1 1 0 )
(command "insert" "Res" '(50 -1) 1 1 0 )
(command "insert" "Res" '(48 -2) 1 1 0 )
(command "layer" "m" "Res" "" )
(command "insert" "Res" '(49 -2) 1 1 0 )
(command "insert" "Res" '(48 -1) 1 1 0 )
(command "insert" "Res" '(50 -2) 1 1 0 )
(command "insert" "Res" '(49 -1) 1 1 0 )
(command "insert" "Res" '(50 -1) 1 1 0 )
(command "insert" "Res" '(48 -2) 1 1 0 )
(command "layer" "m" "ped" "" )
(command "insert" "ped" '(1 -3) 1 1 0 )
(command "insert" "ped" '(2 -18) 1 1 0 )
(command "insert" "ped" '(2 -8) 1 1 0 )
(command "insert" "ped" '(1 -17) 1 1 0 )
(command "insert" "ped" '(2 -1) 1 1 0 )
(command "insert" "ped" '(1 -15) 1 1 0 )
(command "insert" "ped" '(6 -2) 1 1 0 )
(command "insert" "ped" '(1 -6) 1 1 0 )
(command "insert" "ped" '(2 -12) 1 1 0 )
(command "insert" "ped" '(5 -1) 1 1 0 )
(command "insert" "ped" '(2 -5) 1 1 0 )
(command "insert" "ped" '(1 -11) 1 1 0 )
(command "insert" "ped" '(7 -2) 1 1 0 )
(command "insert" "ped" '(1 -2) 1 1 0 )
(command "insert" "ped" '(2 -19) 1 1 0 )
(command "insert" "ped" '(2 -9) 1 1 0 )
(command "insert" "ped" '(8 -1) 1 1 0 )
(command "insert" "ped" '(1 -16) 1 1 0 )
(command "insert" "ped" '(1 -14) 1 1 0 )
(command "insert" "ped" '(1 -5) 1 1 0 )
(command "insert" "ped" '(2 -13) 1 1 0 )
(command "insert" "ped" '(1 -20) 1 1 0 )
(command "insert" "ped" '(2 -2) 1 1 0 )
(command "insert" "ped" '(1 -10) 1 1 0 )
(command "insert" "ped" '(4 -1) 1 1 0 )
(command "insert" "ped" '(1 -1) 1 1 0 )
(command "insert" "ped" '(2 -16) 1 1 0 )
(command "insert" "ped" '(3 -2) 1 1 0 )
(command "insert" "ped" '(2 -6) 1 1 0 )
(command "insert" "ped" '(8 -2) 1 1 0 )
(command "insert" "ped" '(7 -1) 1 1 0 )
(command "insert" "ped" '(1 -13) 1 1 0 )
(command "insert" "ped" '(2 -20) 1 1 0 )
(command "insert" "ped" '(1 -4) 1 1 0 )
(command "insert" "ped" '(2 -10) 1 1 0 )
(command "insert" "ped" '(1 -19) 1 1 0 )
(command "insert" "ped" '(2 -3) 1 1 0 )
(command "insert" "ped" '(1 -9) 1 1 0 )
(command "insert" "ped" '(4 -2) 1 1 0 )
(command "insert" "ped" '(2 -14) 1 1 0 )
(command "insert" "ped" '(2 -17) 1 1 0 )
(command "insert" "ped" '(2 -7) 1 1 0 )
(command "insert" "ped" '(1 -12) 1 1 0 )
(command "insert" "ped" '(6 -1) 1 1 0 )
(command "insert" "ped" '(3 -1) 1 1 0 )
(command "insert" "ped" '(2 -11) 1 1 0 )
(command "insert" "ped" '(1 -18) 1 1 0 )
(command "insert" "ped" '(1 -8) 1 1 0 )
(command "insert" "ped" '(1 -7) 1 1 0 )
(command "insert" "ped" '(2 -15) 1 1 0 )
(command "insert" "ped" '(5 -2) 1 1 0 )
(command "insert" "ped" '(2 -4) 1 1 0 )
(command "layer" "m" "mroads" "" )
(command "insert" "mroads" '(5 -31) 1 1 0 )
(command "insert" "mroads" '(66 -31) 1 1 0 )
(command "insert" "mroads" '(6 -28) 1 1 0 )
(command "insert" "mroads" '(67 -30) 1 1 0 )
(command "insert" "mroads" '(7 -25) 1 1 0 )
(command "insert" "mroads" '(22 -19) 1 1 0 )
(command "insert" "mroads" '(18 -19) 1 1 0 )
(command "insert" "mroads" '(38 -21) 1 1 0 )
(command "insert" "mroads" '(114 -31) 1 1 0 )
(command "insert" "mroads" '(13 -32) 1 1 0 )
(command "insert" "mroads" '(35 -15) 1 1 0 )
(command "insert" "mroads" '(14 -31) 1 1 0 )
(command "insert" "mroads" '(15 -30) 1 1 0 )
(command "insert" "mroads" '(35 -21) 1 1 0 )
(command "insert" "mroads" '(12 -17) 1 1 0 )
(command "insert" "mroads" '(36 -22) 1 1 0 )
(command "insert" "mroads" '(1 -28) 1 1 0 )
(command "insert" "mroads" '(25 -15) 1 1 0 )
(command "insert" "mroads" '(39 -16) 1 1 0 )
(command "insert" "mroads" '(63 -30) 1 1 0 )
(command "insert" "mroads" '(37 -23) 1 1 0 )
(command "insert" "mroads" '(2 -27) 1 1 0 )
(command "insert" "mroads" '(109 -32) 1 1 0 )
(command "insert" "mroads" '(29 -17) 1 1 0 )
(command "insert" "mroads" '(31 -15) 1 1 0 )
(command "insert" "mroads" '(5 -24) 1 1 0 )
(command "insert" "mroads" '(20 -32) 1 1 0 )
(command "insert" "mroads" '(6 -23) 1 1 0 )
(command "insert" "mroads" '(30 -16) 1 1 0 )
(command "insert" "mroads" '(28 -32) 1 1 0 )
(command "insert" "mroads" '(7 -22) 1 1 0 )
(command "insert" "mroads" '(41 -23) 1 1 0 )
(command "insert" "mroads" '(42 -31) 1 1 0 )
(command "insert" "mroads" '(23 -19) 1 1 0 )
(command "insert" "mroads" '(21 -15) 1 1 0 )
(command "insert" "mroads" '(43 -30) 1 1 0 )
(command "insert" "mroads" '(116 -32) 1 1 0 )
(command "insert" "mroads" '(8 -18) 1 1 0 )
(command "insert" "mroads" '(11 -15) 1 1 0 )
(command "insert" "mroads" '(35 -26) 1 1 0 )
(command "insert" "mroads" '(9 -19) 1 1 0 )
(command "insert" "mroads" '(36 -29) 1 1 0 )
(command "insert" "mroads" '(1 -21) 1 1 0 )
(command "insert" "mroads" '(25 -16) 1 1 0 )
(command "insert" "mroads" '(29 -20) 1 1 0 )
(command "insert" "mroads" '(37 -16) 1 1 0 )
(command "insert" "mroads" '(98 -30) 1 1 0 )
(command "insert" "mroads" '(38 -31) 1 1 0 )
(command "insert" "mroads" '(99 -31) 1 1 0 )
(command "insert" "mroads" '(39 -30) 1 1 0 )
(command "insert" "mroads" '(3 -17) 1 1 0 )
(command "insert" "mroads" '(19 -18) 1 1 0 )
(command "insert" "mroads" '(7 -15) 1 1 0 )
(command "insert" "mroads" '(31 -18) 1 1 0 )
(command "insert" "mroads" '(46 -30) 1 1 0 )
(command "insert" "mroads" '(6 -32) 1 1 0 )
(command "insert" "mroads" '(34 -32) 1 1 0 )
(command "insert" "mroads" '(32 -16) 1 1 0 )
(command "insert" "mroads" '(94 -30) 1 1 0 )
(command "insert" "mroads" '(18 -31) 1 1 0 )
(command "insert" "mroads" '(42 -32) 1 1 0 )
(command "insert" "mroads" '(86 -32) 1 1 0 )
(command "insert" "mroads" '(34 -26) 1 1 0 )
(command "insert" "mroads" '(8 -25) 1 1 0 )
(command "insert" "mroads" '(94 -32) 1 1 0 )
(command "insert" "mroads" '(9 -20) 1 1 0 )
(command "insert" "mroads" '(10 -19) 1 1 0 )
(command "insert" "mroads" '(37 -25) 1 1 0 )
(command "insert" "mroads" '(26 -30) 1 1 0 )
(command "insert" "mroads" '(7 -18) 1 1 0 )
(command "insert" "mroads" '(38 -22) 1 1 0 )
(command "insert" "mroads" '(27 -31) 1 1 0 )
(command "insert" "mroads" '(40 -20) 1 1 0 )
(command "insert" "mroads" '(39 -23) 1 1 0 )
(command "insert" "mroads" '(88 -31) 1 1 0 )
(command "insert" "mroads" '(74 -30) 1 1 0 )
(command "insert" "mroads" '(89 -30) 1 1 0 )
(command "insert" "mroads" '(3 -22) 1 1 0 )
(command "insert" "mroads" '(75 -31) 1 1 0 )
(command "insert" "mroads" '(4 -17) 1 1 0 )
(command "insert" "mroads" '(5 -20) 1 1 0 )
(command "insert" "mroads" '(6 -27) 1 1 0 )
(command "insert" "mroads" '(21 -17) 1 1 0 )
(command "insert" "mroads" '(17 -17) 1 1 0 )
(command "insert" "mroads" '(22 -30) 1 1 0 )
(command "insert" "mroads" '(33 -22) 1 1 0 )
(command "insert" "mroads" '(23 -31) 1 1 0 )
(command "insert" "mroads" '(12 -32) 1 1 0 )
(command "insert" "mroads" '(34 -21) 1 1 0 )
(command "insert" "mroads" '(70 -30) 1 1 0 )
(command "insert" "mroads" '(85 -30) 1 1 0 )
(command "insert" "mroads" '(48 -32) 1 1 0 )
(command "insert" "mroads" '(71 -31) 1 1 0 )
(command "insert" "mroads" '(34 -15) 1 1 0 )
(command "insert" "mroads" '(11 -19) 1 1 0 )
(command "insert" "mroads" '(100 -32) 1 1 0 )
(command "insert" "mroads" '(27 -20) 1 1 0 )
(command "insert" "mroads" '(1 -25) 1 1 0 )
(command "insert" "mroads" '(108 -32) 1 1 0 )
(command "insert" "mroads" '(2 -30) 1 1 0 )
(command "insert" "mroads" '(3 -31) 1 1 0 )
(command "insert" "mroads" '(64 -31) 1 1 0 )
(command "insert" "mroads" '(4 -24) 1 1 0 )
(command "insert" "mroads" '(19 -32) 1 1 0 )
(command "insert" "mroads" '(62 -31) 1 1 0 )
(command "insert" "mroads" '(50 -30) 1 1 0 )
(command "insert" "mroads" '(65 -30) 1 1 0 )
(command "insert" "mroads" '(5 -29) 1 1 0 )
(command "insert" "mroads" '(27 -32) 1 1 0 )
(command "insert" "mroads" '(6 -18) 1 1 0 )
(command "insert" "mroads" '(101 -32) 1 1 0 )
(command "insert" "mroads" '(112 -31) 1 1 0 )
(command "insert" "mroads" '(41 -21) 1 1 0 )
(command "insert" "mroads" '(22 -17) 1 1 0 )
(command "insert" "mroads" '(79 -32) 1 1 0 )
(command "insert" "mroads" '(18 -17) 1 1 0 )
(command "insert" "mroads" '(23 -20) 1 1 0 )
(command "insert" "mroads" '(40 -31) 1 1 0 )
(command "insert" "mroads" '(115 -32) 1 1 0 )
(command "insert" "mroads" '(60 -31) 1 1 0 )
(command "insert" "mroads" '(61 -30) 1 1 0 )
(command "insert" "mroads" '(35 -23) 1 1 0 )
(command "insert" "mroads" '(24 -16) 1 1 0 )
(command "insert" "mroads" '(36 -16) 1 1 0 )
(command "insert" "mroads" '(108 -31) 1 1 0 )
(command "insert" "mroads" '(37 -21) 1 1 0 )
(command "insert" "mroads" '(2 -25) 1 1 0 )
(command "insert" "mroads" '(109 -30) 1 1 0 )
(command "insert" "mroads" '(7 -16) 1 1 0 )
(command "insert" "mroads" '(38 -26) 1 1 0 )
(command "insert" "mroads" '(40 -18) 1 1 0 )
(command "insert" "mroads" '(114 -32) 1 1 0 )
(command "insert" "mroads" '(116 -30) 1 1 0 )
(command "insert" "mroads" '(6 -21) 1 1 0 )
(command "insert" "mroads" '(111 -31) 1 1 0 )
(command "insert" "mroads" '(19 -15) 1 1 0 )
(command "insert" "mroads" '(41 -30) 1 1 0 )
(command "insert" "mroads" '(5 -32) 1 1 0 )
(command "insert" "mroads" '(33 -32) 1 1 0 )
(command "insert" "mroads" '(41 -32) 1 1 0 )
(command "insert" "mroads" '(7 -29) 1 1 0 )
(command "insert" "mroads" '(85 -32) 1 1 0 )
(command "insert" "mroads" '(9 -15) 1 1 0 )
(command "insert" "mroads" '(33 -26) 1 1 0 )
(command "insert" "mroads" '(22 -31) 1 1 0 )
(command "insert" "mroads" '(93 -32) 1 1 0 )
(command "insert" "mroads" '(8 -20) 1 1 0 )
(command "insert" "mroads" '(37 -15) 1 1 0 )
(command "insert" "mroads" '(35 -28) 1 1 0 )
(command "insert" "mroads" '(9 -17) 1 1 0 )
(command "insert" "mroads" '(96 -30) 1 1 0 )
(command "insert" "mroads" '(36 -31) 1 1 0 )
(command "insert" "mroads" '(15 -15) 1 1 0 )
(command "insert" "mroads" '(97 -31) 1 1 0 )
(command "insert" "mroads" '(37 -30) 1 1 0 )
(command "insert" "mroads" '(38 -29) 1 1 0 )
(command "insert" "mroads" '(83 -31) 1 1 0 )
(command "insert" "mroads" '(39 -24) 1 1 0 )
(command "insert" "mroads" '(5 -15) 1 1 0 )
(command "insert" "mroads" '(3 -19) 1 1 0 )
(command "insert" "mroads" '(4 -20) 1 1 0 )
(command "insert" "mroads" '(19 -20) 1 1 0 )
(command "insert" "mroads" '(92 -30) 1 1 0 )
(command "insert" "mroads" '(16 -31) 1 1 0 )
(command "insert" "mroads" '(93 -31) 1 1 0 )
(command "insert" "mroads" '(17 -30) 1 1 0 )
(command "insert" "mroads" '(32 -18) 1 1 0 )
(command "insert" "mroads" '(11 -32) 1 1 0 )
(command "insert" "mroads" '(33 -19) 1 1 0 )
(command "insert" "mroads" '(40 -29) 1 1 0 )
(command "insert" "mroads" '(8 -27) 1 1 0 )
(command "insert" "mroads" '(63 -32) 1 1 0 )
(command "insert" "mroads" '(5 -21) 1 1 0 )
(command "insert" "mroads" '(24 -30) 1 1 0 )
(command "insert" "mroads" '(14 -17) 1 1 0 )
(command "insert" "mroads" '(71 -32) 1 1 0 )
(command "insert" "mroads" '(10 -17) 1 1 0 )
(command "insert" "mroads" '(25 -31) 1 1 0 )
(command "insert" "mroads" '(99 -32) 1 1 0 )
(command "insert" "mroads" '(111 -32) 1 1 0 )
(command "insert" "mroads" '(107 -32) 1 1 0 )
(command "insert" "mroads" '(38 -20) 1 1 0 )
(command "insert" "mroads" '(12 -31) 1 1 0 )
(command "insert" "mroads" '(27 -17) 1 1 0 )
(command "insert" "mroads" '(39 -17) 1 1 0 )
(command "insert" "mroads" '(13 -30) 1 1 0 )
(command "insert" "mroads" '(41 -24) 1 1 0 )
(command "insert" "mroads" '(3 -24) 1 1 0 )
(command "insert" "mroads" '(56 -32) 1 1 0 )
(command "insert" "mroads" '(4 -19) 1 1 0 )
(command "insert" "mroads" '(26 -32) 1 1 0 )
(command "insert" "mroads" '(5 -18) 1 1 0 )
(command "insert" "mroads" '(20 -30) 1 1 0 )
(command "insert" "mroads" '(6 -25) 1 1 0 )
(command "insert" "mroads" '(21 -31) 1 1 0 )
(command "insert" "mroads" '(40 -22) 1 1 0 )
(command "insert" "mroads" '(78 -32) 1 1 0 )
(command "insert" "mroads" '(41 -18) 1 1 0 )
(command "insert" "mroads" '(18 -20) 1 1 0 )
(command "insert" "mroads" '(33 -20) 1 1 0 )
(command "insert" "mroads" '(69 -31) 1 1 0 )
(command "insert" "mroads" '(34 -19) 1 1 0 )
(command "insert" "mroads" '(32 -15) 1 1 0 )
(command "insert" "mroads" '(15 -32) 1 1 0 )
(command "insert" "mroads" '(64 -32) 1 1 0 )
(command "insert" "mroads" '(35 -16) 1 1 0 )
(command "insert" "mroads" '(38 -15) 1 1 0 )
(command "insert" "mroads" '(77 -32) 1 1 0 )
(command "insert" "mroads" '(1 -31) 1 1 0 )
(command "insert" "mroads" '(28 -17) 1 1 0 )
(command "insert" "mroads" '(2 -28) 1 1 0 )
(command "insert" "mroads" '(48 -30) 1 1 0 )
(command "insert" "mroads" '(113 -32) 1 1 0 )
(command "insert" "mroads" '(49 -31) 1 1 0 )
(command "insert" "mroads" '(4 -26) 1 1 0 )
(command "insert" "mroads" '(28 -15) 1 1 0 )
(command "insert" "mroads" '(5 -27) 1 1 0 )
(command "insert" "mroads" '(40 -26) 1 1 0 )
(command "insert" "mroads" '(4 -32) 1 1 0 )
(command "insert" "mroads" '(7 -21) 1 1 0 )
(command "insert" "mroads" '(18 -15) 1 1 0 )
(command "insert" "mroads" '(40 -32) 1 1 0 )
(command "insert" "mroads" '(34 -20) 1 1 0 )
(command "insert" "mroads" '(58 -31) 1 1 0 )
(command "insert" "mroads" '(44 -30) 1 1 0 )
(command "insert" "mroads" '(59 -30) 1 1 0 )
(command "insert" "mroads" '(92 -32) 1 1 0 )
(command "insert" "mroads" '(45 -31) 1 1 0 )
(command "insert" "mroads" '(6 -17) 1 1 0 )
(command "insert" "mroads" '(106 -31) 1 1 0 )
(command "insert" "mroads" '(35 -25) 1 1 0 )
(command "insert" "mroads" '(24 -18) 1 1 0 )
(command "insert" "mroads" '(107 -30) 1 1 0 )
(command "insert" "mroads" '(36 -18) 1 1 0 )
(command "insert" "mroads" '(25 -19) 1 1 0 )
(command "insert" "mroads" '(13 -16) 1 1 0 )
(command "insert" "mroads" '(37 -19) 1 1 0 )
(command "insert" "mroads" '(2 -23) 1 1 0 )
(command "insert" "mroads" '(38 -24) 1 1 0 )
(command "insert" "mroads" '(39 -29) 1 1 0 )
(command "insert" "mroads" '(54 -31) 1 1 0 )
(command "insert" "mroads" '(115 -31) 1 1 0 )
(command "insert" "mroads" '(55 -30) 1 1 0 )
(command "insert" "mroads" '(22 -20) 1 1 0 )
(command "insert" "mroads" '(30 -20) 1 1 0 )
(command "insert" "mroads" '(19 -17) 1 1 0 )
(command "insert" "mroads" '(102 -31) 1 1 0 )
(command "insert" "mroads" '(41 -28) 1 1 0 )
(command "insert" "mroads" '(31 -17) 1 1 0 )
(command "insert" "mroads" '(103 -30) 1 1 0 )
(command "insert" "mroads" '(10 -32) 1 1 0 )
(command "insert" "mroads" '(22 -32) 1 1 0 )
(command "insert" "mroads" '(18 -32) 1 1 0 )
(command "insert" "mroads" '(33 -24) 1 1 0 )
(command "insert" "mroads" '(62 -32) 1 1 0 )
(command "insert" "mroads" '(110 -30) 1 1 0 )
(command "insert" "mroads" '(34 -31) 1 1 0 )
(command "insert" "mroads" '(8 -22) 1 1 0 )
(command "insert" "mroads" '(23 -17) 1 1 0 )
(command "insert" "mroads" '(70 -32) 1 1 0 )
(command "insert" "mroads" '(35 -30) 1 1 0 )
(command "insert" "mroads" '(98 -32) 1 1 0 )
(command "insert" "mroads" '(36 -25) 1 1 0 )
(command "insert" "mroads" '(10 -20) 1 1 0 )
(command "insert" "mroads" '(25 -20) 1 1 0 )
(command "insert" "mroads" '(82 -31) 1 1 0 )
(command "insert" "mroads" '(106 -32) 1 1 0 )
(command "insert" "mroads" '(37 -28) 1 1 0 )
(command "insert" "mroads" '(26 -19) 1 1 0 )
(command "insert" "mroads" '(38 -19) 1 1 0 )
(command "insert" "mroads" '(3 -15) 1 1 0 )
(command "insert" "mroads" '(39 -26) 1 1 0 )
(command "insert" "mroads" '(51 -31) 1 1 0 )
(command "insert" "mroads" '(3 -21) 1 1 0 )
(command "insert" "mroads" '(25 -32) 1 1 0 )
(command "insert" "mroads" '(90 -30) 1 1 0 )
(command "insert" "mroads" '(30 -31) 1 1 0 )
(command "insert" "mroads" '(4 -22) 1 1 0 )
(command "insert" "mroads" '(91 -31) 1 1 0 )
(command "insert" "mroads" '(31 -30) 1 1 0 )
(command "insert" "mroads" '(5 -23) 1 1 0 )
(command "insert" "mroads" '(20 -17) 1 1 0 )
(command "insert" "mroads" '(16 -17) 1 1 0 )
(command "insert" "mroads" '(21 -20) 1 1 0 )
(command "insert" "mroads" '(32 -20) 1 1 0 )
(command "insert" "mroads" '(33 -17) 1 1 0 )
(command "insert" "mroads" '(34 -22) 1 1 0 )
(command "insert" "mroads" '(8 -29) 1 1 0 )
(command "insert" "mroads" '(61 -31) 1 1 0 )
(command "insert" "mroads" '(86 -30) 1 1 0 )
(command "insert" "mroads" '(10 -31) 1 1 0 )
(command "insert" "mroads" '(6 -19) 1 1 0 )
(command "insert" "mroads" '(87 -31) 1 1 0 )
(command "insert" "mroads" '(11 -30) 1 1 0 )
(command "insert" "mroads" '(76 -32) 1 1 0 )
(command "insert" "mroads" '(27 -19) 1 1 0 )
(command "insert" "mroads" '(39 -19) 1 1 0 )
(command "insert" "mroads" '(28 -20) 1 1 0 )
(command "insert" "mroads" '(3 -26) 1 1 0 )
(command "insert" "mroads" '(40 -15) 1 1 0 )
(command "insert" "mroads" '(4 -29) 1 1 0 )
(command "insert" "mroads" '(19 -31) 1 1 0 )
(command "insert" "mroads" '(7 -26) 1 1 0 )
(command "insert" "mroads" '(5 -16) 1 1 0 )
(command "insert" "mroads" '(3 -32) 1 1 0 )
(command "insert" "mroads" '(66 -30) 1 1 0 )
(command "insert" "mroads" '(6 -31) 1 1 0 )
(command "insert" "mroads" '(67 -31) 1 1 0 )
(command "insert" "mroads" '(7 -30) 1 1 0 )
(command "insert" "mroads" '(22 -18) 1 1 0 )
(command "insert" "mroads" '(55 -32) 1 1 0 )
(command "insert" "mroads" '(18 -18) 1 1 0 )
(command "insert" "mroads" '(83 -32) 1 1 0 )
(command "insert" "mroads" '(114 -30) 1 1 0 )
(command "insert" "mroads" '(34 -17) 1 1 0 )
(command "insert" "mroads" '(91 -32) 1 1 0 )
(command "insert" "mroads" '(14 -30) 1 1 0 )
(command "insert" "mroads" '(36 -15) 1 1 0 )
(command "insert" "mroads" '(15 -31) 1 1 0 )
(command "insert" "mroads" '(35 -18) 1 1 0 )
(command "insert" "mroads" '(12 -16) 1 1 0 )
(command "insert" "mroads" '(36 -21) 1 1 0 )
(command "insert" "mroads" '(1 -29) 1 1 0 )
(command "insert" "mroads" '(63 -31) 1 1 0 )
(command "insert" "mroads" '(28 -19) 1 1 0 )
(command "insert" "mroads" '(2 -26) 1 1 0 )
(command "insert" "mroads" '(26 -15) 1 1 0 )
(command "insert" "mroads" '(12 -15) 1 1 0 )
(command "insert" "mroads" '(29 -18) 1 1 0 )
(command "insert" "mroads" '(5 -25) 1 1 0 )
(command "insert" "mroads" '(16 -15) 1 1 0 )
(command "insert" "mroads" '(6 -22) 1 1 0 )
(command "insert" "mroads" '(30 -19) 1 1 0 )
(command "insert" "mroads" '(41 -25) 1 1 0 )
(command "insert" "mroads" '(56 -31) 1 1 0 )
(command "insert" "mroads" '(9 -32) 1 1 0 )
(command "insert" "mroads" '(42 -30) 1 1 0 )
(command "insert" "mroads" '(23 -16) 1 1 0 )
(command "insert" "mroads" '(43 -31) 1 1 0 )
(command "insert" "mroads" '(17 -32) 1 1 0 )
(command "insert" "mroads" '(22 -15) 1 1 0 )
(command "insert" "mroads" '(61 -32) 1 1 0 )
(command "insert" "mroads" '(52 -30) 1 1 0 )
(command "insert" "mroads" '(105 -30) 1 1 0 )
(command "insert" "mroads" '(69 -32) 1 1 0 )
(command "insert" "mroads" '(34 -24) 1 1 0 )
(command "insert" "mroads" '(8 -17) 1 1 0 )
(command "insert" "mroads" '(97 -32) 1 1 0 )
(command "insert" "mroads" '(35 -27) 1 1 0 )
(command "insert" "mroads" '(24 -20) 1 1 0 )
(command "insert" "mroads" '(105 -32) 1 1 0 )
(command "insert" "mroads" '(36 -28) 1 1 0 )
(command "insert" "mroads" '(1 -22) 1 1 0 )
(command "insert" "mroads" '(6 -29) 1 1 0 )
(command "insert" "mroads" '(37 -17) 1 1 0 )
(command "insert" "mroads" '(2 -21) 1 1 0 )
(command "insert" "mroads" '(38 -30) 1 1 0 )
(command "insert" "mroads" '(53 -30) 1 1 0 )
(command "insert" "mroads" '(112 -32) 1 1 0 )
(command "insert" "mroads" '(39 -31) 1 1 0 )
(command "insert" "mroads" '(100 -31) 1 1 0 )
(command "insert" "mroads" '(24 -32) 1 1 0 )
(command "insert" "mroads" '(101 -30) 1 1 0 )
(command "insert" "mroads" '(19 -19) 1 1 0 )
(command "insert" "mroads" '(31 -19) 1 1 0 )
(command "insert" "mroads" '(20 -20) 1 1 0 )
(command "insert" "mroads" '(47 -31) 1 1 0 )
(command "insert" "mroads" '(32 -31) 1 1 0 )
(command "insert" "mroads" '(18 -30) 1 1 0 )
(command "insert" "mroads" '(33 -30) 1 1 0 )
(command "insert" "mroads" '(34 -29) 1 1 0 )
(command "insert" "mroads" '(8 -24) 1 1 0 )
(command "insert" "mroads" '(39 -32) 1 1 0 )
(command "insert" "mroads" '(80 -31) 1 1 0 )
(command "insert" "mroads" '(81 -30) 1 1 0 )
(command "insert" "mroads" '(36 -27) 1 1 0 )
(command "insert" "mroads" '(10 -18) 1 1 0 )
(command "insert" "mroads" '(75 -32) 1 1 0 )
(command "insert" "mroads" '(37 -26) 1 1 0 )
(command "insert" "mroads" '(26 -17) 1 1 0 )
(command "insert" "mroads" '(38 -17) 1 1 0 )
(command "insert" "mroads" '(39 -20) 1 1 0 )
(command "insert" "mroads" '(88 -30) 1 1 0 )
(command "insert" "mroads" '(28 -31) 1 1 0 )
(command "insert" "mroads" '(89 -31) 1 1 0 )
(command "insert" "mroads" '(29 -30) 1 1 0 )
(command "insert" "mroads" '(3 -23) 1 1 0 )
(command "insert" "mroads" '(4 -16) 1 1 0 )
(command "insert" "mroads" '(2 -32) 1 1 0 )
(command "insert" "mroads" '(76 -31) 1 1 0 )
(command "insert" "mroads" '(46 -32) 1 1 0 )
(command "insert" "mroads" '(20 -19) 1 1 0 )
(command "insert" "mroads" '(33 -29) 1 1 0 )
(command "insert" "mroads" '(77 -30) 1 1 0 )
(command "insert" "mroads" '(6 -26) 1 1 0 )
(command "insert" "mroads" '(21 -18) 1 1 0 )
(command "insert" "mroads" '(54 -32) 1 1 0 )
(command "insert" "mroads" '(33 -23) 1 1 0 )
(command "insert" "mroads" '(90 -32) 1 1 0 )
(command "insert" "mroads" '(84 -30) 1 1 0 )
(command "insert" "mroads" '(8 -31) 1 1 0 )
(command "insert" "mroads" '(95 -31) 1 1 0 )
(command "insert" "mroads" '(85 -31) 1 1 0 )
(command "insert" "mroads" '(9 -30) 1 1 0 )
(command "insert" "mroads" '(15 -16) 1 1 0 )
(command "insert" "mroads" '(11 -16) 1 1 0 )
(command "insert" "mroads" '(1 -26) 1 1 0 )
(command "insert" "mroads" '(40 -21) 1 1 0 )
(command "insert" "mroads" '(73 -31) 1 1 0 )
(command "insert" "mroads" '(3 -28) 1 1 0 )
(command "insert" "mroads" '(64 -30) 1 1 0 )
(command "insert" "mroads" '(4 -31) 1 1 0 )
(command "insert" "mroads" '(65 -31) 1 1 0 )
(command "insert" "mroads" '(5 -30) 1 1 0 )
(command "insert" "mroads" '(40 -23) 1 1 0 )
(command "insert" "mroads" '(112 -30) 1 1 0 )
(command "insert" "mroads" '(8 -32) 1 1 0 )
(command "insert" "mroads" '(41 -22) 1 1 0 )
(command "insert" "mroads" '(22 -16) 1 1 0 )
(command "insert" "mroads" '(113 -31) 1 1 0 )
(command "insert" "mroads" '(18 -16) 1 1 0 )
(command "insert" "mroads" '(16 -32) 1 1 0 )
(command "insert" "mroads" '(60 -32) 1 1 0 )
(command "insert" "mroads" '(68 -32) 1 1 0 )
(command "insert" "mroads" '(96 -32) 1 1 0 )
(command "insert" "mroads" '(60 -30) 1 1 0 )
(command "insert" "mroads" '(104 -32) 1 1 0 )
(command "insert" "mroads" '(35 -20) 1 1 0 )
(command "insert" "mroads" '(24 -15) 1 1 0 )
(command "insert" "mroads" '(36 -23) 1 1 0 )
(command "insert" "mroads" '(108 -30) 1 1 0 )
(command "insert" "mroads" '(37 -22) 1 1 0 )
(command "insert" "mroads" '(2 -24) 1 1 0 )
(command "insert" "mroads" '(109 -31) 1 1 0 )
(command "insert" "mroads" '(29 -16) 1 1 0 )
(command "insert" "mroads" '(30 -15) 1 1 0 )
(command "insert" "mroads" '(25 -18) 1 1 0 )
(command "insert" "mroads" '(40 -30) 1 1 0 )
(command "insert" "mroads" '(30 -17) 1 1 0 )
(command "insert" "mroads" '(7 -17) 1 1 0 )
(command "insert" "mroads" '(31 -20) 1 1 0 )
(command "insert" "mroads" '(20 -15) 1 1 0 )
(command "insert" "mroads" '(33 -31) 1 1 0 )
(command "insert" "mroads" '(23 -18) 1 1 0 )
(command "insert" "mroads" '(47 -32) 1 1 0 )
(command "insert" "mroads" '(33 -27) 1 1 0 )
(command "insert" "mroads" '(38 -32) 1 1 0 )
(command "insert" "mroads" '(10 -15) 1 1 0 )
(command "insert" "mroads" '(8 -19) 1 1 0 )
(command "insert" "mroads" '(35 -29) 1 1 0 )
(command "insert" "mroads" '(9 -18) 1 1 0 )
(command "insert" "mroads" '(74 -32) 1 1 0 )
(command "insert" "mroads" '(52 -32) 1 1 0 )
(command "insert" "mroads" '(36 -30) 1 1 0 )
(command "insert" "mroads" '(51 -30) 1 1 0 )
(command "insert" "mroads" '(41 -27) 1 1 0 )
(command "insert" "mroads" '(82 -32) 1 1 0 )
(command "insert" "mroads" '(37 -31) 1 1 0 )
(command "insert" "mroads" '(26 -20) 1 1 0 )
(command "insert" "mroads" '(7 -19) 1 1 0 )
(command "insert" "mroads" '(98 -31) 1 1 0 )
(command "insert" "mroads" '(38 -28) 1 1 0 )
(command "insert" "mroads" '(40 -19) 1 1 0 )
(command "insert" "mroads" '(99 -30) 1 1 0 )
(command "insert" "mroads" '(39 -25) 1 1 0 )
(command "insert" "mroads" '(3 -16) 1 1 0 )
(command "insert" "mroads" '(1 -32) 1 1 0 )
(command "insert" "mroads" '(6 -15) 1 1 0 )
(command "insert" "mroads" '(46 -31) 1 1 0 )
(command "insert" "mroads" '(53 -32) 1 1 0 )
(command "insert" "mroads" '(16 -30) 1 1 0 )
(command "insert" "mroads" '(47 -30) 1 1 0 )
(command "insert" "mroads" '(17 -31) 1 1 0 )
(command "insert" "mroads" '(32 -17) 1 1 0 )
(command "insert" "mroads" '(7 -28) 1 1 0 )
(command "insert" "mroads" '(89 -32) 1 1 0 )
(command "insert" "mroads" '(7 -24) 1 1 0 )
(command "insert" "mroads" '(94 -31) 1 1 0 )
(command "insert" "mroads" '(33 -28) 1 1 0 )
(command "insert" "mroads" '(95 -30) 1 1 0 )
(command "insert" "mroads" '(34 -27) 1 1 0 )
(command "insert" "mroads" '(8 -26) 1 1 0 )
(command "insert" "mroads" '(14 -16) 1 1 0 )
(command "insert" "mroads" '(10 -16) 1 1 0 )
(command "insert" "mroads" '(37 -24) 1 1 0 )
(command "insert" "mroads" '(68 -30) 1 1 0 )
(command "insert" "mroads" '(26 -31) 1 1 0 )
(command "insert" "mroads" '(26 -18) 1 1 0 )
(command "insert" "mroads" '(38 -23) 1 1 0 )
(command "insert" "mroads" '(83 -30) 1 1 0 )
(command "insert" "mroads" '(27 -30) 1 1 0 )
(command "insert" "mroads" '(39 -22) 1 1 0 )
(command "insert" "mroads" '(13 -31) 1 1 0 )
(command "insert" "mroads" '(74 -31) 1 1 0 )
(command "insert" "mroads" '(3 -25) 1 1 0 )
(command "insert" "mroads" '(75 -30) 1 1 0 )
(command "insert" "mroads" '(4 -18) 1 1 0 )
(command "insert" "mroads" '(62 -30) 1 1 0 )
(command "insert" "mroads" '(5 -19) 1 1 0 )
(command "insert" "mroads" '(23 -32) 1 1 0 )
(command "insert" "mroads" '(6 -24) 1 1 0 )
(command "insert" "mroads" '(21 -16) 1 1 0 )
(command "insert" "mroads" '(17 -16) 1 1 0 )
(command "insert" "mroads" '(41 -19) 1 1 0 )
(command "insert" "mroads" '(31 -32) 1 1 0 )
(command "insert" "mroads" '(59 -32) 1 1 0 )
(command "insert" "mroads" '(33 -21) 1 1 0 )
(command "insert" "mroads" '(23 -30) 1 1 0 )
(command "insert" "mroads" '(34 -18) 1 1 0 )
(command "insert" "mroads" '(67 -32) 1 1 0 )
(command "insert" "mroads" '(6 -20) 1 1 0 )
(command "insert" "mroads" '(70 -31) 1 1 0 )
(command "insert" "mroads" '(33 -15) 1 1 0 )
(command "insert" "mroads" '(71 -30) 1 1 0 )
(command "insert" "mroads" '(11 -18) 1 1 0 )
(command "insert" "mroads" '(35 -17) 1 1 0 )
(command "insert" "mroads" '(1 -24) 1 1 0 )
(command "insert" "mroads" '(39 -15) 1 1 0 )
(command "insert" "mroads" '(28 -16) 1 1 0 )
(command "insert" "mroads" '(2 -31) 1 1 0 )
(command "insert" "mroads" '(12 -30) 1 1 0 )
(command "insert" "mroads" '(41 -31) 1 1 0 )
(command "insert" "mroads" '(79 -31) 1 1 0 )
(command "insert" "mroads" '(3 -30) 1 1 0 )
(command "insert" "mroads" '(40 -17) 1 1 0 )
(command "insert" "mroads" '(4 -25) 1 1 0 )
(command "insert" "mroads" '(50 -31) 1 1 0 )
(command "insert" "mroads" '(5 -28) 1 1 0 )
(command "insert" "mroads" '(29 -15) 1 1 0 )
(command "insert" "mroads" '(40 -25) 1 1 0 )
(command "insert" "mroads" '(41 -20) 1 1 0 )
(command "insert" "mroads" '(58 -30) 1 1 0 )
(command "insert" "mroads" '(37 -32) 1 1 0 )
(command "insert" "mroads" '(59 -31) 1 1 0 )
(command "insert" "mroads" '(41 -16) 1 1 0 )
(command "insert" "mroads" '(45 -32) 1 1 0 )
(command "insert" "mroads" '(73 -32) 1 1 0 )
(command "insert" "mroads" '(106 -30) 1 1 0 )
(command "insert" "mroads" '(35 -22) 1 1 0 )
(command "insert" "mroads" '(24 -17) 1 1 0 )
(command "insert" "mroads" '(107 -31) 1 1 0 )
(command "insert" "mroads" '(81 -32) 1 1 0 )
(command "insert" "mroads" '(36 -17) 1 1 0 )
(command "insert" "mroads" '(13 -17) 1 1 0 )
(command "insert" "mroads" '(37 -20) 1 1 0 )
(command "insert" "mroads" '(2 -22) 1 1 0 )
(command "insert" "mroads" '(72 -30) 1 1 0 )
(command "insert" "mroads" '(38 -27) 1 1 0 )
(command "insert" "mroads" '(54 -30) 1 1 0 )
(command "insert" "mroads" '(34 -23) 1 1 0 )
(command "insert" "mroads" '(55 -31) 1 1 0 )
(command "insert" "mroads" '(116 -31) 1 1 0 )
(command "insert" "mroads" '(102 -30) 1 1 0 )
(command "insert" "mroads" '(41 -29) 1 1 0 )
(command "insert" "mroads" '(103 -31) 1 1 0 )
(command "insert" "mroads" '(88 -32) 1 1 0 )
(command "insert" "mroads" '(84 -31) 1 1 0 )
(command "insert" "mroads" '(8 -15) 1 1 0 )
(command "insert" "mroads" '(33 -25) 1 1 0 )
(command "insert" "mroads" '(34 -30) 1 1 0 )
(command "insert" "mroads" '(8 -21) 1 1 0 )
(command "insert" "mroads" '(35 -31) 1 1 0 )
(command "insert" "mroads" '(9 -16) 1 1 0 )
(command "insert" "mroads" '(14 -15) 1 1 0 )
(command "insert" "mroads" '(40 -28) 1 1 0 )
(command "insert" "mroads" '(96 -31) 1 1 0 )
(command "insert" "mroads" '(36 -24) 1 1 0 )
(command "insert" "mroads" '(78 -31) 1 1 0 )
(command "insert" "mroads" '(82 -30) 1 1 0 )
(command "insert" "mroads" '(97 -30) 1 1 0 )
(command "insert" "mroads" '(37 -29) 1 1 0 )
(command "insert" "mroads" '(31 -31) 1 1 0 )
(command "insert" "mroads" '(38 -18) 1 1 0 )
(command "insert" "mroads" '(103 -32) 1 1 0 )
(command "insert" "mroads" '(39 -27) 1 1 0 )
(command "insert" "mroads" '(4 -15) 1 1 0 )
(command "insert" "mroads" '(7 -23) 1 1 0 )
(command "insert" "mroads" '(3 -18) 1 1 0 )
(command "insert" "mroads" '(30 -30) 1 1 0 )
(command "insert" "mroads" '(4 -21) 1 1 0 )
(command "insert" "mroads" '(79 -30) 1 1 0 )
(command "insert" "mroads" '(20 -16) 1 1 0 )
(command "insert" "mroads" '(92 -31) 1 1 0 )
(command "insert" "mroads" '(16 -16) 1 1 0 )
(command "insert" "mroads" '(30 -32) 1 1 0 )
(command "insert" "mroads" '(93 -30) 1 1 0 )
(command "insert" "mroads" '(58 -32) 1 1 0 )
(command "insert" "mroads" '(32 -19) 1 1 0 )
(command "insert" "mroads" '(33 -18) 1 1 0 )
(command "insert" "mroads" '(66 -32) 1 1 0 )
(command "insert" "mroads" '(110 -32) 1 1 0 )
(command "insert" "mroads" '(34 -25) 1 1 0 )
(command "insert" "mroads" '(8 -28) 1 1 0 )
(command "insert" "mroads" '(57 -30) 1 1 0 )
(command "insert" "mroads" '(24 -31) 1 1 0 )
(command "insert" "mroads" '(10 -30) 1 1 0 )
(command "insert" "mroads" '(25 -30) 1 1 0 )
(command "insert" "mroads" '(11 -31) 1 1 0 )
(command "insert" "mroads" '(72 -31) 1 1 0 )
(command "insert" "mroads" '(27 -16) 1 1 0 )
(command "insert" "mroads" '(49 -32) 1 1 0 )
(command "insert" "mroads" '(73 -30) 1 1 0 )
(command "insert" "mroads" '(3 -27) 1 1 0 )
(command "insert" "mroads" '(4 -28) 1 1 0 )
(command "insert" "mroads" '(41 -15) 1 1 0 )
(command "insert" "mroads" '(5 -17) 1 1 0 )
(command "insert" "mroads" '(20 -31) 1 1 0 )
(command "insert" "mroads" '(6 -30) 1 1 0 )
(command "insert" "mroads" '(21 -30) 1 1 0 )
(command "insert" "mroads" '(7 -31) 1 1 0 )
(command "insert" "mroads" '(68 -31) 1 1 0 )
(command "insert" "mroads" '(36 -32) 1 1 0 )
(command "insert" "mroads" '(69 -30) 1 1 0 )
(command "insert" "mroads" '(34 -16) 1 1 0 )
(command "insert" "mroads" '(44 -32) 1 1 0 )
(command "insert" "mroads" '(72 -32) 1 1 0 )
(command "insert" "mroads" '(6 -16) 1 1 0 )
(command "insert" "mroads" '(80 -32) 1 1 0 )
(command "insert" "mroads" '(11 -20) 1 1 0 )
(command "insert" "mroads" '(35 -19) 1 1 0 )
(command "insert" "mroads" '(36 -20) 1 1 0 )
(command "insert" "mroads" '(1 -30) 1 1 0 )
(command "insert" "mroads" '(28 -18) 1 1 0 )
(command "insert" "mroads" '(2 -29) 1 1 0 )
(command "insert" "mroads" '(48 -31) 1 1 0 )
(command "insert" "mroads" '(29 -19) 1 1 0 )
(command "insert" "mroads" '(27 -15) 1 1 0 )
(command "insert" "mroads" '(49 -30) 1 1 0 )
(command "insert" "mroads" '(4 -27) 1 1 0 )
(command "insert" "mroads" '(32 -32) 1 1 0 )
(command "insert" "mroads" '(5 -26) 1 1 0 )
(command "insert" "mroads" '(51 -32) 1 1 0 )
(command "insert" "mroads" '(40 -27) 1 1 0 )
(command "insert" "mroads" '(30 -18) 1 1 0 )
(command "insert" "mroads" '(17 -15) 1 1 0 )
(command "insert" "mroads" '(41 -26) 1 1 0 )
(command "insert" "mroads" '(56 -30) 1 1 0 )
(command "insert" "mroads" '(57 -31) 1 1 0 )
(command "insert" "mroads" '(86 -31) 1 1 0 )
(command "insert" "mroads" '(104 -30) 1 1 0 )
(command "insert" "mroads" '(44 -31) 1 1 0 )
(command "insert" "mroads" '(23 -15) 1 1 0 )
(command "insert" "mroads" '(105 -31) 1 1 0 )
(command "insert" "mroads" '(45 -30) 1 1 0 )
(command "insert" "mroads" '(8 -16) 1 1 0 )
(command "insert" "mroads" '(35 -24) 1 1 0 )
(command "insert" "mroads" '(50 -32) 1 1 0 )
(command "insert" "mroads" '(24 -19) 1 1 0 )
(command "insert" "mroads" '(36 -19) 1 1 0 )
(command "insert" "mroads" '(1 -23) 1 1 0 )
(command "insert" "mroads" '(104 -31) 1 1 0 )
(command "insert" "mroads" '(13 -15) 1 1 0 )
(command "insert" "mroads" '(37 -18) 1 1 0 )
(command "insert" "mroads" '(102 -32) 1 1 0 )
(command "insert" "mroads" '(38 -25) 1 1 0 )
(command "insert" "mroads" '(53 -31) 1 1 0 )
(command "insert" "mroads" '(78 -30) 1 1 0 )
(command "insert" "mroads" '(39 -28) 1 1 0 )
(command "insert" "mroads" '(84 -32) 1 1 0 )
(command "insert" "mroads" '(100 -30) 1 1 0 )
(command "insert" "mroads" '(115 -30) 1 1 0 )
(command "insert" "mroads" '(25 -17) 1 1 0 )
(command "insert" "mroads" '(101 -31) 1 1 0 )
(command "insert" "mroads" '(21 -32) 1 1 0 )
(command "insert" "mroads" '(19 -16) 1 1 0 )
(command "insert" "mroads" '(31 -16) 1 1 0 )
(command "insert" "mroads" '(29 -32) 1 1 0 )
(command "insert" "mroads" '(41 -17) 1 1 0 )
(command "insert" "mroads" '(32 -30) 1 1 0 )
(command "insert" "mroads" '(65 -32) 1 1 0 )
(command "insert" "mroads" '(52 -31) 1 1 0 )
(command "insert" "mroads" '(7 -20) 1 1 0 )
(command "insert" "mroads" '(110 -31) 1 1 0 )
(command "insert" "mroads" '(34 -28) 1 1 0 )
(command "insert" "mroads" '(8 -23) 1 1 0 )
(command "insert" "mroads" '(80 -30) 1 1 0 )
(command "insert" "mroads" '(111 -30) 1 1 0 )
(command "insert" "mroads" '(57 -32) 1 1 0 )
(command "insert" "mroads" '(81 -31) 1 1 0 )
(command "insert" "mroads" '(36 -26) 1 1 0 )
(command "insert" "mroads" '(40 -24) 1 1 0 )
(command "insert" "mroads" '(37 -27) 1 1 0 )
(command "insert" "mroads" '(26 -16) 1 1 0 )
(command "insert" "mroads" '(38 -16) 1 1 0 )
(command "insert" "mroads" '(39 -21) 1 1 0 )
(command "insert" "mroads" '(28 -30) 1 1 0 )
(command "insert" "mroads" '(29 -31) 1 1 0 )
(command "insert" "mroads" '(3 -20) 1 1 0 )
(command "insert" "mroads" '(90 -31) 1 1 0 )
(command "insert" "mroads" '(4 -23) 1 1 0 )
(command "insert" "mroads" '(76 -30) 1 1 0 )
(command "insert" "mroads" '(91 -30) 1 1 0 )
(command "insert" "mroads" '(7 -27) 1 1 0 )
(command "insert" "mroads" '(5 -22) 1 1 0 )
(command "insert" "mroads" '(20 -18) 1 1 0 )
(command "insert" "mroads" '(77 -31) 1 1 0 )
(command "insert" "mroads" '(21 -19) 1 1 0 )
(command "insert" "mroads" '(7 -32) 1 1 0 )
(command "insert" "mroads" '(35 -32) 1 1 0 )
(command "insert" "mroads" '(113 -30) 1 1 0 )
(command "insert" "mroads" '(33 -16) 1 1 0 )
(command "insert" "mroads" '(43 -32) 1 1 0 )
(command "insert" "mroads" '(8 -30) 1 1 0 )
(command "insert" "mroads" '(40 -16) 1 1 0 )
(command "insert" "mroads" '(87 -32) 1 1 0 )
(command "insert" "mroads" '(9 -31) 1 1 0 )
(command "insert" "mroads" '(95 -32) 1 1 0 )
(command "insert" "mroads" '(15 -17) 1 1 0 )
(command "insert" "mroads" '(87 -30) 1 1 0 )
(command "insert" "mroads" '(11 -17) 1 1 0 )
(command "insert" "mroads" '(27 -18) 1 1 0 )
(command "insert" "mroads" '(1 -27) 1 1 0 )
(command "insert" "mroads" '(39 -18) 1 1 0 )
(command "insert" "mroads" '(14 -32) 1 1 0 )
(command "insert" "mroads" '(3 -29) 1 1 0 )
(command "insert" "mroads" '(4 -30) 1 1 0 )
(command "insert" "mroads" '(19 -30) 1 1 0 )
(command "layer" "m" "Commmer" "" )
(command "insert" "Commmer" '(32 -1) 1 1 0 )
(command "insert" "Commmer" '(23 -1) 1 1 0 )
(command "insert" "Commmer" '(21 -2) 1 1 0 )
(command "insert" "Commmer" '(16 -2) 1 1 0 )
(command "insert" "Commmer" '(15 -1) 1 1 0 )
(command "insert" "Commmer" '(28 -1) 1 1 0 )
(command "insert" "Commmer" '(25 -1) 1 1 0 )
(command "insert" "Commmer" '(27 -2) 1 1 0 )
(command "insert" "Commmer" '(32 -2) 1 1 0 )
(command "insert" "Commmer" '(18 -1) 1 1 0 )
(command "insert" "Commmer" '(31 -1) 1 1 0 )
(command "insert" "Commmer" '(22 -2) 1 1 0 )
(command "insert" "Commmer" '(21 -1) 1 1 0 )
(command "insert" "Commmer" '(23 -2) 1 1 0 )
(command "insert" "Commmer" '(17 -2) 1 1 0 )
(command "insert" "Commmer" '(28 -2) 1 1 0 )
(command "insert" "Commmer" '(34 -1) 1 1 0 )
(command "insert" "Commmer" '(24 -1) 1 1 0 )
(command "insert" "Commmer" '(33 -2) 1 1 0 )
(command "insert" "Commmer" '(30 -1) 1 1 0 )
(command "insert" "Commmer" '(27 -1) 1 1 0 )
(command "insert" "Commmer" '(18 -2) 1 1 0 )
(command "insert" "Commmer" '(20 -1) 1 1 0 )
(command "insert" "Commmer" '(17 -1) 1 1 0 )
(command "insert" "Commmer" '(19 -2) 1 1 0 )
(command "insert" "Commmer" '(29 -2) 1 1 0 )
(command "insert" "Commmer" '(24 -2) 1 1 0 )
(command "insert" "Commmer" '(34 -2) 1 1 0 )
(command "insert" "Commmer" '(35 -1) 1 1 0 )
(command "insert" "Commmer" '(26 -2) 1 1 0 )
(command "insert" "Commmer" '(33 -1) 1 1 0 )
(command "insert" "Commmer" '(35 -2) 1 1 0 )
(command "insert" "Commmer" '(26 -1) 1 1 0 )
(command "insert" "Commmer" '(15 -2) 1 1 0 )
(command "insert" "Commmer" '(20 -2) 1 1 0 )
(command "insert" "Commmer" '(30 -2) 1 1 0 )
(command "insert" "Commmer" '(16 -1) 1 1 0 )
(command "insert" "Commmer" '(29 -1) 1 1 0 )
(command "insert" "Commmer" '(31 -2) 1 1 0 )
(command "insert" "Commmer" '(25 -2) 1 1 0 )
(command "insert" "Commmer" '(22 -1) 1 1 0 )
(command "insert" "Commmer" '(19 -1) 1 1 0 )
(command "layer" "m" "Commmer" "" )
(command "insert" "Commmer" '(32 -1) 1 1 0 )
(command "insert" "Commmer" '(35 -1) 1 1 0 )
(command "insert" "Commmer" '(21 -2) 1 1 0 )
(command "insert" "Commmer" '(16 -2) 1 1 0 )
(command "insert" "Commmer" '(26 -2) 1 1 0 )
(command "insert" "Commmer" '(28 -1) 1 1 0 )
(command "insert" "Commmer" '(25 -1) 1 1 0 )
(command "insert" "Commmer" '(34 -2) 1 1 0 )
(command "insert" "Commmer" '(27 -2) 1 1 0 )
(command "insert" "Commmer" '(32 -2) 1 1 0 )
(command "insert" "Commmer" '(18 -1) 1 1 0 )
(command "insert" "Commmer" '(31 -1) 1 1 0 )
(command "insert" "Commmer" '(22 -2) 1 1 0 )
(command "insert" "Commmer" '(21 -1) 1 1 0 )
(command "insert" "Commmer" '(23 -2) 1 1 0 )
(command "insert" "Commmer" '(17 -2) 1 1 0 )
(command "insert" "Commmer" '(28 -2) 1 1 0 )
(command "insert" "Commmer" '(34 -1) 1 1 0 )
(command "insert" "Commmer" '(24 -1) 1 1 0 )
(command "insert" "Commmer" '(33 -2) 1 1 0 )
(command "insert" "Commmer" '(30 -1) 1 1 0 )
(command "insert" "Commmer" '(27 -1) 1 1 0 )
(command "insert" "Commmer" '(18 -2) 1 1 0 )
(command "insert" "Commmer" '(20 -1) 1 1 0 )
(command "insert" "Commmer" '(17 -1) 1 1 0 )
(command "insert" "Commmer" '(19 -2) 1 1 0 )
(command "insert" "Commmer" '(29 -2) 1 1 0 )
(command "insert" "Commmer" '(24 -2) 1 1 0 )
(command "insert" "Commmer" '(23 -1) 1 1 0 )
(command "insert" "Commmer" '(15 -1) 1 1 0 )
(command "insert" "Commmer" '(33 -1) 1 1 0 )
(command "insert" "Commmer" '(35 -2) 1 1 0 )
(command "insert" "Commmer" '(26 -1) 1 1 0 )
(command "insert" "Commmer" '(15 -2) 1 1 0 )
(command "insert" "Commmer" '(20 -2) 1 1 0 )
(command "insert" "Commmer" '(30 -2) 1 1 0 )
(command "insert" "Commmer" '(16 -1) 1 1 0 )
(command "insert" "Commmer" '(29 -1) 1 1 0 )
(command "insert" "Commmer" '(31 -2) 1 1 0 )
(command "insert" "Commmer" '(25 -2) 1 1 0 )
(command "insert" "Commmer" '(22 -1) 1 1 0 )
(command "insert" "Commmer" '(19 -1) 1 1 0 )
(command "layer" "m" "edge" "" )
(command "insert" "edge" '(44 -2) 1 1 0 )
(command "insert" "edge" '(47 -2) 1 1 0 )
(command "insert" "edge" '(45 -1) 1 1 0 )
(command "insert" "edge" '(41 -2) 1 1 0 )
(command "insert" "edge" '(38 -1) 1 1 0 )
(command "insert" "edge" '(46 -1) 1 1 0 )
(command "insert" "edge" '(43 -1) 1 1 0 )
(command "insert" "edge" '(40 -2) 1 1 0 )
(command "insert" "edge" '(45 -2) 1 1 0 )
(command "insert" "edge" '(37 -2) 1 1 0 )
(command "insert" "edge" '(42 -2) 1 1 0 )
(command "insert" "edge" '(37 -1) 1 1 0 )
(command "insert" "edge" '(44 -1) 1 1 0 )
(command "insert" "edge" '(41 -1) 1 1 0 )
(command "insert" "edge" '(39 -1) 1 1 0 )
(command "insert" "edge" '(36 -1) 1 1 0 )
(command "insert" "edge" '(43 -2) 1 1 0 )
(command "insert" "edge" '(47 -1) 1 1 0 )
(command "insert" "edge" '(40 -1) 1 1 0 )
(command "insert" "edge" '(38 -2) 1 1 0 )
(command "insert" "edge" '(42 -1) 1 1 0 )
(command "insert" "edge" '(36 -2) 1 1 0 )
(command "insert" "edge" '(46 -2) 1 1 0 )
(command "insert" "edge" '(39 -2) 1 1 0 )
(command "layer" "m" "ped" "" )
(command "insert" "ped" '(1 -3) 1 1 0 )
(command "insert" "ped" '(2 -18) 1 1 0 )
(command "insert" "ped" '(2 -8) 1 1 0 )
(command "insert" "ped" '(1 -17) 1 1 0 )
(command "insert" "ped" '(2 -1) 1 1 0 )
(command "insert" "ped" '(1 -15) 1 1 0 )
(command "insert" "ped" '(6 -2) 1 1 0 )
(command "insert" "ped" '(1 -6) 1 1 0 )
(command "insert" "ped" '(2 -12) 1 1 0 )
(command "insert" "ped" '(5 -1) 1 1 0 )
(command "insert" "ped" '(2 -5) 1 1 0 )
(command "insert" "ped" '(1 -11) 1 1 0 )
(command "insert" "ped" '(7 -2) 1 1 0 )
(command "insert" "ped" '(1 -2) 1 1 0 )
(command "insert" "ped" '(2 -19) 1 1 0 )
(command "insert" "ped" '(2 -9) 1 1 0 )
(command "insert" "ped" '(8 -1) 1 1 0 )
(command "insert" "ped" '(1 -16) 1 1 0 )
(command "insert" "ped" '(1 -14) 1 1 0 )
(command "insert" "ped" '(1 -5) 1 1 0 )
(command "insert" "ped" '(2 -13) 1 1 0 )
(command "insert" "ped" '(1 -20) 1 1 0 )
(command "insert" "ped" '(2 -2) 1 1 0 )
(command "insert" "ped" '(1 -10) 1 1 0 )
(command "insert" "ped" '(4 -1) 1 1 0 )
(command "insert" "ped" '(1 -1) 1 1 0 )
(command "insert" "ped" '(2 -16) 1 1 0 )
(command "insert" "ped" '(3 -2) 1 1 0 )
(command "insert" "ped" '(2 -6) 1 1 0 )
(command "insert" "ped" '(8 -2) 1 1 0 )
(command "insert" "ped" '(7 -1) 1 1 0 )
(command "insert" "ped" '(1 -13) 1 1 0 )
(command "insert" "ped" '(2 -20) 1 1 0 )
(command "insert" "ped" '(1 -4) 1 1 0 )
(command "insert" "ped" '(2 -10) 1 1 0 )
(command "insert" "ped" '(1 -19) 1 1 0 )
(command "insert" "ped" '(2 -3) 1 1 0 )
(command "insert" "ped" '(1 -9) 1 1 0 )
(command "insert" "ped" '(4 -2) 1 1 0 )
(command "insert" "ped" '(2 -14) 1 1 0 )
(command "insert" "ped" '(2 -17) 1 1 0 )
(command "insert" "ped" '(2 -7) 1 1 0 )
(command "insert" "ped" '(1 -12) 1 1 0 )
(command "insert" "ped" '(6 -1) 1 1 0 )
(command "insert" "ped" '(3 -1) 1 1 0 )
(command "insert" "ped" '(2 -11) 1 1 0 )
(command "insert" "ped" '(1 -18) 1 1 0 )
(command "insert" "ped" '(1 -8) 1 1 0 )
(command "insert" "ped" '(1 -7) 1 1 0 )
(command "insert" "ped" '(2 -15) 1 1 0 )
(command "insert" "ped" '(5 -2) 1 1 0 )
(command "insert" "ped" '(2 -4) 1 1 0 )
(command "layer" "m" "mroads" "" )
(command "insert" "mroads" '(5 -31) 1 1 0 )
(command "insert" "mroads" '(66 -31) 1 1 0 )
(command "insert" "mroads" '(6 -28) 1 1 0 )
(command "insert" "mroads" '(67 -30) 1 1 0 )
(command "insert" "mroads" '(7 -25) 1 1 0 )
(command "insert" "mroads" '(22 -19) 1 1 0 )
(command "insert" "mroads" '(18 -19) 1 1 0 )
(command "insert" "mroads" '(38 -21) 1 1 0 )
(command "insert" "mroads" '(114 -31) 1 1 0 )
(command "insert" "mroads" '(13 -32) 1 1 0 )
(command "insert" "mroads" '(35 -15) 1 1 0 )
(command "insert" "mroads" '(14 -31) 1 1 0 )
(command "insert" "mroads" '(15 -30) 1 1 0 )
(command "insert" "mroads" '(35 -21) 1 1 0 )
(command "insert" "mroads" '(12 -17) 1 1 0 )
(command "insert" "mroads" '(36 -22) 1 1 0 )
(command "insert" "mroads" '(1 -28) 1 1 0 )
(command "insert" "mroads" '(25 -15) 1 1 0 )
(command "insert" "mroads" '(39 -16) 1 1 0 )
(command "insert" "mroads" '(63 -30) 1 1 0 )
(command "insert" "mroads" '(37 -23) 1 1 0 )
(command "insert" "mroads" '(2 -27) 1 1 0 )
(command "insert" "mroads" '(109 -32) 1 1 0 )
(command "insert" "mroads" '(29 -17) 1 1 0 )
(command "insert" "mroads" '(31 -15) 1 1 0 )
(command "insert" "mroads" '(5 -24) 1 1 0 )
(command "insert" "mroads" '(20 -32) 1 1 0 )
(command "insert" "mroads" '(6 -23) 1 1 0 )
(command "insert" "mroads" '(30 -16) 1 1 0 )
(command "insert" "mroads" '(28 -32) 1 1 0 )
(command "insert" "mroads" '(7 -22) 1 1 0 )
(command "insert" "mroads" '(41 -23) 1 1 0 )
(command "insert" "mroads" '(42 -31) 1 1 0 )
(command "insert" "mroads" '(23 -19) 1 1 0 )
(command "insert" "mroads" '(21 -15) 1 1 0 )
(command "insert" "mroads" '(43 -30) 1 1 0 )
(command "insert" "mroads" '(116 -32) 1 1 0 )
(command "insert" "mroads" '(8 -18) 1 1 0 )
(command "insert" "mroads" '(11 -15) 1 1 0 )
(command "insert" "mroads" '(35 -26) 1 1 0 )
(command "insert" "mroads" '(9 -19) 1 1 0 )
(command "insert" "mroads" '(36 -29) 1 1 0 )
(command "insert" "mroads" '(1 -21) 1 1 0 )
(command "insert" "mroads" '(25 -16) 1 1 0 )
(command "insert" "mroads" '(29 -20) 1 1 0 )
(command "insert" "mroads" '(37 -16) 1 1 0 )
(command "insert" "mroads" '(98 -30) 1 1 0 )
(command "insert" "mroads" '(38 -31) 1 1 0 )
(command "insert" "mroads" '(99 -31) 1 1 0 )
(command "insert" "mroads" '(39 -30) 1 1 0 )
(command "insert" "mroads" '(3 -17) 1 1 0 )
(command "insert" "mroads" '(19 -18) 1 1 0 )
(command "insert" "mroads" '(7 -15) 1 1 0 )
(command "insert" "mroads" '(31 -18) 1 1 0 )
(command "insert" "mroads" '(46 -30) 1 1 0 )
(command "insert" "mroads" '(6 -32) 1 1 0 )
(command "insert" "mroads" '(34 -32) 1 1 0 )
(command "insert" "mroads" '(32 -16) 1 1 0 )
(command "insert" "mroads" '(94 -30) 1 1 0 )
(command "insert" "mroads" '(18 -31) 1 1 0 )
(command "insert" "mroads" '(42 -32) 1 1 0 )
(command "insert" "mroads" '(86 -32) 1 1 0 )
(command "insert" "mroads" '(34 -26) 1 1 0 )
(command "insert" "mroads" '(8 -25) 1 1 0 )
(command "insert" "mroads" '(94 -32) 1 1 0 )
(command "insert" "mroads" '(9 -20) 1 1 0 )
(command "insert" "mroads" '(10 -19) 1 1 0 )
(command "insert" "mroads" '(37 -25) 1 1 0 )
(command "insert" "mroads" '(26 -30) 1 1 0 )
(command "insert" "mroads" '(7 -18) 1 1 0 )
(command "insert" "mroads" '(38 -22) 1 1 0 )
(command "insert" "mroads" '(27 -31) 1 1 0 )
(command "insert" "mroads" '(40 -20) 1 1 0 )
(command "insert" "mroads" '(39 -23) 1 1 0 )
(command "insert" "mroads" '(88 -31) 1 1 0 )
(command "insert" "mroads" '(74 -30) 1 1 0 )
(command "insert" "mroads" '(89 -30) 1 1 0 )
(command "insert" "mroads" '(3 -22) 1 1 0 )
(command "insert" "mroads" '(75 -31) 1 1 0 )
(command "insert" "mroads" '(4 -17) 1 1 0 )
(command "insert" "mroads" '(5 -20) 1 1 0 )
(command "insert" "mroads" '(6 -27) 1 1 0 )
(command "insert" "mroads" '(21 -17) 1 1 0 )
(command "insert" "mroads" '(17 -17) 1 1 0 )
(command "insert" "mroads" '(22 -30) 1 1 0 )
(command "insert" "mroads" '(33 -22) 1 1 0 )
(command "insert" "mroads" '(23 -31) 1 1 0 )
(command "insert" "mroads" '(12 -32) 1 1 0 )
(command "insert" "mroads" '(34 -21) 1 1 0 )
(command "insert" "mroads" '(70 -30) 1 1 0 )
(command "insert" "mroads" '(85 -30) 1 1 0 )
(command "insert" "mroads" '(48 -32) 1 1 0 )
(command "insert" "mroads" '(71 -31) 1 1 0 )
(command "insert" "mroads" '(34 -15) 1 1 0 )
(command "insert" "mroads" '(11 -19) 1 1 0 )
(command "insert" "mroads" '(100 -32) 1 1 0 )
(command "insert" "mroads" '(27 -20) 1 1 0 )
(command "insert" "mroads" '(1 -25) 1 1 0 )
(command "insert" "mroads" '(108 -32) 1 1 0 )
(command "insert" "mroads" '(2 -30) 1 1 0 )
(command "insert" "mroads" '(3 -31) 1 1 0 )
(command "insert" "mroads" '(64 -31) 1 1 0 )
(command "insert" "mroads" '(4 -24) 1 1 0 )
(command "insert" "mroads" '(19 -32) 1 1 0 )
(command "insert" "mroads" '(62 -31) 1 1 0 )
(command "insert" "mroads" '(50 -30) 1 1 0 )
(command "insert" "mroads" '(65 -30) 1 1 0 )
(command "insert" "mroads" '(5 -29) 1 1 0 )
(command "insert" "mroads" '(27 -32) 1 1 0 )
(command "insert" "mroads" '(6 -18) 1 1 0 )
(command "insert" "mroads" '(101 -32) 1 1 0 )
(command "insert" "mroads" '(112 -31) 1 1 0 )
(command "insert" "mroads" '(41 -21) 1 1 0 )
(command "insert" "mroads" '(22 -17) 1 1 0 )
(command "insert" "mroads" '(79 -32) 1 1 0 )
(command "insert" "mroads" '(18 -17) 1 1 0 )
(command "insert" "mroads" '(23 -20) 1 1 0 )
(command "insert" "mroads" '(40 -31) 1 1 0 )
(command "insert" "mroads" '(115 -32) 1 1 0 )
(command "insert" "mroads" '(60 -31) 1 1 0 )
(command "insert" "mroads" '(61 -30) 1 1 0 )
(command "insert" "mroads" '(35 -23) 1 1 0 )
(command "insert" "mroads" '(24 -16) 1 1 0 )
(command "insert" "mroads" '(36 -16) 1 1 0 )
(command "insert" "mroads" '(108 -31) 1 1 0 )
(command "insert" "mroads" '(37 -21) 1 1 0 )
(command "insert" "mroads" '(2 -25) 1 1 0 )
(command "insert" "mroads" '(109 -30) 1 1 0 )
(command "insert" "mroads" '(7 -16) 1 1 0 )
(command "insert" "mroads" '(38 -26) 1 1 0 )
(command "insert" "mroads" '(40 -18) 1 1 0 )
(command "insert" "mroads" '(114 -32) 1 1 0 )
(command "insert" "mroads" '(116 -30) 1 1 0 )
(command "insert" "mroads" '(6 -21) 1 1 0 )
(command "insert" "mroads" '(111 -31) 1 1 0 )
(command "insert" "mroads" '(19 -15) 1 1 0 )
(command "insert" "mroads" '(41 -30) 1 1 0 )
(command "insert" "mroads" '(5 -32) 1 1 0 )
(command "insert" "mroads" '(33 -32) 1 1 0 )
(command "insert" "mroads" '(41 -32) 1 1 0 )
(command "insert" "mroads" '(7 -29) 1 1 0 )
(command "insert" "mroads" '(85 -32) 1 1 0 )
(command "insert" "mroads" '(9 -15) 1 1 0 )
(command "insert" "mroads" '(33 -26) 1 1 0 )
(command "insert" "mroads" '(22 -31) 1 1 0 )
(command "insert" "mroads" '(93 -32) 1 1 0 )
(command "insert" "mroads" '(8 -20) 1 1 0 )
(command "insert" "mroads" '(37 -15) 1 1 0 )
(command "insert" "mroads" '(35 -28) 1 1 0 )
(command "insert" "mroads" '(9 -17) 1 1 0 )
(command "insert" "mroads" '(96 -30) 1 1 0 )
(command "insert" "mroads" '(36 -31) 1 1 0 )
(command "insert" "mroads" '(15 -15) 1 1 0 )
(command "insert" "mroads" '(97 -31) 1 1 0 )
(command "insert" "mroads" '(37 -30) 1 1 0 )
(command "insert" "mroads" '(38 -29) 1 1 0 )
(command "insert" "mroads" '(83 -31) 1 1 0 )
(command "insert" "mroads" '(39 -24) 1 1 0 )
(command "insert" "mroads" '(5 -15) 1 1 0 )
(command "insert" "mroads" '(3 -19) 1 1 0 )
(command "insert" "mroads" '(4 -20) 1 1 0 )
(command "insert" "mroads" '(19 -20) 1 1 0 )
(command "insert" "mroads" '(92 -30) 1 1 0 )
(command "insert" "mroads" '(16 -31) 1 1 0 )
(command "insert" "mroads" '(93 -31) 1 1 0 )
(command "insert" "mroads" '(17 -30) 1 1 0 )
(command "insert" "mroads" '(32 -18) 1 1 0 )
(command "insert" "mroads" '(11 -32) 1 1 0 )
(command "insert" "mroads" '(33 -19) 1 1 0 )
(command "insert" "mroads" '(40 -29) 1 1 0 )
(command "insert" "mroads" '(8 -27) 1 1 0 )
(command "insert" "mroads" '(63 -32) 1 1 0 )
(command "insert" "mroads" '(5 -21) 1 1 0 )
(command "insert" "mroads" '(24 -30) 1 1 0 )
(command "insert" "mroads" '(14 -17) 1 1 0 )
(command "insert" "mroads" '(71 -32) 1 1 0 )
(command "insert" "mroads" '(10 -17) 1 1 0 )
(command "insert" "mroads" '(25 -31) 1 1 0 )
(command "insert" "mroads" '(99 -32) 1 1 0 )
(command "insert" "mroads" '(111 -32) 1 1 0 )
(command "insert" "mroads" '(107 -32) 1 1 0 )
(command "insert" "mroads" '(38 -20) 1 1 0 )
(command "insert" "mroads" '(12 -31) 1 1 0 )
(command "insert" "mroads" '(27 -17) 1 1 0 )
(command "insert" "mroads" '(39 -17) 1 1 0 )
(command "insert" "mroads" '(13 -30) 1 1 0 )
(command "insert" "mroads" '(41 -24) 1 1 0 )
(command "insert" "mroads" '(3 -24) 1 1 0 )
(command "insert" "mroads" '(56 -32) 1 1 0 )
(command "insert" "mroads" '(4 -19) 1 1 0 )
(command "insert" "mroads" '(26 -32) 1 1 0 )
(command "insert" "mroads" '(5 -18) 1 1 0 )
(command "insert" "mroads" '(20 -30) 1 1 0 )
(command "insert" "mroads" '(6 -25) 1 1 0 )
(command "insert" "mroads" '(21 -31) 1 1 0 )
(command "insert" "mroads" '(40 -22) 1 1 0 )
(command "insert" "mroads" '(78 -32) 1 1 0 )
(command "insert" "mroads" '(41 -18) 1 1 0 )
(command "insert" "mroads" '(18 -20) 1 1 0 )
(command "insert" "mroads" '(33 -20) 1 1 0 )
(command "insert" "mroads" '(69 -31) 1 1 0 )
(command "insert" "mroads" '(34 -19) 1 1 0 )
(command "insert" "mroads" '(32 -15) 1 1 0 )
(command "insert" "mroads" '(15 -32) 1 1 0 )
(command "insert" "mroads" '(64 -32) 1 1 0 )
(command "insert" "mroads" '(35 -16) 1 1 0 )
(command "insert" "mroads" '(38 -15) 1 1 0 )
(command "insert" "mroads" '(77 -32) 1 1 0 )
(command "insert" "mroads" '(1 -31) 1 1 0 )
(command "insert" "mroads" '(28 -17) 1 1 0 )
(command "insert" "mroads" '(2 -28) 1 1 0 )
(command "insert" "mroads" '(48 -30) 1 1 0 )
(command "insert" "mroads" '(113 -32) 1 1 0 )
(command "insert" "mroads" '(49 -31) 1 1 0 )
(command "insert" "mroads" '(4 -26) 1 1 0 )
(command "insert" "mroads" '(28 -15) 1 1 0 )
(command "insert" "mroads" '(5 -27) 1 1 0 )
(command "insert" "mroads" '(40 -26) 1 1 0 )
(command "insert" "mroads" '(4 -32) 1 1 0 )
(command "insert" "mroads" '(7 -21) 1 1 0 )
(command "insert" "mroads" '(18 -15) 1 1 0 )
(command "insert" "mroads" '(40 -32) 1 1 0 )
(command "insert" "mroads" '(34 -20) 1 1 0 )
(command "insert" "mroads" '(58 -31) 1 1 0 )
(command "insert" "mroads" '(44 -30) 1 1 0 )
(command "insert" "mroads" '(59 -30) 1 1 0 )
(command "insert" "mroads" '(92 -32) 1 1 0 )
(command "insert" "mroads" '(45 -31) 1 1 0 )
(command "insert" "mroads" '(6 -17) 1 1 0 )
(command "insert" "mroads" '(106 -31) 1 1 0 )
(command "insert" "mroads" '(35 -25) 1 1 0 )
(command "insert" "mroads" '(24 -18) 1 1 0 )
(command "insert" "mroads" '(107 -30) 1 1 0 )
(command "insert" "mroads" '(36 -18) 1 1 0 )
(command "insert" "mroads" '(25 -19) 1 1 0 )
(command "insert" "mroads" '(13 -16) 1 1 0 )
(command "insert" "mroads" '(37 -19) 1 1 0 )
(command "insert" "mroads" '(2 -23) 1 1 0 )
(command "insert" "mroads" '(38 -24) 1 1 0 )
(command "insert" "mroads" '(39 -29) 1 1 0 )
(command "insert" "mroads" '(54 -31) 1 1 0 )
(command "insert" "mroads" '(115 -31) 1 1 0 )
(command "insert" "mroads" '(55 -30) 1 1 0 )
(command "insert" "mroads" '(22 -20) 1 1 0 )
(command "insert" "mroads" '(30 -20) 1 1 0 )
(command "insert" "mroads" '(19 -17) 1 1 0 )
(command "insert" "mroads" '(102 -31) 1 1 0 )
(command "insert" "mroads" '(41 -28) 1 1 0 )
(command "insert" "mroads" '(31 -17) 1 1 0 )
(command "insert" "mroads" '(103 -30) 1 1 0 )
(command "insert" "mroads" '(10 -32) 1 1 0 )
(command "insert" "mroads" '(22 -32) 1 1 0 )
(command "insert" "mroads" '(18 -32) 1 1 0 )
(command "insert" "mroads" '(33 -24) 1 1 0 )
(command "insert" "mroads" '(62 -32) 1 1 0 )
(command "insert" "mroads" '(110 -30) 1 1 0 )
(command "insert" "mroads" '(34 -31) 1 1 0 )
(command "insert" "mroads" '(8 -22) 1 1 0 )
(command "insert" "mroads" '(23 -17) 1 1 0 )
(command "insert" "mroads" '(70 -32) 1 1 0 )
(command "insert" "mroads" '(35 -30) 1 1 0 )
(command "insert" "mroads" '(98 -32) 1 1 0 )
(command "insert" "mroads" '(36 -25) 1 1 0 )
(command "insert" "mroads" '(10 -20) 1 1 0 )
(command "insert" "mroads" '(25 -20) 1 1 0 )
(command "insert" "mroads" '(82 -31) 1 1 0 )
(command "insert" "mroads" '(106 -32) 1 1 0 )
(command "insert" "mroads" '(37 -28) 1 1 0 )
(command "insert" "mroads" '(26 -19) 1 1 0 )
(command "insert" "mroads" '(38 -19) 1 1 0 )
(command "insert" "mroads" '(3 -15) 1 1 0 )
(command "insert" "mroads" '(39 -26) 1 1 0 )
(command "insert" "mroads" '(51 -31) 1 1 0 )
(command "insert" "mroads" '(3 -21) 1 1 0 )
(command "insert" "mroads" '(25 -32) 1 1 0 )
(command "insert" "mroads" '(90 -30) 1 1 0 )
(command "insert" "mroads" '(30 -31) 1 1 0 )
(command "insert" "mroads" '(4 -22) 1 1 0 )
(command "insert" "mroads" '(91 -31) 1 1 0 )
(command "insert" "mroads" '(31 -30) 1 1 0 )
(command "insert" "mroads" '(5 -23) 1 1 0 )
(command "insert" "mroads" '(20 -17) 1 1 0 )
(command "insert" "mroads" '(16 -17) 1 1 0 )
(command "insert" "mroads" '(21 -20) 1 1 0 )
(command "insert" "mroads" '(32 -20) 1 1 0 )
(command "insert" "mroads" '(33 -17) 1 1 0 )
(command "insert" "mroads" '(34 -22) 1 1 0 )
(command "insert" "mroads" '(8 -29) 1 1 0 )
(command "insert" "mroads" '(61 -31) 1 1 0 )
(command "insert" "mroads" '(86 -30) 1 1 0 )
(command "insert" "mroads" '(10 -31) 1 1 0 )
(command "insert" "mroads" '(6 -19) 1 1 0 )
(command "insert" "mroads" '(87 -31) 1 1 0 )
(command "insert" "mroads" '(11 -30) 1 1 0 )
(command "insert" "mroads" '(76 -32) 1 1 0 )
(command "insert" "mroads" '(27 -19) 1 1 0 )
(command "insert" "mroads" '(39 -19) 1 1 0 )
(command "insert" "mroads" '(28 -20) 1 1 0 )
(command "insert" "mroads" '(3 -26) 1 1 0 )
(command "insert" "mroads" '(40 -15) 1 1 0 )
(command "insert" "mroads" '(4 -29) 1 1 0 )
(command "insert" "mroads" '(19 -31) 1 1 0 )
(command "insert" "mroads" '(7 -26) 1 1 0 )
(command "insert" "mroads" '(5 -16) 1 1 0 )
(command "insert" "mroads" '(3 -32) 1 1 0 )
(command "insert" "mroads" '(66 -30) 1 1 0 )
(command "insert" "mroads" '(6 -31) 1 1 0 )
(command "insert" "mroads" '(67 -31) 1 1 0 )
(command "insert" "mroads" '(7 -30) 1 1 0 )
(command "insert" "mroads" '(22 -18) 1 1 0 )
(command "insert" "mroads" '(55 -32) 1 1 0 )
(command "insert" "mroads" '(18 -18) 1 1 0 )
(command "insert" "mroads" '(83 -32) 1 1 0 )
(command "insert" "mroads" '(114 -30) 1 1 0 )
(command "insert" "mroads" '(34 -17) 1 1 0 )
(command "insert" "mroads" '(91 -32) 1 1 0 )
(command "insert" "mroads" '(14 -30) 1 1 0 )
(command "insert" "mroads" '(36 -15) 1 1 0 )
(command "insert" "mroads" '(15 -31) 1 1 0 )
(command "insert" "mroads" '(35 -18) 1 1 0 )
(command "insert" "mroads" '(12 -16) 1 1 0 )
(command "insert" "mroads" '(36 -21) 1 1 0 )
(command "insert" "mroads" '(1 -29) 1 1 0 )
(command "insert" "mroads" '(63 -31) 1 1 0 )
(command "insert" "mroads" '(28 -19) 1 1 0 )
(command "insert" "mroads" '(2 -26) 1 1 0 )
(command "insert" "mroads" '(26 -15) 1 1 0 )
(command "insert" "mroads" '(12 -15) 1 1 0 )
(command "insert" "mroads" '(29 -18) 1 1 0 )
(command "insert" "mroads" '(5 -25) 1 1 0 )
(command "insert" "mroads" '(16 -15) 1 1 0 )
(command "insert" "mroads" '(6 -22) 1 1 0 )
(command "insert" "mroads" '(30 -19) 1 1 0 )
(command "insert" "mroads" '(41 -25) 1 1 0 )
(command "insert" "mroads" '(56 -31) 1 1 0 )
(command "insert" "mroads" '(9 -32) 1 1 0 )
(command "insert" "mroads" '(42 -30) 1 1 0 )
(command "insert" "mroads" '(23 -16) 1 1 0 )
(command "insert" "mroads" '(43 -31) 1 1 0 )
(command "insert" "mroads" '(17 -32) 1 1 0 )
(command "insert" "mroads" '(22 -15) 1 1 0 )
(command "insert" "mroads" '(61 -32) 1 1 0 )
(command "insert" "mroads" '(52 -30) 1 1 0 )
(command "insert" "mroads" '(105 -30) 1 1 0 )
(command "insert" "mroads" '(69 -32) 1 1 0 )
(command "insert" "mroads" '(34 -24) 1 1 0 )
(command "insert" "mroads" '(8 -17) 1 1 0 )
(command "insert" "mroads" '(97 -32) 1 1 0 )
(command "insert" "mroads" '(35 -27) 1 1 0 )
(command "insert" "mroads" '(24 -20) 1 1 0 )
(command "insert" "mroads" '(105 -32) 1 1 0 )
(command "insert" "mroads" '(36 -28) 1 1 0 )
(command "insert" "mroads" '(1 -22) 1 1 0 )
(command "insert" "mroads" '(6 -29) 1 1 0 )
(command "insert" "mroads" '(37 -17) 1 1 0 )
(command "insert" "mroads" '(2 -21) 1 1 0 )
(command "insert" "mroads" '(38 -30) 1 1 0 )
(command "insert" "mroads" '(53 -30) 1 1 0 )
(command "insert" "mroads" '(112 -32) 1 1 0 )
(command "insert" "mroads" '(39 -31) 1 1 0 )
(command "insert" "mroads" '(100 -31) 1 1 0 )
(command "insert" "mroads" '(24 -32) 1 1 0 )
(command "insert" "mroads" '(101 -30) 1 1 0 )
(command "insert" "mroads" '(19 -19) 1 1 0 )
(command "insert" "mroads" '(31 -19) 1 1 0 )
(command "insert" "mroads" '(20 -20) 1 1 0 )
(command "insert" "mroads" '(47 -31) 1 1 0 )
(command "insert" "mroads" '(32 -31) 1 1 0 )
(command "insert" "mroads" '(18 -30) 1 1 0 )
(command "insert" "mroads" '(33 -30) 1 1 0 )
(command "insert" "mroads" '(34 -29) 1 1 0 )
(command "insert" "mroads" '(8 -24) 1 1 0 )
(command "insert" "mroads" '(39 -32) 1 1 0 )
(command "insert" "mroads" '(80 -31) 1 1 0 )
(command "insert" "mroads" '(81 -30) 1 1 0 )
(command "insert" "mroads" '(36 -27) 1 1 0 )
(command "insert" "mroads" '(10 -18) 1 1 0 )
(command "insert" "mroads" '(75 -32) 1 1 0 )
(command "insert" "mroads" '(37 -26) 1 1 0 )
(command "insert" "mroads" '(26 -17) 1 1 0 )
(command "insert" "mroads" '(38 -17) 1 1 0 )
(command "insert" "mroads" '(39 -20) 1 1 0 )
(command "insert" "mroads" '(88 -30) 1 1 0 )
(command "insert" "mroads" '(28 -31) 1 1 0 )
(command "insert" "mroads" '(89 -31) 1 1 0 )
(command "insert" "mroads" '(29 -30) 1 1 0 )
(command "insert" "mroads" '(3 -23) 1 1 0 )
(command "insert" "mroads" '(4 -16) 1 1 0 )
(command "insert" "mroads" '(2 -32) 1 1 0 )
(command "insert" "mroads" '(76 -31) 1 1 0 )
(command "insert" "mroads" '(46 -32) 1 1 0 )
(command "insert" "mroads" '(20 -19) 1 1 0 )
(command "insert" "mroads" '(33 -29) 1 1 0 )
(command "insert" "mroads" '(77 -30) 1 1 0 )
(command "insert" "mroads" '(6 -26) 1 1 0 )
(command "insert" "mroads" '(21 -18) 1 1 0 )
(command "insert" "mroads" '(54 -32) 1 1 0 )
(command "insert" "mroads" '(33 -23) 1 1 0 )
(command "insert" "mroads" '(90 -32) 1 1 0 )
(command "insert" "mroads" '(84 -30) 1 1 0 )
(command "insert" "mroads" '(8 -31) 1 1 0 )
(command "insert" "mroads" '(95 -31) 1 1 0 )
(command "insert" "mroads" '(85 -31) 1 1 0 )
(command "insert" "mroads" '(9 -30) 1 1 0 )
(command "insert" "mroads" '(15 -16) 1 1 0 )
(command "insert" "mroads" '(11 -16) 1 1 0 )
(command "insert" "mroads" '(1 -26) 1 1 0 )
(command "insert" "mroads" '(40 -21) 1 1 0 )
(command "insert" "mroads" '(73 -31) 1 1 0 )
(command "insert" "mroads" '(3 -28) 1 1 0 )
(command "insert" "mroads" '(64 -30) 1 1 0 )
(command "insert" "mroads" '(4 -31) 1 1 0 )
(command "insert" "mroads" '(65 -31) 1 1 0 )
(command "insert" "mroads" '(5 -30) 1 1 0 )
(command "insert" "mroads" '(40 -23) 1 1 0 )
(command "insert" "mroads" '(112 -30) 1 1 0 )
(command "insert" "mroads" '(8 -32) 1 1 0 )
(command "insert" "mroads" '(41 -22) 1 1 0 )
(command "insert" "mroads" '(22 -16) 1 1 0 )
(command "insert" "mroads" '(113 -31) 1 1 0 )
(command "insert" "mroads" '(18 -16) 1 1 0 )
(command "insert" "mroads" '(16 -32) 1 1 0 )
(command "insert" "mroads" '(60 -32) 1 1 0 )
(command "insert" "mroads" '(68 -32) 1 1 0 )
(command "insert" "mroads" '(96 -32) 1 1 0 )
(command "insert" "mroads" '(60 -30) 1 1 0 )
(command "insert" "mroads" '(104 -32) 1 1 0 )
(command "insert" "mroads" '(35 -20) 1 1 0 )
(command "insert" "mroads" '(24 -15) 1 1 0 )
(command "insert" "mroads" '(36 -23) 1 1 0 )
(command "insert" "mroads" '(108 -30) 1 1 0 )
(command "insert" "mroads" '(37 -22) 1 1 0 )
(command "insert" "mroads" '(2 -24) 1 1 0 )
(command "insert" "mroads" '(109 -31) 1 1 0 )
(command "insert" "mroads" '(29 -16) 1 1 0 )
(command "insert" "mroads" '(30 -15) 1 1 0 )
(command "insert" "mroads" '(25 -18) 1 1 0 )
(command "insert" "mroads" '(40 -30) 1 1 0 )
(command "insert" "mroads" '(30 -17) 1 1 0 )
(command "insert" "mroads" '(7 -17) 1 1 0 )
(command "insert" "mroads" '(31 -20) 1 1 0 )
(command "insert" "mroads" '(20 -15) 1 1 0 )
(command "insert" "mroads" '(33 -31) 1 1 0 )
(command "insert" "mroads" '(23 -18) 1 1 0 )
(command "insert" "mroads" '(47 -32) 1 1 0 )
(command "insert" "mroads" '(33 -27) 1 1 0 )
(command "insert" "mroads" '(38 -32) 1 1 0 )
(command "insert" "mroads" '(10 -15) 1 1 0 )
(command "insert" "mroads" '(8 -19) 1 1 0 )
(command "insert" "mroads" '(35 -29) 1 1 0 )
(command "insert" "mroads" '(9 -18) 1 1 0 )
(command "insert" "mroads" '(74 -32) 1 1 0 )
(command "insert" "mroads" '(52 -32) 1 1 0 )
(command "insert" "mroads" '(36 -30) 1 1 0 )
(command "insert" "mroads" '(51 -30) 1 1 0 )
(command "insert" "mroads" '(41 -27) 1 1 0 )
(command "insert" "mroads" '(82 -32) 1 1 0 )
(command "insert" "mroads" '(37 -31) 1 1 0 )
(command "insert" "mroads" '(26 -20) 1 1 0 )
(command "insert" "mroads" '(7 -19) 1 1 0 )
(command "insert" "mroads" '(98 -31) 1 1 0 )
(command "insert" "mroads" '(38 -28) 1 1 0 )
(command "insert" "mroads" '(40 -19) 1 1 0 )
(command "insert" "mroads" '(99 -30) 1 1 0 )
(command "insert" "mroads" '(39 -25) 1 1 0 )
(command "insert" "mroads" '(3 -16) 1 1 0 )
(command "insert" "mroads" '(1 -32) 1 1 0 )
(command "insert" "mroads" '(6 -15) 1 1 0 )
(command "insert" "mroads" '(46 -31) 1 1 0 )
(command "insert" "mroads" '(53 -32) 1 1 0 )
(command "insert" "mroads" '(16 -30) 1 1 0 )
(command "insert" "mroads" '(47 -30) 1 1 0 )
(command "insert" "mroads" '(17 -31) 1 1 0 )
(command "insert" "mroads" '(32 -17) 1 1 0 )
(command "insert" "mroads" '(7 -28) 1 1 0 )
(command "insert" "mroads" '(89 -32) 1 1 0 )
(command "insert" "mroads" '(7 -24) 1 1 0 )
(command "insert" "mroads" '(94 -31) 1 1 0 )
(command "insert" "mroads" '(33 -28) 1 1 0 )
(command "insert" "mroads" '(95 -30) 1 1 0 )
(command "insert" "mroads" '(34 -27) 1 1 0 )
(command "insert" "mroads" '(8 -26) 1 1 0 )
(command "insert" "mroads" '(14 -16) 1 1 0 )
(command "insert" "mroads" '(10 -16) 1 1 0 )
(command "insert" "mroads" '(37 -24) 1 1 0 )
(command "insert" "mroads" '(68 -30) 1 1 0 )
(command "insert" "mroads" '(26 -31) 1 1 0 )
(command "insert" "mroads" '(26 -18) 1 1 0 )
(command "insert" "mroads" '(38 -23) 1 1 0 )
(command "insert" "mroads" '(83 -30) 1 1 0 )
(command "insert" "mroads" '(27 -30) 1 1 0 )
(command "insert" "mroads" '(39 -22) 1 1 0 )
(command "insert" "mroads" '(13 -31) 1 1 0 )
(command "insert" "mroads" '(74 -31) 1 1 0 )
(command "insert" "mroads" '(3 -25) 1 1 0 )
(command "insert" "mroads" '(75 -30) 1 1 0 )
(command "insert" "mroads" '(4 -18) 1 1 0 )
(command "insert" "mroads" '(62 -30) 1 1 0 )
(command "insert" "mroads" '(5 -19) 1 1 0 )
(command "insert" "mroads" '(23 -32) 1 1 0 )
(command "insert" "mroads" '(6 -24) 1 1 0 )
(command "insert" "mroads" '(21 -16) 1 1 0 )
(command "insert" "mroads" '(17 -16) 1 1 0 )
(command "insert" "mroads" '(41 -19) 1 1 0 )
(command "insert" "mroads" '(31 -32) 1 1 0 )
(command "insert" "mroads" '(59 -32) 1 1 0 )
(command "insert" "mroads" '(33 -21) 1 1 0 )
(command "insert" "mroads" '(23 -30) 1 1 0 )
(command "insert" "mroads" '(34 -18) 1 1 0 )
(command "insert" "mroads" '(67 -32) 1 1 0 )
(command "insert" "mroads" '(6 -20) 1 1 0 )
(command "insert" "mroads" '(70 -31) 1 1 0 )
(command "insert" "mroads" '(33 -15) 1 1 0 )
(command "insert" "mroads" '(71 -30) 1 1 0 )
(command "insert" "mroads" '(11 -18) 1 1 0 )
(command "insert" "mroads" '(35 -17) 1 1 0 )
(command "insert" "mroads" '(1 -24) 1 1 0 )
(command "insert" "mroads" '(39 -15) 1 1 0 )
(command "insert" "mroads" '(28 -16) 1 1 0 )
(command "insert" "mroads" '(2 -31) 1 1 0 )
(command "insert" "mroads" '(12 -30) 1 1 0 )
(command "insert" "mroads" '(41 -31) 1 1 0 )
(command "insert" "mroads" '(79 -31) 1 1 0 )
(command "insert" "mroads" '(3 -30) 1 1 0 )
(command "insert" "mroads" '(40 -17) 1 1 0 )
(command "insert" "mroads" '(4 -25) 1 1 0 )
(command "insert" "mroads" '(50 -31) 1 1 0 )
(command "insert" "mroads" '(5 -28) 1 1 0 )
(command "insert" "mroads" '(29 -15) 1 1 0 )
(command "insert" "mroads" '(40 -25) 1 1 0 )
(command "insert" "mroads" '(41 -20) 1 1 0 )
(command "insert" "mroads" '(58 -30) 1 1 0 )
(command "insert" "mroads" '(37 -32) 1 1 0 )
(command "insert" "mroads" '(59 -31) 1 1 0 )
(command "insert" "mroads" '(41 -16) 1 1 0 )
(command "insert" "mroads" '(45 -32) 1 1 0 )
(command "insert" "mroads" '(73 -32) 1 1 0 )
(command "insert" "mroads" '(106 -30) 1 1 0 )
(command "insert" "mroads" '(35 -22) 1 1 0 )
(command "insert" "mroads" '(24 -17) 1 1 0 )
(command "insert" "mroads" '(107 -31) 1 1 0 )
(command "insert" "mroads" '(81 -32) 1 1 0 )
(command "insert" "mroads" '(36 -17) 1 1 0 )
(command "insert" "mroads" '(13 -17) 1 1 0 )
(command "insert" "mroads" '(37 -20) 1 1 0 )
(command "insert" "mroads" '(2 -22) 1 1 0 )
(command "insert" "mroads" '(72 -30) 1 1 0 )
(command "insert" "mroads" '(38 -27) 1 1 0 )
(command "insert" "mroads" '(54 -30) 1 1 0 )
(command "insert" "mroads" '(34 -23) 1 1 0 )
(command "insert" "mroads" '(55 -31) 1 1 0 )
(command "insert" "mroads" '(116 -31) 1 1 0 )
(command "insert" "mroads" '(102 -30) 1 1 0 )
(command "insert" "mroads" '(41 -29) 1 1 0 )
(command "insert" "mroads" '(103 -31) 1 1 0 )
(command "insert" "mroads" '(88 -32) 1 1 0 )
(command "insert" "mroads" '(84 -31) 1 1 0 )
(command "insert" "mroads" '(8 -15) 1 1 0 )
(command "insert" "mroads" '(33 -25) 1 1 0 )
(command "insert" "mroads" '(34 -30) 1 1 0 )
(command "insert" "mroads" '(8 -21) 1 1 0 )
(command "insert" "mroads" '(35 -31) 1 1 0 )
(command "insert" "mroads" '(9 -16) 1 1 0 )
(command "insert" "mroads" '(14 -15) 1 1 0 )
(command "insert" "mroads" '(40 -28) 1 1 0 )
(command "insert" "mroads" '(96 -31) 1 1 0 )
(command "insert" "mroads" '(36 -24) 1 1 0 )
(command "insert" "mroads" '(78 -31) 1 1 0 )
(command "insert" "mroads" '(82 -30) 1 1 0 )
(command "insert" "mroads" '(97 -30) 1 1 0 )
(command "insert" "mroads" '(37 -29) 1 1 0 )
(command "insert" "mroads" '(31 -31) 1 1 0 )
(command "insert" "mroads" '(38 -18) 1 1 0 )
(command "insert" "mroads" '(103 -32) 1 1 0 )
(command "insert" "mroads" '(39 -27) 1 1 0 )
(command "insert" "mroads" '(4 -15) 1 1 0 )
(command "insert" "mroads" '(7 -23) 1 1 0 )
(command "insert" "mroads" '(3 -18) 1 1 0 )
(command "insert" "mroads" '(30 -30) 1 1 0 )
(command "insert" "mroads" '(4 -21) 1 1 0 )
(command "insert" "mroads" '(79 -30) 1 1 0 )
(command "insert" "mroads" '(20 -16) 1 1 0 )
(command "insert" "mroads" '(92 -31) 1 1 0 )
(command "insert" "mroads" '(16 -16) 1 1 0 )
(command "insert" "mroads" '(30 -32) 1 1 0 )
(command "insert" "mroads" '(93 -30) 1 1 0 )
(command "insert" "mroads" '(58 -32) 1 1 0 )
(command "insert" "mroads" '(32 -19) 1 1 0 )
(command "insert" "mroads" '(33 -18) 1 1 0 )
(command "insert" "mroads" '(66 -32) 1 1 0 )
(command "insert" "mroads" '(110 -32) 1 1 0 )
(command "insert" "mroads" '(34 -25) 1 1 0 )
(command "insert" "mroads" '(8 -28) 1 1 0 )
(command "insert" "mroads" '(57 -30) 1 1 0 )
(command "insert" "mroads" '(24 -31) 1 1 0 )
(command "insert" "mroads" '(10 -30) 1 1 0 )
(command "insert" "mroads" '(25 -30) 1 1 0 )
(command "insert" "mroads" '(11 -31) 1 1 0 )
(command "insert" "mroads" '(72 -31) 1 1 0 )
(command "insert" "mroads" '(27 -16) 1 1 0 )
(command "insert" "mroads" '(49 -32) 1 1 0 )
(command "insert" "mroads" '(73 -30) 1 1 0 )
(command "insert" "mroads" '(3 -27) 1 1 0 )
(command "insert" "mroads" '(4 -28) 1 1 0 )
(command "insert" "mroads" '(41 -15) 1 1 0 )
(command "insert" "mroads" '(5 -17) 1 1 0 )
(command "insert" "mroads" '(20 -31) 1 1 0 )
(command "insert" "mroads" '(6 -30) 1 1 0 )
(command "insert" "mroads" '(21 -30) 1 1 0 )
(command "insert" "mroads" '(7 -31) 1 1 0 )
(command "insert" "mroads" '(68 -31) 1 1 0 )
(command "insert" "mroads" '(36 -32) 1 1 0 )
(command "insert" "mroads" '(69 -30) 1 1 0 )
(command "insert" "mroads" '(34 -16) 1 1 0 )
(command "insert" "mroads" '(44 -32) 1 1 0 )
(command "insert" "mroads" '(72 -32) 1 1 0 )
(command "insert" "mroads" '(6 -16) 1 1 0 )
(command "insert" "mroads" '(80 -32) 1 1 0 )
(command "insert" "mroads" '(11 -20) 1 1 0 )
(command "insert" "mroads" '(35 -19) 1 1 0 )
(command "insert" "mroads" '(36 -20) 1 1 0 )
(command "insert" "mroads" '(1 -30) 1 1 0 )
(command "insert" "mroads" '(28 -18) 1 1 0 )
(command "insert" "mroads" '(2 -29) 1 1 0 )
(command "insert" "mroads" '(48 -31) 1 1 0 )
(command "insert" "mroads" '(29 -19) 1 1 0 )
(command "insert" "mroads" '(27 -15) 1 1 0 )
(command "insert" "mroads" '(49 -30) 1 1 0 )
(command "insert" "mroads" '(4 -27) 1 1 0 )
(command "insert" "mroads" '(32 -32) 1 1 0 )
(command "insert" "mroads" '(5 -26) 1 1 0 )
(command "insert" "mroads" '(51 -32) 1 1 0 )
(command "insert" "mroads" '(40 -27) 1 1 0 )
(command "insert" "mroads" '(30 -18) 1 1 0 )
(command "insert" "mroads" '(17 -15) 1 1 0 )
(command "insert" "mroads" '(41 -26) 1 1 0 )
(command "insert" "mroads" '(56 -30) 1 1 0 )
(command "insert" "mroads" '(57 -31) 1 1 0 )
(command "insert" "mroads" '(86 -31) 1 1 0 )
(command "insert" "mroads" '(104 -30) 1 1 0 )
(command "insert" "mroads" '(44 -31) 1 1 0 )
(command "insert" "mroads" '(23 -15) 1 1 0 )
(command "insert" "mroads" '(105 -31) 1 1 0 )
(command "insert" "mroads" '(45 -30) 1 1 0 )
(command "insert" "mroads" '(8 -16) 1 1 0 )
(command "insert" "mroads" '(35 -24) 1 1 0 )
(command "insert" "mroads" '(50 -32) 1 1 0 )
(command "insert" "mroads" '(24 -19) 1 1 0 )
(command "insert" "mroads" '(36 -19) 1 1 0 )
(command "insert" "mroads" '(1 -23) 1 1 0 )
(command "insert" "mroads" '(104 -31) 1 1 0 )
(command "insert" "mroads" '(13 -15) 1 1 0 )
(command "insert" "mroads" '(37 -18) 1 1 0 )
(command "insert" "mroads" '(102 -32) 1 1 0 )
(command "insert" "mroads" '(38 -25) 1 1 0 )
(command "insert" "mroads" '(53 -31) 1 1 0 )
(command "insert" "mroads" '(78 -30) 1 1 0 )
(command "insert" "mroads" '(39 -28) 1 1 0 )
(command "insert" "mroads" '(84 -32) 1 1 0 )
(command "insert" "mroads" '(100 -30) 1 1 0 )
(command "insert" "mroads" '(115 -30) 1 1 0 )
(command "insert" "mroads" '(25 -17) 1 1 0 )
(command "insert" "mroads" '(101 -31) 1 1 0 )
(command "insert" "mroads" '(21 -32) 1 1 0 )
(command "insert" "mroads" '(19 -16) 1 1 0 )
(command "insert" "mroads" '(31 -16) 1 1 0 )
(command "insert" "mroads" '(29 -32) 1 1 0 )
(command "insert" "mroads" '(41 -17) 1 1 0 )
(command "insert" "mroads" '(32 -30) 1 1 0 )
(command "insert" "mroads" '(65 -32) 1 1 0 )
(command "insert" "mroads" '(52 -31) 1 1 0 )
(command "insert" "mroads" '(7 -20) 1 1 0 )
(command "insert" "mroads" '(110 -31) 1 1 0 )
(command "insert" "mroads" '(34 -28) 1 1 0 )
(command "insert" "mroads" '(8 -23) 1 1 0 )
(command "insert" "mroads" '(80 -30) 1 1 0 )
(command "insert" "mroads" '(111 -30) 1 1 0 )
(command "insert" "mroads" '(57 -32) 1 1 0 )
(command "insert" "mroads" '(81 -31) 1 1 0 )
(command "insert" "mroads" '(36 -26) 1 1 0 )
(command "insert" "mroads" '(40 -24) 1 1 0 )
(command "insert" "mroads" '(37 -27) 1 1 0 )
(command "insert" "mroads" '(26 -16) 1 1 0 )
(command "insert" "mroads" '(38 -16) 1 1 0 )
(command "insert" "mroads" '(39 -21) 1 1 0 )
(command "insert" "mroads" '(28 -30) 1 1 0 )
(command "insert" "mroads" '(29 -31) 1 1 0 )
(command "insert" "mroads" '(3 -20) 1 1 0 )
(command "insert" "mroads" '(90 -31) 1 1 0 )
(command "insert" "mroads" '(4 -23) 1 1 0 )
(command "insert" "mroads" '(76 -30) 1 1 0 )
(command "insert" "mroads" '(91 -30) 1 1 0 )
(command "insert" "mroads" '(7 -27) 1 1 0 )
(command "insert" "mroads" '(5 -22) 1 1 0 )
(command "insert" "mroads" '(20 -18) 1 1 0 )
(command "insert" "mroads" '(77 -31) 1 1 0 )
(command "insert" "mroads" '(21 -19) 1 1 0 )
(command "insert" "mroads" '(7 -32) 1 1 0 )
(command "insert" "mroads" '(35 -32) 1 1 0 )
(command "insert" "mroads" '(113 -30) 1 1 0 )
(command "insert" "mroads" '(33 -16) 1 1 0 )
(command "insert" "mroads" '(43 -32) 1 1 0 )
(command "insert" "mroads" '(8 -30) 1 1 0 )
(command "insert" "mroads" '(40 -16) 1 1 0 )
(command "insert" "mroads" '(87 -32) 1 1 0 )
(command "insert" "mroads" '(9 -31) 1 1 0 )
(command "insert" "mroads" '(95 -32) 1 1 0 )
(command "insert" "mroads" '(15 -17) 1 1 0 )
(command "insert" "mroads" '(87 -30) 1 1 0 )
(command "insert" "mroads" '(11 -17) 1 1 0 )
(command "insert" "mroads" '(27 -18) 1 1 0 )
(command "insert" "mroads" '(1 -27) 1 1 0 )
(command "insert" "mroads" '(39 -18) 1 1 0 )
(command "insert" "mroads" '(14 -32) 1 1 0 )
(command "insert" "mroads" '(3 -29) 1 1 0 )
(command "insert" "mroads" '(4 -30) 1 1 0 )
(command "insert" "mroads" '(19 -30) 1 1 0 )
(command "layer" "m" "Commmer" "" )
(command "insert" "Commmer" '(32 -1) 1 1 0 )
(command "insert" "Commmer" '(23 -1) 1 1 0 )
(command "insert" "Commmer" '(21 -2) 1 1 0 )
(command "insert" "Commmer" '(16 -2) 1 1 0 )
(command "insert" "Commmer" '(26 -2) 1 1 0 )
(command "insert" "Commmer" '(28 -1) 1 1 0 )
(command "insert" "Commmer" '(25 -1) 1 1 0 )
(command "insert" "Commmer" '(27 -2) 1 1 0 )
(command "insert" "Commmer" '(32 -2) 1 1 0 )
(command "insert" "Commmer" '(18 -1) 1 1 0 )
(command "insert" "Commmer" '(31 -1) 1 1 0 )
(command "insert" "Commmer" '(22 -2) 1 1 0 )
(command "insert" "Commmer" '(21 -1) 1 1 0 )
(command "insert" "Commmer" '(23 -2) 1 1 0 )
(command "insert" "Commmer" '(17 -2) 1 1 0 )
(command "insert" "Commmer" '(28 -2) 1 1 0 )
(command "insert" "Commmer" '(34 -1) 1 1 0 )
(command "insert" "Commmer" '(24 -1) 1 1 0 )
(command "insert" "Commmer" '(33 -2) 1 1 0 )
(command "insert" "Commmer" '(30 -1) 1 1 0 )
(command "insert" "Commmer" '(27 -1) 1 1 0 )
(command "insert" "Commmer" '(18 -2) 1 1 0 )
(command "insert" "Commmer" '(20 -1) 1 1 0 )
(command "insert" "Commmer" '(17 -1) 1 1 0 )
(command "insert" "Commmer" '(19 -2) 1 1 0 )
(command "insert" "Commmer" '(29 -2) 1 1 0 )
(command "insert" "Commmer" '(24 -2) 1 1 0 )
(command "insert" "Commmer" '(34 -2) 1 1 0 )
(command "insert" "Commmer" '(35 -1) 1 1 0 )
(command "insert" "Commmer" '(15 -1) 1 1 0 )
(command "insert" "Commmer" '(33 -1) 1 1 0 )
(command "insert" "Commmer" '(35 -2) 1 1 0 )
(command "insert" "Commmer" '(15 -2) 1 1 0 )
(command "insert" "Commmer" '(26 -1) 1 1 0 )
(command "insert" "Commmer" '(20 -2) 1 1 0 )
(command "insert" "Commmer" '(30 -2) 1 1 0 )
(command "insert" "Commmer" '(16 -1) 1 1 0 )
(command "insert" "Commmer" '(29 -1) 1 1 0 )
(command "insert" "Commmer" '(31 -2) 1 1 0 )
(command "insert" "Commmer" '(25 -2) 1 1 0 )
(command "insert" "Commmer" '(22 -1) 1 1 0 )
(command "insert" "Commmer" '(19 -1) 1 1 0 )
